-- ****************************************************************************
-- Copyright (c) 2017 :
-- Westermo Teleindustri AB
-- 640 40 Stora Sundby
-- Sweden
-- url: http://www.westermo.com
--
-- Contact:  support@westermo.se
-- Description: Westermo WeOS Tech Preview Private MIB-file #### TECHNOLOGY PREVIEW ONLY ###
--
-- ****************************************************************************

WESTERMO-WEOS-TECHPREVIEW-MIB DEFINITIONS ::= BEGIN

IMPORTS
    NOTIFICATION-TYPE
    FROM SNMPv2-SMI

    otherNotificationPrefix
    FROM WESTERMO-WEOS-MIB;

-- -------------------------------------------------------------
-- Notification group
-- -------------------------------------------------------------
-- -------------------------------------------------------------
-- Notification: Other
-- -------------------------------------------------------------

remoteTriggerSet NOTIFICATION-TYPE
OBJECTS { remoteTriggerStatus }
      STATUS current
      DESCRIPTION
          "Notification associated with Remote trigger state."
      ::= { otherNotificationPrefix 1 }

remoteTriggerTimeout NOTIFICATION-TYPE
OBJECTS { remoteTriggerStatus }
      STATUS current
      DESCRIPTION
          "Notification associated with Remote triggert state."
      ::= { otherNotificationPrefix 2 }


END
