-- *****************************************************************
-- Moxa NPort 6000 Series MIB
--
-- Copyright (c) 2006-2020 by Moxa Inc.
-- All rights reserved.

-- Version: 1.16
-- Date: 2017/03/15
-- *****************************************************************

MOXA-NP6000-MIB DEFINITIONS ::= BEGIN
    IMPORTS
        enterprises, IpAddress, OBJECT-TYPE
        	FROM SNMPv2-SMI
        	TEXTUAL-CONVENTION, MacAddress, DisplayString  
        	FROM SNMPv2-TC;
        
    moxa 				OBJECT IDENTIFIER ::= { enterprises 8691 }	-- 1.3.6.1.4.1.8691
    
    nport OBJECT IDENTIFIER ::= { moxa 2 }			-- 1.3.6.1.4.1.8691.2
    
    np6000   MODULE-IDENTITY
	    LAST-UPDATED "201703150000Z"
	    ORGANIZATION "Moxa Inc."
	    CONTACT-INFO
	            "Email: support@moxa.com
    			     Tel: +886-2-89191230"
	             
	    DESCRIPTION
	            "The MIB module for Moxa NPort 6000 Series specific information."            
	
	    ::= { nport 8 }    -- 1.3.6.1.4.1.8691.2.8
    
-- -------------------------------------------------------------
-- groups in the MOXA-NP6000 MIB
-- -------------------------------------------------------------

swMgmt		OBJECT IDENTIFIER ::= { np6000 1 }			-- 1.3.6.1.4.1.8691.2.8.1    

-- -------------------------------------------------------------
-- Textual Conventions
-- -------------------------------------------------------------

PortList ::= TEXTUAL-CONVENTION
	STATUS			current
	DESCRIPTION		
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING
	
-- -------------------------------------------------------------
-- swMgmt group
-- -------------------------------------------------------------

-- -------------------------------------------------------------
-- Overview
-- -------------------------------------------------------------

	overview OBJECT IDENTIFIER ::= { swMgmt 1 }		-- 1.3.6.1.4.1.8691.2.8.1.1

    modelName OBJECT-TYPE
        SYNTAX DisplayString
        MAX-ACCESS read-only
        STATUS current
        DESCRIPTION
            "The model name of the NPort. The possible values 
	    of this parameter are:
            'NP6150' for NPort 6150, 'NP6250' for NPort 6250,
            'NP6250-S-SC' for NPort 6250-S-SC, 'NP6250-M-SC' for
            NPort NPort 6250-M-SC, 'NP6450' for NPort 6450,
            'NP6650-8' for NPort 6650-8, and 'NP6650-16' for NPort
            6650-16."
        ::= { overview 1 }							-- 1.3.6.1.4.1.8691.2.8.1.1.1
    
    serialNumber OBJECT-TYPE
        SYNTAX INTEGER
        MAX-ACCESS read-only
        STATUS current
        DESCRIPTION
            "The serial number of the NPort. Every NPort 6000
            series device server is assigned a unique serial
            number before it is shipped."
        ::= { overview 2 }
    
    firmwareVersion OBJECT-TYPE
        SYNTAX DisplayString
        MAX-ACCESS read-only                
        STATUS current
        DESCRIPTION
            "The version of the firmware currently running on
            the NPort."
        ::= { overview 3 }
    
    macAddress OBJECT-TYPE
        SYNTAX MacAddress
        MAX-ACCESS read-only               
        STATUS current
        DESCRIPTION
            "The MAC address of the NPort's Ethernet interface."
        ::= { overview 4 }

    viewLanSpeed OBJECT-TYPE
        SYNTAX DisplayString
        MAX-ACCESS read-only               
        STATUS current
        DESCRIPTION
            "The current speed and link status of the NPort's built-in
            LAN port. The possible values are 'No link',
            '10M/Link,' or '100M/Link.'"
        ::= { overview 5 }
        
    viewLanModuleSpeed OBJECT-TYPE
        SYNTAX DisplayString
        MAX-ACCESS read-only               
        STATUS current
        DESCRIPTION
            "The current speed and link status of the 
             the network module's LAN ports, if 
            the module is installed.
            The value includes two parts. Each part indicates the
            status of one of the LAN ports. The possible values 
            are 'No link', '10M/Link,' '100M/Link,' or continunous 
            dashes to indicate that the LAN module is not installed."
        ::= { overview 6 }

	upTime OBJECT-TYPE
        SYNTAX DisplayString
        MAX-ACCESS read-only               
        STATUS current
        DESCRIPTION
            "The time (in human-readable notation) since the
            system was last re-initialized."
        ::= { overview 7 }
        
    moduleType OBJECT-TYPE
        SYNTAX DisplayString
        MAX-ACCESS read-only               
        STATUS current
        DESCRIPTION
            "The module name currently plugged into the NPort."
        ::= { overview 8 }
    
    moduleApVersion OBJECT-TYPE
        SYNTAX DisplayString
        MAX-ACCESS read-only               
        STATUS current
        DESCRIPTION
            "The module AP version currently plugged into the NPort."
        ::= { overview 9 }    
    
    viewIpv4Address OBJECT-TYPE
        SYNTAX DisplayString
        MAX-ACCESS read-only                
        STATUS current
        DESCRIPTION
            "An IPv4 address is a number assigned to a network
            device (such as a computer) as a permanent address
            on the network. Computers use the IP address to
            identify and talk to each other over the network.
            Choose a proper IP address that is unique and valid
            in your network environment."
        ::= { overview 10 }
    
    viewIpv6LinkLocalAddress OBJECT-TYPE
        SYNTAX DisplayString
        MAX-ACCESS read-only                
        STATUS current
        DESCRIPTION
            "An IPv6 Link-Local address is a number assigned to a network
            device (such as a computer) as a permanent address
            on the network. Computers use the IP address to
            identify and talk to each other over the network.
            Choose a proper IP address that is unique and valid
            in your network environment."
        ::= { overview 11 }
    
    viewIpv6GlobalAddress OBJECT-TYPE
        SYNTAX DisplayString
        MAX-ACCESS read-only                
        STATUS current
        DESCRIPTION
            "An IPv6 Global address is a number assigned to a network
            device (such as a computer) as a permanent address
            on the network. Computers use the IP address to
            identify and talk to each other over the network.
            Choose a proper IP address that is unique and valid
            in your network environment."
        ::= { overview 12 }

-- -------------------------------------------------------------
-- Basic settings
-- -------------------------------------------------------------

	basicSetting OBJECT IDENTIFIER ::= { swMgmt 2}			-- 1.3.6.1.4.1.8691.2.8.1.2

-- -------------------------------------------------------------
-- Basic settings -> Server settings
-- -------------------------------------------------------------
	
	serverSetting OBJECT IDENTIFIER ::= { basicSetting 1 }	-- 1.3.6.1.4.1.8691.2.8.1.2.1
	
	serverName OBJECT-TYPE
        SYNTAX DisplayString
        MAX-ACCESS read-write                
        STATUS current
        DESCRIPTION
            "A text string used to identify the NPort."
        ::= { serverSetting 1 }
       
    serverLocation OBJECT-TYPE
        SYNTAX DisplayString
        MAX-ACCESS read-write                
        STATUS current
        DESCRIPTION
            "A text string used to identify the location of the NPort. This
            option is useful for specifying the location or
            application of different NPort device servers."
        ::= { serverSetting 2 }
        
-- -------------------------------------------------------------
-- Basic settings -> Time settings
-- -------------------------------------------------------------
	
	timeSetting OBJECT IDENTIFIER ::= { basicSetting 2 }	-- 1.3.6.1.4.1.8691.2.8.1.2.2
	
    timeZone OBJECT-TYPE
        SYNTAX INTEGER
        MAX-ACCESS read-write                
        STATUS current
        DESCRIPTION
            "The time-zone index of the NPort."
        ::= { timeSetting 1 }
    
    localTime OBJECT-TYPE
        SYNTAX DisplayString (SIZE (0..19))
        MAX-ACCESS read-write               
        STATUS current
        DESCRIPTION
            "The system time in the following format 
            yyyy/mm/dd hh:mm:ss"
        ::= { timeSetting 2 }
        
    timeServer OBJECT-TYPE
        SYNTAX DisplayString
        MAX-ACCESS read-write               
        STATUS current
        DESCRIPTION
            "The NPort 6000 series device server uses SNTP
            (RFC-1769) for auto time calibration.
            Input the correct 'Time server' IP address or domain
            name. Once the NPort 6000 series device server is
            configured with the correct Time server address, it
            will request time information from the Time server
            every 10 minutes."
        ::= { timeSetting 3 }

-- -------------------------------------------------------------
-- Network settings -> Basic
-- -------------------------------------------------------------
    
    networkSetting OBJECT IDENTIFIER ::= { swMgmt 3 }		-- 1.3.6.1.4.1.8691.2.8.1.3
    
    ipv4Configuration OBJECT-TYPE
        SYNTAX INTEGER { static(0), dhcp(1), dhcp-BOOTP(2), bootp(3), pppoe(4)}
        MAX-ACCESS read-write               
        STATUS current
        DESCRIPTION
            "The IPv4 configuration mode of the NPort. You can
            choose from four possible IP configuration modes:
            Static, DHCP, DHCP/BOOTP, BOOTP, and PPPoE."
        ::= { networkSetting 1 }
        
    ipv4Address OBJECT-TYPE
        SYNTAX IpAddress
        MAX-ACCESS read-write                
        STATUS current
        DESCRIPTION
            "An IPv4 address is a number assigned to a network
            device (such as a computer) as a permanent address
            on the network. Computers use the IP address to
            identify and talk to each other over the network.
            Choose a proper IP address that is unique and valid
            in your network environment."
        ::= { networkSetting 2 }
    
    ipv4NetMask OBJECT-TYPE
        SYNTAX IpAddress
        MAX-ACCESS read-write                
        STATUS current
        DESCRIPTION
            "A subnet mask represents all of the network hosts
            at one geographic location, in one building, or on
            the same local area network. When a packet is sent
            out over the network, the NPort will use the subnet mask 
            to check whether the TCP/IP host specified in the 
            packet is on the local network segment. If the address 
            is on the same network segment as the NPort, a connection 
            is established directly from the NPort. Otherwise, the
            connection is established through the given default
            gateway."
        ::= { networkSetting 3 }
    
    ipv4DefaultGateway OBJECT-TYPE
        SYNTAX IpAddress
        MAX-ACCESS read-write                
        STATUS current
        DESCRIPTION
            "A gateway is a network computer that acts as an
            entrance to another network. Usually, the computers
            that control traffic within the network or at the
            local Internet service provider are gateway nodes.
            The NPort needs to know the IP address of the 
            default gateway computer in order to communicate with 
            the hosts outside the local network environment. 
            For correct gateway IP address information, 
            consult with the network administrator."
        ::= { networkSetting 4 }
    
    ipv4DnsServer1IpAddr OBJECT-TYPE
        SYNTAX IpAddress
        MAX-ACCESS read-write               
        STATUS current
        DESCRIPTION
            "The first DNS server address. When the user wants
            to visit a particular website, the computer asks a
            Domain Name System (DNS) server for the website’s
            correct IP address, and then the computer uses the
            response to connect to the web server. DNS is the
            way that Internet domain names are identified and
            translated into IP addresses. A domain name is an
            alphanumeric name, such as moxa.com, that it is
            usually easier to remember. A DNS server is a host
            that translates this kind of text-based domain name
            into the numeric IP address used to establish a
            TCP/IP connection."
        ::= { networkSetting 5 }
        
    ipv4DnsServer2IpAddr OBJECT-TYPE
        SYNTAX IpAddress
        MAX-ACCESS read-write               
        STATUS current
        DESCRIPTION
            "The second DNS server address. When the user wants
            to visit a particular website, the computer asks a
            Domain Name System (DNS) server for the website’s
            correct IP address, and then the computer uses the
            response to connect to the web server. DNS is the
            way that Internet domain names are identified and
            translated into IP addresses. A domain name is an
            alphanumeric name, such as moxa.com, that it is
            usually easier to remember. A DNS server is a host
            that translates this kind of text-based domain name
            into the numeric IP address used to establish a
            TCP/IP connection."
        ::= { networkSetting 6 }
    
    ipv4PppoeUserAccount OBJECT-TYPE
        SYNTAX DisplayString
        MAX-ACCESS read-write
        STATUS current
        DESCRIPTION
            "The user account used by the NPort to access
            the Internet using PPPoE. For dynamic broad band
            networks such as xDSL or Cable Modem, users must 
            enter the username and password that they
            received from their ISP to establish a network
            connection."
        ::= { networkSetting 7 }
    
    ipv4PppoePassword OBJECT-TYPE
        SYNTAX DisplayString
        MAX-ACCESS read-write
        STATUS current
        DESCRIPTION
            "The password used by the NPort to access the Internet
            using PPPoE. For dynamic broad band networks such as
            xDSL or Cable Modem, users must enter the
            username and password that they received from their
            ISP to establish a network connection."
        ::= { networkSetting 8 }
        
    ipv4WinsFunction OBJECT-TYPE
        SYNTAX INTEGER { disable(0), enable(1)}
        MAX-ACCESS read-write               
        STATUS current
        DESCRIPTION
            "Enable or disable the WINS server."
        ::= { networkSetting 9 }
    
    ipv4WinsServer OBJECT-TYPE
        SYNTAX IpAddress
        MAX-ACCESS read-write               
        STATUS current
        DESCRIPTION
            "If a WINS Server is connected to the network, use
            this field to record the WINS Server’s IP address.
            TCP/IP uses IP addresses to identify hosts, but
            users often use symbolic names, such as computer
            names. The WINS Server, which uses NetBIOS over
            TCP/IP, contains a dynamic database to map computer
            names to IP addresses."
        ::= { networkSetting 10 }
    
    lan1Speed OBJECT-TYPE
        SYNTAX INTEGER { 
        	auto-Negation(0), 
        	tenMbps-Half(1), 
        	tenMbps-Full(2), 
        	hundredMbps-Half(3), 
        	hundredMbps-Full(4)
        }
        MAX-ACCESS read-write               
        STATUS current
        DESCRIPTION
            "IEEE802.3 Ethernet supports the auto negotiation
            speed function to get suitable speeds. However, for
            connecting to some switches/hubs, the communication
            speed must be fixed at 100 Mbps or 10 Mbps. Users can
            use this function to fix the communication speed.
            Note: NPort 6250-S-SC, 6250-M-SC only accept setting
             as 'auto-Negation'."
        ::= { networkSetting 11 }
    
-- -------------------------------------------------------------
-- Network settings -> Advanced
-- -------------------------------------------------------------
        
    routingProtocol OBJECT-TYPE
        SYNTAX INTEGER { none(0), rip-1(1), rip-2(2)}
        MAX-ACCESS read-write               
        STATUS current
        DESCRIPTION
            "The routing protocol used by the NPort. This value
            could be none, RIP-1, or RIP-2."
        ::= { networkSetting 12 }
        
    gratuitousArp OBJECT-TYPE
        SYNTAX INTEGER { disable(0), enable(1)}
        MAX-ACCESS read-write               
        STATUS current
        DESCRIPTION
            "Enable or disable the gratuitous ARP function. For some
            applications, users need the NPort 6000 series
            device server to send broadcast packets to update
            the ARP table on the server. If the customer enables
            this function and sets the send period, the NPort
            6000 series device server will send broadcast
            packets periodically."
        ::= { networkSetting 13 }
        
    gratuitousArpSendPeriod  OBJECT-TYPE
        SYNTAX INTEGER
        MAX-ACCESS read-write               
        STATUS current
        DESCRIPTION
            "The send period of the gratuitous ARP function."
        ::= { networkSetting 14 }

    
-- -------------------------------------------------------------
-- Network settings -> Module
-- -------------------------------------------------------------
        
    moduleSetting OBJECT IDENTIFIER ::= { networkSetting 15 } 
        
-- -------------------------------------------------------------
-- Network settings -> Module -> Redundancy settings
-- -------------------------------------------------------------
        
    redundancySetting OBJECT IDENTIFIER ::= { moduleSetting 1 }

    redundancyProtocol OBJECT-TYPE
        SYNTAX INTEGER  { spanningTree(1), turboRing(2), turboRingV2(3) }
        MAX-ACCESS read-write
        STATUS current
        DESCRIPTION
        "This set the redundancy protocol.
        Note: NPort 6150, 6250, 6250-S-SC, 6250-M-SC 
        do not support write access."
        ::= { redundancySetting 1 }

    spanningTree OBJECT IDENTIFIER ::= { redundancySetting 2 }
    
    spanningTreeBridgePriority OBJECT-TYPE
        SYNTAX INTEGER {priority-0(0), priority-4096(4096), priority-8192(8192), priority-12288(12288),
                        priority-16384(16384), priority-20480(20480), priority-24576(24576),
                        priority-28672(28672), priority-32768(32768), priority-36864(36864),
                        priority-40960(40960), priority-45056(45056), priority-49152(49152),
                        priority-53248(53248), priority-57344(57344), priority-61440(61440)}
        MAX-ACCESS read-write               
        STATUS current
        DESCRIPTION
            "The bridge priority of spanning tree protocol.
        		Note: NPort 6150, 6250, 6250-S-SC, 6250-M-SC 
        		do not support write access."
        ::= { spanningTree 1 }

    spanningTreeHelloTime OBJECT-TYPE
        SYNTAX INTEGER  
        MAX-ACCESS read-write               
        STATUS current
        DESCRIPTION
            "The hello time of spanning tree protocol. Range is 1~10.
             A Bridge shall enforce the following relationships: 
				2 x (Forward Delay - 1) >= Max Age
				Max Age >= 2 x (Hello Time + 1).
        Note: NPort 6150, 6250, 6250-S-SC, 6250-M-SC 
        do not support write access."
        ::= { spanningTree 2 }
    
    spanningTreeForwardingDelay OBJECT-TYPE
        SYNTAX INTEGER  
        MAX-ACCESS read-write               
        STATUS current
        DESCRIPTION
            "The forwarding delay of spanning tree protocol. Range is 4~30.
             A Bridge shall enforce the following relationships: 
				2 x (Forward Delay - 1) >= Max Age
				Max Age >= 2 x (Hello Time + 1).
        Note: NPort 6150, 6250, 6250-S-SC, 6250-M-SC 
        do not support write access."
        ::= { spanningTree 3 }

    spanningTreeMaxAge OBJECT-TYPE
        SYNTAX INTEGER  
        MAX-ACCESS read-write               
        STATUS current
        DESCRIPTION
            "The max. age of spanning tree protocol. Range is 6~40.
             A Bridge shall enforce the following relationships: 
				2 x (Forward Delay - 1) >= Max Age
				Max Age >= 2 x (Hello Time + 1).
        Note: NPort 6150, 6250, 6250-S-SC, 6250-M-SC 
        do not support write access."
        ::= { spanningTree 4 }
    
    spanningTreePortTable OBJECT-TYPE
        SYNTAX SEQUENCE OF SpanningTreePortEntry
        MAX-ACCESS not-accessible               
        STATUS current
        DESCRIPTION
            "The spanning tree table."
        ::= { spanningTree 5 }
    
    spanningTreePortEntry OBJECT-TYPE
        SYNTAX SpanningTreePortEntry
        MAX-ACCESS not-accessible               
        STATUS current
        DESCRIPTION
            "The spanning tree port entry."
        INDEX { spanningTreePortIndex }
        ::= { spanningTreePortTable 1 }
        
    SpanningTreePortEntry ::=
        SEQUENCE {
            spanningTreePortIndex
                INTEGER,
            spanningTreePortEnable
                INTEGER,
            spanningTreePortPriority
                INTEGER,
            spanningTreePortCost
                INTEGER
        }
    spanningTreePortIndex OBJECT-TYPE
        SYNTAX INTEGER 
        MAX-ACCESS read-only                
        STATUS current
        DESCRIPTION
            "The index of spanning tree table."
        ::= { spanningTreePortEntry 1 }

    spanningTreePortEnable OBJECT-TYPE
        SYNTAX INTEGER { disable(0), enable(1) }
        MAX-ACCESS read-write               
        STATUS current
        DESCRIPTION
            "This enable of spanning tree protocol for this port.
            Note: NPort 6150, 6250, 6250-S-SC, 6250-M-SC 
            do not support write access."
        ::= { spanningTreePortEntry 2 }
    
    spanningTreePortPriority OBJECT-TYPE
        SYNTAX INTEGER {priority-0(0), priority-16(16), priority-32(32), priority-48(48),
                        priority-64(64), priority-80(80), priority-96(96), priority-112(112),
                        priority-128(128), priority-144(144), priority-160(160), priority-176(176),
                        priority-192(192), priority-208(208), priority-224(224), priority-240(240)}
        MAX-ACCESS read-write               
        STATUS current
        DESCRIPTION
            "The port priority of spanning tree protocol.
            Note: NPort 6150, 6250, 6250-S-SC, 6250-M-SC 
            do not support write access."
        ::= { spanningTreePortEntry 3 }
    
    spanningTreePortCost OBJECT-TYPE
        SYNTAX INTEGER 
        MAX-ACCESS read-write               
        STATUS current
        DESCRIPTION
            "The port cost of spanning tree protocol. Range is 1~20000000.
            Note: NPort 6150, 6250, 6250-S-SC, 6250-M-SC 
            do not support write access."
        ::= { spanningTreePortEntry 4 }

    turboRing OBJECT IDENTIFIER ::= { redundancySetting 3}
        
    turboRingMasterSetup OBJECT-TYPE
        SYNTAX INTEGER  { no(0), yes(1) }
        MAX-ACCESS read-write               
        STATUS current
        DESCRIPTION
            "Set this to be Master.
            Note: NPort 6150, 6250, 6250-S-SC, 6250-M-SC 
            do not support write access."
        ::= { turboRing 1 }
        
    turboRingRdntPort1 OBJECT-TYPE
        SYNTAX  INTEGER
        ACCESS  read-write
        STATUS  current
        DESCRIPTION
            "The port number of 1st Redundant Port on the TURBO RING.
            Note: NPort 6150, 6250, 6250-S-SC, 6250-M-SC 
            do not support write access."
        ::= { turboRing 2 } 
        
    turboRingRdntPort2 OBJECT-TYPE
        SYNTAX  INTEGER
        ACCESS  read-write
        STATUS  current
        DESCRIPTION
            "The port number of 2nd Redundant Port on the TURBO RING.
            Note: NPort 6150, 6250, 6250-S-SC, 6250-M-SC 
            do not support write access."
        ::= { turboRing 3 } 

    turboRingV2 OBJECT IDENTIFIER ::= { redundancySetting 4}
        
    turboRingV2MasterSetup OBJECT-TYPE
        SYNTAX INTEGER  { no(0), yes(1) }
        MAX-ACCESS read-write               
        STATUS current
        DESCRIPTION
            "Set this to be Master.
            Note: NPort 6150, 6250, 6250-S-SC, 6250-M-SC 
            do not support write access."
        ::= { turboRingV2 1 }
        
    turboRingV2RdntPort1 OBJECT-TYPE
        SYNTAX  INTEGER
        ACCESS  read-write
        STATUS  current
        DESCRIPTION
            "The port number of 1st Redundant Port on the TURBO RING V2.
            Note: NPort 6150, 6250, 6250-S-SC, 6250-M-SC 
            do not support write access."
        ::= { turboRingV2 2 } 
        
    turboRingV2RdntPort2 OBJECT-TYPE
        SYNTAX  INTEGER
        ACCESS  read-write
        STATUS  current
        DESCRIPTION
            "The port number of 2nd Redundant Port on the TURBO RING V2.
            Note: NPort 6150, 6250, 6250-S-SC, 6250-M-SC 
            do not support write access."
        ::= { turboRingV2 3 } 

-- -------------------------------------------------------------
-- Network settings -> Module -> GSM/GPRS settings
-- -------------------------------------------------------------
        
    gsmGprsSetting OBJECT IDENTIFIER ::= { moduleSetting 2 }

    gsmGprsType OBJECT-TYPE
        SYNTAX INTEGER  { gsm(0), gprs(1), sms(2) }
        MAX-ACCESS read-write
        STATUS current
        DESCRIPTION
        "This set the GSM/GPRS type.
        Note: NPort 6150, 6250, 6250-S-SC, 6250-M-SC 
        do not support write access."
        ::= { gsmGprsSetting 1 }

    gsmGprsPIN OBJECT-TYPE
        SYNTAX DisplayString
        MAX-ACCESS read-write
        STATUS current
        DESCRIPTION
        "This set the PIN of SIM card.
        Note: NPort 6150, 6250, 6250-S-SC, 6250-M-SC 
        do not support write access."
        ::= { gsmGprsSetting 2 }

    gsmGprsBand OBJECT-TYPE
        SYNTAX INTEGER  { band-850-Mhz(0), band-900-Mhz(1), band-1800-Mhz(2), band-1900-Mhz(3), band-850-1900-Mhz(4), band-900-1800-Mhz(5), band-900-1900-Mhz(6)}
        MAX-ACCESS read-write
        STATUS current
        DESCRIPTION
        "This set the GSM band.
        Note: NPort 6150, 6250, 6250-S-SC, 6250-M-SC 
        do not support write access."
        ::= { gsmGprsSetting 3 }
    
-- -------------------------------------------------------------
-- Network settings -> Module -> GSM/GPRS settings -> gsm
-- -------------------------------------------------------------
        
    gsmSetting OBJECT IDENTIFIER ::= { gsmGprsSetting 4 }

    gsmMode OBJECT-TYPE
        SYNTAX INTEGER  { ppp(0), pppd(1) }
        MAX-ACCESS read-write
        STATUS current
        DESCRIPTION
        "This set the GSM mode.
        Note: NPort 6150, 6250, 6250-S-SC, 6250-M-SC 
        do not support write access."
        ::= { gsmSetting 1 }

	gsmDestinationIpAddress OBJECT-TYPE
		SYNTAX IpAddress
		MAX-ACCESS read-write                
		STATUS current
		DESCRIPTION
			"Destination IP address is the IP address of the
			remote dial-in/dial-out server.
        Note: NPort 6150, 6250, 6250-S-SC, 6250-M-SC 
        do not support write access."
		::= { gsmSetting 2 }    
		
	gsmSourceIpAddress OBJECT-TYPE
		SYNTAX IpAddress
		MAX-ACCESS read-write                
		STATUS current
		DESCRIPTION
			"Source IP address is IP address of this serial
			port. The NPort 6000 series device server will
			automatically assign an IP address for the port.
			We recommend leaving this field blank.
        Note: NPort 6150, 6250, 6250-S-SC, 6250-M-SC 
        do not support write access."
		::= { gsmSetting 3 }    
		
	gsmIpNetmask OBJECT-TYPE
		SYNTAX IpAddress
		MAX-ACCESS read-write                
		STATUS current
		DESCRIPTION
			"The IP netmask used for dial-in/dial-out networks.
        Note: NPort 6150, 6250, 6250-S-SC, 6250-M-SC 
        do not support write access."
		::= { gsmSetting 4 } 
		
	gsmTcpIpCompression OBJECT-TYPE
		SYNTAX INTEGER { disable(0), enable(1)}
		MAX-ACCESS read-write                
		STATUS current
		DESCRIPTION
			"Depends on whether the remote user's application
			requests compression.
        Note: NPort 6150, 6250, 6250-S-SC, 6250-M-SC 
        do not support write access."
		::= { gsmSetting 5 } 
	
	gsmInactivityTime OBJECT-TYPE
        SYNTAX INTEGER
        MAX-ACCESS read-write                
        STATUS current
        DESCRIPTION
            "0 ms: TCP connection will not be closed if the 
            serial line becomes idle.
            1-65535 ms: The NPort 6000 series device server
            automatically closes the TCP connection if there is
            no serial data activity for the given time. After
            the connection is closed, the NPort 6000 series
            device server starts listening for another
            TCP connection.
            Note: NPort 6150, 6250, 6250-S-SC, 6250-M-SC 
            do not support write access."
        ::= { gsmSetting 6 }
		
	gsmLinkQualityReport OBJECT-TYPE
		SYNTAX INTEGER { disable(0), enable(1)}
		MAX-ACCESS read-write                
		STATUS current
		DESCRIPTION
			"Choose YES if you are using software to collect Link quality
			information.
			Note: NPort 6150, 6250, 6250-S-SC, 6250-M-SC 
			do not support write access."
		::= { gsmSetting 7 } 
		
	gsmUsername OBJECT-TYPE
		SYNTAX DisplayString (SIZE(0..16))
		MAX-ACCESS read-write                
		STATUS current
		DESCRIPTION
			"Dial-out user name.
			Note: NPort 6150, 6250, 6250-S-SC, 6250-M-SC 
			do not support write access."
		::= { gsmSetting 8 }
		
	gsmPassword OBJECT-TYPE
		SYNTAX DisplayString (SIZE(0..16))
		MAX-ACCESS read-write                
		STATUS current
		DESCRIPTION
			"Dial-out user password.
			Note: NPort 6150, 6250, 6250-S-SC, 6250-M-SC 
			do not support write access."
		::= { gsmSetting 9 }
		
	gsmAuthenticationType OBJECT-TYPE
        SYNTAX INTEGER  { none(0), local(1), radius(2), radius-local(3), local-radius(4), tacacsPlus(5), tacacsPlus-local(6), local-tacacsPlus(7)}
        MAX-ACCESS read-write                
        STATUS current
        DESCRIPTION
            "Dial-in authentication type.
            Note: NPort 6150, 6250, 6250-S-SC, 6250-M-SC 
            do not support write access."
        ::= { gsmSetting 10 }
    
    gsmTryNextAuth OBJECT-TYPE
        SYNTAX INTEGER { disable(0), enable(1)}
        MAX-ACCESS read-write               
        STATUS current
        DESCRIPTION
            "Try next type on authentication denied or not.
            Note: NPort 6150, 6250, 6250-S-SC, 6250-M-SC 
            do not support write access."
		::= { gsmSetting 11 }    
        
	gsmOutPhoneNumber OBJECT-TYPE
		SYNTAX DisplayString (SIZE(0..20))
		MAX-ACCESS read-write                
		STATUS current
		DESCRIPTION
		"Set the number used to dial out.
		Note: NPort 6150, 6250, 6250-S-SC, 6250-M-SC 
		do not support write access."
		::= { gsmSetting 12 }

	gsmInitialString OBJECT-TYPE
		SYNTAX DisplayString (SIZE(0..24))
		MAX-ACCESS read-write                
		STATUS current
		DESCRIPTION
		"Set the modem's initial string to establish the
		connection. E.g., 'AT&S0=1' for auto-answer.
		Note: NPort 6150, 6250, 6250-S-SC, 6250-M-SC 
		do not support write access."
		::= { gsmSetting 13 }
		
	gsmConnectionControl OBJECT-TYPE
		SYNTAX INTEGER { alwaysOn-None(0), periodicallyConnect-InactivityTime(1), remoteHostFail-remoteHostRecovered(2) }
		MAX-ACCESS read-write                
		STATUS current
		DESCRIPTION
			"Set the connect/disconnect condition.
			Note: NPort 6150, 6250, 6250-S-SC, 6250-M-SC 
			do not support write access."
		::= { gsmSetting 14 } 
	
	gsmConnectionInterval OBJECT-TYPE
        SYNTAX INTEGER
        MAX-ACCESS read-write                
        STATUS current
        DESCRIPTION
            "Set the connection interval when connect condition is 'periodically connect'.
             Range is 5~65535 minutes.
             Note: NPort 6150, 6250, 6250-S-SC, 6250-M-SC 
             do not support write access."
        ::= { gsmSetting 15 }

	gsmPingRemoteHost OBJECT-TYPE
        SYNTAX DisplayString (SIZE(0..40))
        MAX-ACCESS read-write                
        STATUS current
        DESCRIPTION
            "Set the remote hostname when connect condition is 'remote host fail'.
            Note: NPort 6150, 6250, 6250-S-SC, 6250-M-SC 
            do not support write access."
        ::= { gsmSetting 16 }
        
    gsmInPhoneNumber OBJECT-TYPE
		SYNTAX DisplayString (SIZE(0..20))
		MAX-ACCESS read-write                
		STATUS current
		DESCRIPTION
		"Set the number allow to dial in.
		Note: NPort 6150, 6250, 6250-S-SC, 6250-M-SC 
		do not support write access."
		::= { gsmSetting 17 }

-- -------------------------------------------------------------
-- Network settings -> Module -> GSM/GPRS settings -> gprs
-- -------------------------------------------------------------
        
    gprsSetting OBJECT IDENTIFIER ::= { gsmGprsSetting 5 }
		
	gprsTcpIpCompression OBJECT-TYPE
		SYNTAX INTEGER { disable(0), enable(1)}
		MAX-ACCESS read-write                
		STATUS current
		DESCRIPTION
			"Depends on whether the remote user's application
			requests compression.
			Note: NPort 6150, 6250, 6250-S-SC, 6250-M-SC 
			do not support write access."
		::= { gprsSetting 1 } 
	
	gprsInactivityTime OBJECT-TYPE
        SYNTAX INTEGER
        MAX-ACCESS read-write                
        STATUS current
        DESCRIPTION
            "0 ms: TCP connection will not be closed if the 
            serial line becomes idle.
            1-65535 ms: The NPort 6000 series device server
            automatically closes the TCP connection if there is
            no serial data activity for the given time. After
            the connection is closed, the NPort 6000 series
            device server starts listening for another
            TCP connection.
            Note: NPort 6150, 6250, 6250-S-SC, 6250-M-SC 
            do not support write access."
        ::= { gprsSetting 2 }
		
	gprsLinkQualityReport OBJECT-TYPE
		SYNTAX INTEGER { disable(0), enable(1)}
		MAX-ACCESS read-write                
		STATUS current
		DESCRIPTION
			"Choose YES if you are using software to collect Link quality
			information.
			Note: NPort 6150, 6250, 6250-S-SC, 6250-M-SC 
			do not support write access."
		::= { gprsSetting 3 } 
		
	gprsInitialString OBJECT-TYPE
		SYNTAX DisplayString (SIZE(0..24))
		MAX-ACCESS read-write                
		STATUS current
		DESCRIPTION
		"Set the modem's initial string to establish the
		connection. E.g., 'AT&S0=1' for auto-answer.
		Note: NPort 6150, 6250, 6250-S-SC, 6250-M-SC 
		do not support write access."
		::= { gprsSetting 4 }

	gprsUsername OBJECT-TYPE
		SYNTAX DisplayString (SIZE(0..16))
		MAX-ACCESS read-write                
		STATUS current
		DESCRIPTION
			"Dial-out user name.
			Note: NPort 6150, 6250, 6250-S-SC, 6250-M-SC 
			do not support write access."
		::= { gprsSetting 5 }
		
	gprsPassword OBJECT-TYPE
		SYNTAX DisplayString (SIZE(0..16))
		MAX-ACCESS read-write                
		STATUS current
		DESCRIPTION
			"Dial-out user password.
			Note: NPort 6150, 6250, 6250-S-SC, 6250-M-SC 
			do not support write access."
		::= { gprsSetting 6 }

	gprsAPN OBJECT-TYPE
		SYNTAX DisplayString (SIZE(0..30))
		MAX-ACCESS read-write                
		STATUS current
		DESCRIPTION
		"Set GPRS APN.
		Note: NPort 6150, 6250, 6250-S-SC, 6250-M-SC 
		do not support write access."
		::= { gprsSetting 7 }
		
	gprsConnectionControl OBJECT-TYPE
		SYNTAX INTEGER { alwaysOn-None(0), periodicallyConnect-InactivityTime(1), remoteHostFail-remoteHostRecovered(2) }
		MAX-ACCESS read-write                
		STATUS current
		DESCRIPTION
			"Set the connect/disconnect condition.
			Note: NPort 6150, 6250, 6250-S-SC, 6250-M-SC 
			do not support write access."
		::= { gprsSetting 8 } 
	
	gprsConnectionInterval OBJECT-TYPE
        SYNTAX INTEGER
        MAX-ACCESS read-write                
        STATUS current
        DESCRIPTION
            "Set the connection interval when connect condition is 'periodically connect'.
             Range is 5~65535 minutes.
             Note: NPort 6150, 6250, 6250-S-SC, 6250-M-SC 
             do not support write access."
        ::= { gprsSetting 9 }

	gprsPingRemoteHost OBJECT-TYPE
        SYNTAX DisplayString (SIZE(0..40))
        MAX-ACCESS read-write                
        STATUS current
        DESCRIPTION
            "Set the remote hostname when connect condition is 'remote host fail'.
             Note: NPort 6150, 6250, 6250-S-SC, 6250-M-SC 
             do not support write access."
        ::= { gprsSetting 10 }

-- -------------------------------------------------------------
-- Network settings -> Module -> GSM/GPRS settings -> sms
-- -------------------------------------------------------------
        
    smsSetting OBJECT IDENTIFIER ::= { gsmGprsSetting 6 }
		
	smsFormat OBJECT-TYPE
		SYNTAX INTEGER { sms-Text-ASCII(0) }
		MAX-ACCESS read-write                
		STATUS current
		DESCRIPTION
			"Set SMS format.
			Note: NPort 6150, 6250, 6250-S-SC, 6250-M-SC 
			do not support write access."
		::= { smsSetting 1 } 

-- -------------------------------------------------------------
-- Network settings -> Module -> V.92 Modem settings
-- -------------------------------------------------------------
        
    v92ModemSetting OBJECT IDENTIFIER ::= { moduleSetting 3 }

    v92ModemMode OBJECT-TYPE
        SYNTAX INTEGER  { ppp(0), pppd(1) }
        MAX-ACCESS read-write
        STATUS current
        DESCRIPTION
        "This set the modem mode.
        Note: NPort 6150, 6250, 6250-S-SC, 6250-M-SC 
        do not support write access."
        ::= { v92ModemSetting 1 }

	v92ModemDestinationIpAddress OBJECT-TYPE
		SYNTAX IpAddress
		MAX-ACCESS read-write                
		STATUS current
		DESCRIPTION
			"Destination IP address is the IP address of the
			remote dial-in/dial-out server.
			Note: NPort 6150, 6250, 6250-S-SC, 6250-M-SC 
			do not support write access."
		::= { v92ModemSetting 2 }    
		
	v92ModemSourceIpAddress OBJECT-TYPE
		SYNTAX IpAddress
		MAX-ACCESS read-write                
		STATUS current
		DESCRIPTION
			"Source IP address is IP address of this serial
			port. The NPort 6000 series device server will
			automatically assign an IP address for the port.
			We recommend leaving this field blank.
			Note: NPort 6150, 6250, 6250-S-SC, 6250-M-SC 
			do not support write access."
		::= { v92ModemSetting 3 }    
		
	v92ModemIpNetmask OBJECT-TYPE
		SYNTAX IpAddress
		MAX-ACCESS read-write                
		STATUS current
		DESCRIPTION
			"The IP netmask used for dial-in/dial-out networks.
			Note: NPort 6150, 6250, 6250-S-SC, 6250-M-SC 
			do not support write access."
		::= { v92ModemSetting 4 } 
		
	v92ModemTcpIpCompression OBJECT-TYPE
		SYNTAX INTEGER { disable(0), enable(1)}
		MAX-ACCESS read-write                
		STATUS current
		DESCRIPTION
			"Depends on whether the remote user's application
			requests compression.
			Note: NPort 6150, 6250, 6250-S-SC, 6250-M-SC 
			do not support write access."
		::= { v92ModemSetting 5 } 
	
	v92ModemInactivityTime OBJECT-TYPE
        SYNTAX INTEGER
        MAX-ACCESS read-write                
        STATUS current
        DESCRIPTION
            "0 ms: TCP connection will not be closed if the 
            serial line becomes idle.
            1-65535 ms: The NPort 6000 series device server
            automatically closes the TCP connection if there is
            no serial data activity for the given time. After
            the connection is closed, the NPort 6000 series
            device server starts listening for another
            TCP connection.
            Note: NPort 6150, 6250, 6250-S-SC, 6250-M-SC 
            do not support write access."
        ::= { v92ModemSetting 6 }
		
	v92ModemLinkQualityReport OBJECT-TYPE
		SYNTAX INTEGER { disable(0), enable(1)}
		MAX-ACCESS read-write                
		STATUS current
		DESCRIPTION
			"Choose YES if you are using software to collect Link quality
			information.
			Note: NPort 6150, 6250, 6250-S-SC, 6250-M-SC 
			do not support write access."
		::= { v92ModemSetting 7 } 
		
	v92ModemUsername OBJECT-TYPE
		SYNTAX DisplayString (SIZE(0..16))
		MAX-ACCESS read-write                
		STATUS current
		DESCRIPTION
			"Dial-out user ID account.
			Note: NPort 6150, 6250, 6250-S-SC, 6250-M-SC 
			do not support write access."
		::= { v92ModemSetting 8 }
		
	v92ModemPassword OBJECT-TYPE
		SYNTAX DisplayString (SIZE(0..16))
		MAX-ACCESS read-write                
		STATUS current
		DESCRIPTION
			"Dial-out user password.
			Note: NPort 6150, 6250, 6250-S-SC, 6250-M-SC 
			do not support write access."
		::= { v92ModemSetting 9 }
		
	v92ModemIncomingPAPCheck OBJECT-TYPE
        SYNTAX INTEGER  { none(0), local(1), radius(2), radius-local(3), local-radius(4), tacacsPlus(5), tacacsPlus-local(6), local-tacacsPlus(7)}
        MAX-ACCESS read-write                
        STATUS current
        DESCRIPTION
            "The Dial in/out incoming PAP check type.
            Note: NPort 6150, 6250, 6250-S-SC, 6250-M-SC 
            do not support write access."
        ::= { v92ModemSetting 10 }
    
    v92ModemIncomingTryNextAuth OBJECT-TYPE
        SYNTAX INTEGER { disable(0), enable(1)}
        MAX-ACCESS read-write               
        STATUS current
        DESCRIPTION
            "Try next type on authentication denied or not.
            Note: NPort 6150, 6250, 6250-S-SC, 6250-M-SC 
            do not support write access."
		::= { v92ModemSetting 11 }    
        
	v92ModemPhoneNumber OBJECT-TYPE
		SYNTAX DisplayString (SIZE(0..20))
		MAX-ACCESS read-write                
		STATUS current
		DESCRIPTION
		"Set the number used to dial out.
		Note: NPort 6150, 6250, 6250-S-SC, 6250-M-SC 
		do not support write access."
		::= { v92ModemSetting 12 }

	v92ModemInitialString OBJECT-TYPE
		SYNTAX DisplayString (SIZE(0..24))
		MAX-ACCESS read-write                
		STATUS current
		DESCRIPTION
		"Set the modem's initial string to establish the
		connection. E.g., 'AT&S0=1' for auto-answer.
		Note: NPort 6150, 6250, 6250-S-SC, 6250-M-SC 
		do not support write access."
		::= { v92ModemSetting 13 }
		
	v92ModemConnectionControl OBJECT-TYPE
		SYNTAX INTEGER { alwaysOn-None(0), periodicallyConnect-InactivityTime(1), remoteHostFail-remoteHostRecovered(2) }
		MAX-ACCESS read-write                
		STATUS current
		DESCRIPTION
			"Set the connect/disconnect condition.
			Note: NPort 6150, 6250, 6250-S-SC, 6250-M-SC 
			do not support write access."
		::= { v92ModemSetting 14 } 
	
	v92ModemConnectionInterval OBJECT-TYPE
        SYNTAX INTEGER
        MAX-ACCESS read-write                
        STATUS current
        DESCRIPTION
            "Set the connection interval when connect condition is 'periodically connect'.
             Range is 5~65535 minutes.
             Note: NPort 6150, 6250, 6250-S-SC, 6250-M-SC 
             do not support write access."
        ::= { v92ModemSetting 15 }

	v92ModemPingRemoteHost OBJECT-TYPE
        SYNTAX DisplayString (SIZE(0..40))
        MAX-ACCESS read-write                
        STATUS current
        DESCRIPTION
            "Set the remote hostname when connect condition is 'remote host fail'.
             Note: NPort 6150, 6250, 6250-S-SC, 6250-M-SC 
             do not support write access."
        ::= { v92ModemSetting 16 }

    ipv6Configuration OBJECT-TYPE
        SYNTAX INTEGER { auto(0), static(1), disable(2)}
        MAX-ACCESS read-write               
        STATUS current
        DESCRIPTION
            "The IPv6 configuration mode of the NPort. You can
            choose from four possible IP configuration modes:
            Auto, DHCPv6, Static, Disable."
        ::= { networkSetting 16 }
    
    ipv6Address OBJECT-TYPE
        SYNTAX DisplayString (SIZE(0..16))
        MAX-ACCESS read-write                
        STATUS current
        DESCRIPTION
            "An IPv6 address is a number assigned to a network
            device (such as a computer) as a permanent address
            on the network. Computers use the IP address to
            identify and talk to each other over the network.
            Choose a proper IP address that is unique and valid
            in your network environment."
        ::= { networkSetting 17 }
    
    ipv6Prefix OBJECT-TYPE
        SYNTAX INTEGER
        MAX-ACCESS read-write                
        STATUS current
        DESCRIPTION
            "A prefix represents all of the network hosts
            at one geographic location, in one building, or on
            the same local area network. When a packet is sent
            out over the network, the NPort will use the prefix 
            to check whether the TCP/IP host specified in the 
            packet is on the local network segment. If the address 
            is on the same network segment as the NPort, a connection 
            is established directly from the NPort. Otherwise, the
            connection is established through the given default
            gateway. Range is 1~128"
        ::= { networkSetting 18 }
    
    ipv6DefaultGateway OBJECT-TYPE
        SYNTAX DisplayString (SIZE(0..16))
        MAX-ACCESS read-write                
        STATUS current
        DESCRIPTION
            "A gateway is a network computer that acts as an
            entrance to another network. Usually, the computers
            that control traffic within the network or at the
            local Internet service provider are gateway nodes.
            The NPort needs to know the IP address of the 
            default gateway computer in order to communicate with 
            the hosts outside the local network environment. 
            For correct gateway IP address information, 
            consult with the network administrator."
        ::= { networkSetting 19 }
    
    ipv6DnsServer1IpAddr OBJECT-TYPE
        SYNTAX DisplayString (SIZE(0..16))
        MAX-ACCESS read-write               
        STATUS current
        DESCRIPTION
            "The first DNS server address. When the user wants
            to visit a particular website, the computer asks a
            Domain Name System (DNS) server for the website’s
            correct IP address, and then the computer uses the
            response to connect to the web server. DNS is the
            way that Internet domain names are identified and
            translated into IP addresses. A domain name is an
            alphanumeric name, such as moxa.com, that it is
            usually easier to remember. A DNS server is a host
            that translates this kind of text-based domain name
            into the numeric IP address used to establish a
            TCP/IP connection."
        ::= { networkSetting 20 }
        
    ipv6DnsServer2IpAddr OBJECT-TYPE
        SYNTAX DisplayString (SIZE(0..16))
        MAX-ACCESS read-write               
        STATUS current
        DESCRIPTION
            "The second DNS server address. When the user wants
            to visit a particular website, the computer asks a
            Domain Name System (DNS) server for the website’s
            correct IP address, and then the computer uses the
            response to connect to the web server. DNS is the
            way that Internet domain names are identified and
            translated into IP addresses. A domain name is an
            alphanumeric name, such as moxa.com, that it is
            usually easier to remember. A DNS server is a host
            that translates this kind of text-based domain name
            into the numeric IP address used to establish a
            TCP/IP connection."
        ::= { networkSetting 21 }
    
    connectionPriority OBJECT-TYPE
        SYNTAX INTEGER { ipv6-first(0), ipv4-first(1)}
        MAX-ACCESS read-write               
        STATUS current
        DESCRIPTION
            "This value determines which DNS record are used 
            in first priority."
        ::= { networkSetting 22 }

-- -------------------------------------------------------------
-- Serial port settings
-- -------------------------------------------------------------

    portSetting OBJECT IDENTIFIER ::= { swMgmt 4 }			-- 1.3.6.1.4.1.8691.2.8.1.2.4
    
-- -------------------------------------------------------------
-- Serial port settings -> Operation Modes settings
-- -------------------------------------------------------------

	opModeSetting OBJECT IDENTIFIER ::= { portSetting 1 }	-- 1.3.6.1.4.1.8691.2.8.1.2.4.1
	
-- --------------------------------------------------------------------------------------
-- Serial port settings -> Operation Modes settings -> Operation Modes
-- --------------------------------------------------------------------------------------

	opMode OBJECT IDENTIFIER ::= { opModeSetting 1 }		-- 1.3.6.1.4.1.8691.2.8.1.2.4.1.1
	
	opModePortTable OBJECT-TYPE
        SYNTAX SEQUENCE OF OpModePortEntry
        MAX-ACCESS not-accessible               
        STATUS current
        DESCRIPTION
            "The serial ports' operation mode table."
        ::= { opMode 1 }
    
    opModePortEntry OBJECT-TYPE
        SYNTAX OpModePortEntry
        MAX-ACCESS not-accessible               
        STATUS current
        DESCRIPTION
            "The serial port's operation mode entry."
        INDEX { portIndex }
        ::= { opModePortTable 1 }
        
    OpModePortEntry ::=
        SEQUENCE {
        	portIndex
        		INTEGER,
            portApplication
                INTEGER,
            portMode
            	INTEGER
        }
        
    portIndex OBJECT-TYPE
        SYNTAX INTEGER
        MAX-ACCESS read-only                
        STATUS current
        DESCRIPTION
            "The serial port index."
        ::= { opModePortEntry 1 }
        
	portApplication OBJECT-TYPE
        SYNTAX INTEGER { 
        	disable(0), 
        	device-Control(4), 
			socket(11),
			pair-Connection(13),
			ethernet-Modem(12),
			terminal(2),
			reverse-Terminal(3),
			printer(6),				       	
			dial-InOut(1)
        }
        MAX-ACCESS read-write                
        STATUS current
        DESCRIPTION
            "The application of the serial port.
            Note that changing this setting may also change the
            operation mode."
        ::= { opModePortEntry 2 }
    
    portMode OBJECT-TYPE
        SYNTAX INTEGER { 
        	pair-Slave(0), 
        	pair-Master(1), 
        	real-Com(2), 
        	raw-PRN(3),
			slip(4), 
			slipd(5), 
			ppp(6), 
			disable(7),
			reverse-Telnet(8), 
			dynamic(9), 
			tcp-Server(10), 
			lpd-PRN(11),	
			ethernet-Modem(12), 
			tcp-Client(13), 
			udp(14), 
			pppd(15), 
			term-ASC(16), 
			term-BIN(17), 
			reverse-SSH(18), 
			ssh(19), 
			rfc-2217(20),
			reverse-Real-Com(21)
        }
        MAX-ACCESS read-write                
        STATUS current
        DESCRIPTION
            "The operation mode of the serial port. Note that
            changing this setting may also change the application."
        ::= { opModePortEntry 3 }
        
        
-- --------------------------------------------------------------------------------------
-- Serial port settings -> Operation Modes settings -> Application
-- --------------------------------------------------------------------------------------

	application OBJECT IDENTIFIER ::= { opModeSetting 2 }
	
-- --------------------------------------------------------------------------------------
-- Serial port settings -> Operation Modes settings -> Application -> Device Control
-- --------------------------------------------------------------------------------------

	deviceControl OBJECT IDENTIFIER ::= { application 1 }
	
	deviceControlTable OBJECT-TYPE
        SYNTAX SEQUENCE OF DeviceControlEntry
        MAX-ACCESS not-accessible               
        STATUS current
        DESCRIPTION
            "The Device Control application table."
        ::= { deviceControl 1 }
    
    deviceControlEntry OBJECT-TYPE
        SYNTAX DeviceControlEntry
        MAX-ACCESS not-accessible               
        STATUS current
        DESCRIPTION
            "The Device Control application entry."
        INDEX { portIndex }
        ::= { deviceControlTable 1 }
        
    DeviceControlEntry ::=
        SEQUENCE {
        	deviceControlTcpAliveCheck
            	INTEGER,
            deviceControlMaxConnection
            	INTEGER,
            deviceControlIgnoreJammedIp
            	INTEGER,
            deviceControlAllowDriverControl
            	INTEGER,
            deviceControlCommandByCommandOperation
            	INTEGER,	
            deviceControlSecure
            	INTEGER,
            deviceControlConnectionDownRTS
            	INTEGER,
            deviceControlConnectionDownDTR
            	INTEGER,
            deviceControlResponseTimeout
            	INTEGER,
            deviceControlNonRequestSerialData
            	INTEGER,
            deviceControlTcpPort
            	INTEGER,
            deviceControlDestinationAddress1
            	DisplayString,
            deviceControlDestinationTcpPort1
            	INTEGER,
            deviceControlDestinationCmdPort1
            	INTEGER,
            deviceControlDestinationAddress2
            	DisplayString,
            deviceControlDestinationTcpPort2
            	INTEGER,
            deviceControlDestinationCmdPort2
            	INTEGER,
            deviceControlDesignatedLocalTcpPort1
            	INTEGER,
            deviceControlDesignatedLocalCmdPort1
            	INTEGER,
            deviceControlDesignatedLocalTcpPort2
            	INTEGER,
            deviceControlDesignatedLocalCmdPort2
            	INTEGER
        }
	
	deviceControlTcpAliveCheck OBJECT-TYPE
        SYNTAX INTEGER
        MAX-ACCESS read-write                
        STATUS current
        DESCRIPTION
            "The TCP alive check time.
            0 min: TCP connection will not be closed when the
            TCP connection is idle.
            1 to 99 min: The NPort 6000 series device server
            automatically closes the TCP connection if there is
            no TCP activity for the given time. After the
            connection is closed, the NPort 6000 series device
            server starts listening for another Real COM driver
            Connection."
        ::= { deviceControlEntry 1 }
        
    deviceControlMaxConnection OBJECT-TYPE
        SYNTAX INTEGER
        MAX-ACCESS read-write                
        STATUS current
        DESCRIPTION
            "Max connection is usually used when the user needs
            to receive data from different hosts simultaneously.
            The factory default is 1. In this case, only one
            specific host can access this port of the NPort 6000
            series device server, and the Real COM driver on that
            host will have full control over the port.
            Max. connection = 1:
            Allows only a single host’s Real COM driver to open
            the specific NPort 6000 series device server’s
            serial port.
            Max connection = 2 to 8:
            Allows 2 to 8 hosts’ Real COM drivers to open the
            specific NPort 6000 series device server’s serial
            port, at the same time. When multiple hosts’ Real
            COM drivers open the serial port at the same time,
            the COM driver only provides a pure data tunnel
            without control ability. The serial port parameter
            will use the firmware settings instead of getting
            the settings from your application program (AP)."
        ::= { deviceControlEntry 2 }
        
    deviceControlIgnoreJammedIp OBJECT-TYPE
        SYNTAX INTEGER { disable(0), enable(1) }
        MAX-ACCESS read-write                
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { deviceControlEntry 3 }
        
    deviceControlAllowDriverControl OBJECT-TYPE
        SYNTAX INTEGER { disable(0), enable(1) }
        MAX-ACCESS read-write                
        STATUS current
        DESCRIPTION
            "If Max connection is greater than 1, NPort will
            ignore driver control commands from all connected
            hosts. However, if you set Allow driver control to
            YES, control commands will be accepted. Note that
            since the NPort 6000 series device server may get
            configuration changes from multiple hosts, the most
            recent command received will take precedence."
        ::= { deviceControlEntry 4 }
    
    deviceControlCommandByCommandOperation OBJECT-TYPE
        SYNTAX INTEGER { disable(0), enable(1) }
        MAX-ACCESS read-write                
        STATUS current
        DESCRIPTION
            "Commands will be sent from the NPort to the 
            serial device. After each command, the NPort will wait to 
            receive a response before sending the next command."
        ::= { deviceControlEntry 5 }     
        
	deviceControlSecure OBJECT-TYPE
        SYNTAX INTEGER { disable(0), enable(1) }
        MAX-ACCESS read-write                
        STATUS current
        DESCRIPTION
            "If 'Secure' is enabled, the data on the Ethernet
            will be encrypted with SSL."
        ::= { deviceControlEntry 6 }
        
	deviceControlConnectionDownRTS OBJECT-TYPE
        SYNTAX INTEGER { always-low(1), always-high(0) }
        MAX-ACCESS read-write                
        STATUS current
        DESCRIPTION
            "For some applications, serial devices must obtain
            the Ethernet link status by reading the RTS signal from the
            NPort 6000 series device server. If this setting is
            set to 'always low,' RTS will change its state to
            low if the Ethernet link is off."
        ::= { deviceControlEntry 7 }
        
    deviceControlConnectionDownDTR OBJECT-TYPE
        SYNTAX INTEGER { always-low(1), always-high(0) }
        MAX-ACCESS read-write                
        STATUS current
        DESCRIPTION
            "For some applications, serial devices must obtain
            the Ethernet link status by reading the DTR signal from the
            NPort 6000 series device server. If this setting is
            set to 'goes low,' DTR will change its state to
            low if the Ethernet link is off."
        ::= { deviceControlEntry 8 }
	
	deviceControlResponseTimeout OBJECT-TYPE
        SYNTAX INTEGER
        MAX-ACCESS read-write                
        STATUS current
        DESCRIPTION
            "After sending a command to the serial device, the NPort 
            will wait for a response. If no response is received from 
            the serial device within the specified time, the NPort will 
            give up and continue to the next command."
        ::= { deviceControlEntry 9 }    
    
    deviceControlNonRequestSerialData OBJECT-TYPE
        SYNTAX INTEGER { discard(0), forward-to-last-requester(1), forward-to-all-open-connections(2) }
        MAX-ACCESS read-write                
        STATUS current
        DESCRIPTION
            "This specifies how the NPort will handle data that is 
            received from a serial device that is not a response to 
            a command. The NPort can either discard such data, forward 
            the data to the network host that sent the most recent request, 
            or forward the data to all open host connections."
        ::= { deviceControlEntry 10 }
    
    deviceControlTcpPort OBJECT-TYPE
        SYNTAX INTEGER
        MAX-ACCESS read-write                
        STATUS current
        DESCRIPTION
            "The 'TCP port' is the TCP port that the NPort
            6000 series device server uses to listen to
            connections, and that other devices must use to
            contact the NPort 6000 series device server.
            This setting is used in RFC2217 mode."
        ::= { deviceControlEntry 11 }
     
	deviceControlDestinationAddress1 OBJECT-TYPE
		SYNTAX DisplayString (SIZE(0..40))
		MAX-ACCESS read-write                
		STATUS current
		DESCRIPTION
			"The NPort 6000 series device server can connect actively 
			to a remote host that has this IP address.
			This setting is used in Reverse RealCOM mode."
		::= { deviceControlEntry 12 }
            	
	deviceControlDestinationTcpPort1 OBJECT-TYPE
		SYNTAX INTEGER
		MAX-ACCESS read-write                
		STATUS current
		DESCRIPTION
			"The NPort 6000 series device server can connect actively 
			to a remote host that has this TCP data port number.
			This setting is used in Reverse RealCOM mode."
		::= { deviceControlEntry 13 }
            	
	deviceControlDestinationCmdPort1 OBJECT-TYPE
		SYNTAX INTEGER
		MAX-ACCESS read-write                
		STATUS current
		DESCRIPTION
			"The NPort 6000 series device server can connect actively 
			to a remote host that has this TCP command port number.
			This setting is used in Reverse RealCOM mode."
		::= { deviceControlEntry 14 }
    
	deviceControlDestinationAddress2 OBJECT-TYPE
		SYNTAX DisplayString (SIZE(0..40))
		MAX-ACCESS read-write                
		STATUS current
		DESCRIPTION
			"The NPort 6000 series device server can connect actively 
			to a remote host that has this IP address.
			This setting is used in Reverse RealCOM mode."
		::= { deviceControlEntry 15 }
    
	deviceControlDestinationTcpPort2 OBJECT-TYPE
		SYNTAX INTEGER
		MAX-ACCESS read-write                
		STATUS current
		DESCRIPTION
			"The NPort 6000 series device server can connect actively 
			to a remote host that has this TCP data port number.
			This setting is used in Reverse RealCOM mode."
		::= { deviceControlEntry 16 }
            	
	deviceControlDestinationCmdPort2 OBJECT-TYPE
		SYNTAX INTEGER
		MAX-ACCESS read-write                
		STATUS current
		DESCRIPTION
			"The NPort 6000 series device server can connect actively 
			to a remote host that has this TCP command port number.
			This setting is used in Reverse RealCOM mode."
		::= { deviceControlEntry 17 }
    
	deviceControlDesignatedLocalTcpPort1 OBJECT-TYPE
		SYNTAX INTEGER
		MAX-ACCESS read-write
		STATUS current
		DESCRIPTION
			"The local TCP data port used to connect actively to the
			remote host. This setting is used in Reverse RealCOM mode."
		::= { deviceControlEntry 18 }
    
	deviceControlDesignatedLocalCmdPort1 OBJECT-TYPE
		SYNTAX INTEGER
		MAX-ACCESS read-write
		STATUS current
		DESCRIPTION
			"The local TCP command port used to connect actively to the
			remote host. This setting is used in Reverse RealCOM mode."
		::= { deviceControlEntry 19 }
            	
	deviceControlDesignatedLocalTcpPort2 OBJECT-TYPE
		SYNTAX INTEGER
		MAX-ACCESS read-write
		STATUS current
		DESCRIPTION
			"The local TCP data port used to connect actively to the
			remote host. This setting is used in Reverse RealCOM mode."
		::= { deviceControlEntry 20 }
            	
	deviceControlDesignatedLocalCmdPort2 OBJECT-TYPE
		SYNTAX INTEGER
		MAX-ACCESS read-write
		STATUS current
		DESCRIPTION
			"The local TCP command port used to connect actively to the
			remote host. This setting is used in Reverse RealCOM mode."
		::= { deviceControlEntry 21 }
            	
-- --------------------------------------------------------------------------------------
-- Serial port settings -> Operation Modes settings -> Application -> Socket
-- --------------------------------------------------------------------------------------

	socket OBJECT IDENTIFIER ::= { application 2 }
	
	socketTable OBJECT-TYPE
        SYNTAX SEQUENCE OF SocketEntry
        MAX-ACCESS not-accessible               
        STATUS current
        DESCRIPTION
            "The Socket application table."
        ::= { socket 1 }
    
    socketEntry OBJECT-TYPE
        SYNTAX SocketEntry
        MAX-ACCESS not-accessible               
        STATUS current
        DESCRIPTION
            "The Socket application entry."
        INDEX { portIndex }
        ::= { socketTable 1 }
        
    SocketEntry ::=
        SEQUENCE {
        	socketTcpAliveCheck
            	INTEGER,
            socketInactivityTime
            	INTEGER,
            socketMaxConnection
            	INTEGER,
            socketIgnoreJammedIp
            	INTEGER,
            socketAllowDriverControl
            	INTEGER,
            socketCommandByCommandOperation
            	INTEGER,
            socketSecure
            	INTEGER,
            socketTcpPort
            	INTEGER,
            socketCmdPort
            	INTEGER,
            socketTcpServerConnectionDownRTS
            	INTEGER,
            socketTcpServerConnectionDownDTR
            	INTEGER,
            socketResponseTimeout
            	INTEGER,
            socketNonRequestSerialData
            	INTEGER,		
            socketTcpClientDestinationAddress1
                DisplayString,
            socketTcpClientDestinationPort1
                INTEGER,
            socketTcpClientDestinationAddress2
                DisplayString,
            socketTcpClientDestinationPort2
            	INTEGER,
            socketTcpClientDestinationAddress3
                DisplayString,
            socketTcpClientDestinationPort3
            	INTEGER,
            socketTcpClientDestinationAddress4
                DisplayString,
            socketTcpClientDestinationPort4
            	INTEGER,
            socketTcpClientDesignatedLocalPort1
            	INTEGER,
            socketTcpClientDesignatedLocalPort2
            	INTEGER,
            socketTcpClientDesignatedLocalPort3
            	INTEGER,
            socketTcpClientDesignatedLocalPort4
            	INTEGER,
            socketTcpClientConnectionControl
            	INTEGER,
            socketUdpDestinationAddress1Begin
            	DisplayString,
            socketUdpDestinationAddress1End
            	DisplayString,
            socketUdpDestinationPort1
            	INTEGER,
            socketUdpDestinationAddress2Begin
            	DisplayString,
            socketUdpDestinationAddress2End
            	DisplayString,
            socketUdpDestinationPort2
            	INTEGER,
            socketUdpDestinationAddress3Begin
            	DisplayString,
            socketUdpDestinationAddress3End
            	DisplayString,
            socketUdpDestinationPort3
            	INTEGER,
            socketUdpDestinationAddress4Begin
            	DisplayString,
            socketUdpDestinationAddress4End
            	DisplayString,
            socketUdpDestinationPort4
            	INTEGER,
            socketUdpLocalListenPort
            	INTEGER,
	    socketUDPDynamicDst
            	INTEGER,
	    socketUDPDynamicDstTimeout
            	INTEGER
        }
        
	socketTcpAliveCheck OBJECT-TYPE
        SYNTAX INTEGER
        MAX-ACCESS read-write                
        STATUS current
        DESCRIPTION
            "The TCP alive check time.
            0 min: TCP connection will not be closed when the
            TCP connection is idle.
            1 to 99 min: The NPort 6000 series device server
            automatically closes the TCP connection if there is
            no TCP activity for the given time. After the
            connection is closed, the NPort 6000 series device
            server starts listening for another Real COM driver
            Connection."
        ::= { socketEntry 1 }
        
    socketInactivityTime OBJECT-TYPE
        SYNTAX INTEGER
        MAX-ACCESS read-write                
        STATUS current
        DESCRIPTION
            "0 ms: TCP connection is not closed when the
            serial line is idle.
            1-65535 ms: The NPort 6000 series device server
            automatically closes the TCP connection if there is
            no serial data activity for the given time. After
            the connection is closed, the NPort 6000 series
            device server starts listening for another
            TCP connection."
        ::= { socketEntry 2 }
        
    socketMaxConnection OBJECT-TYPE
        SYNTAX INTEGER
        MAX-ACCESS read-write                
        STATUS current
        DESCRIPTION
            "Max connection is usually used when the user needs
            to receive data from different hosts simultaneously.
            The factory default is 1. In this case, only one
            specific host can access this port of the NPort 6000
            series device server, and the Real COM driver on that
            host will have full control over the port.
            Max. connection 1:
            Allows only a single host’s Real COM driver to open
            the specific NPort 6000 series device server’s
            serial port.
            Max connection 2 to 8:
            Allows 2 to 8 hosts’ Real COM drivers to open the
            specific NPort 6000 series device server’s serial
            port, at the same time. When multiple hosts’ Real
            COM drivers open the serial port at the same time,
            the COM driver only provides a pure data tunnel
            without control ability. The serial port parameter
            will use the firmware settings instead of depending
            on your application program (AP)."
        ::= { socketEntry 3 }
        
    socketIgnoreJammedIp OBJECT-TYPE
        SYNTAX INTEGER { disable(0), enable(1) }
        MAX-ACCESS read-write                
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { socketEntry 4 }
        
    socketAllowDriverControl OBJECT-TYPE
        SYNTAX INTEGER { disable(0), enable(1) }
        MAX-ACCESS read-write                
        STATUS current
        DESCRIPTION
            "If Max connection is greater than 1, NPort will
            ignore driver control commands from all connected
            hosts. However, if you set Allow driver control to
            YES, control commands will be accepted. Note that
            since the NPort 6000 series device server may get
            configuration changes from multiple hosts, the most
            recent command received will take precedence."
        ::= { socketEntry 5 }

	socketCommandByCommandOperation OBJECT-TYPE
        SYNTAX INTEGER { disable(0), enable(1) }
        MAX-ACCESS read-write                
        STATUS current
        DESCRIPTION
            "Commands will be sent from the NPort to the 
            serial device. After each command, the NPort will wait to 
            receive a response before sending the next command."
        ::= { socketEntry 6 }
	
	socketSecure OBJECT-TYPE
        SYNTAX INTEGER { disable(0), enable(1) }
        MAX-ACCESS read-write                
        STATUS current
        DESCRIPTION
            "If Secure is enabled, data sent over the Ethernet will be
            encrypted with SSL."
        ::= { socketEntry 7 }
        
    socketTcpPort OBJECT-TYPE
        SYNTAX INTEGER
        MAX-ACCESS read-write                
        STATUS current
        DESCRIPTION
            "The 'TCP port' is the TCP port that the NPort
            6000 series device server uses to listen to
            connections, and that other devices must use to
            contact the NPort 6000 series device server."
        ::= { socketEntry 8 }
        
    socketCmdPort OBJECT-TYPE
        SYNTAX INTEGER
        MAX-ACCESS read-write                
        STATUS current
        DESCRIPTION
            "The 'Command port' is a TCP port used to listen for 
            IP-Serial Lib commands from the host. In order to
            prevent a TCP port conflict with other applications,
            the user can set the Command port to another port
            if needed. IP-Serial Lib will automatically check
            the Command Port on the NPort 6000 series device
            server to avoid the need for the user to configure
            the program."
        ::= { socketEntry 9 }
	
    socketTcpServerConnectionDownRTS OBJECT-TYPE
        SYNTAX INTEGER { always-low(1), always-high(0) }
        MAX-ACCESS read-write                
        STATUS current
        DESCRIPTION
            "For some applications, serial devices must obtain
            the Ethernet link status from the RTS signal sent by the
            NPort 6000 series device server. If this setting is
            set to 'goes low,' RTS will change the state to
            low if the Ethernet link is off."
        ::= { socketEntry 10 }
        
    socketTcpServerConnectionDownDTR OBJECT-TYPE
        SYNTAX INTEGER { always-low(1), always-high(0) }
        MAX-ACCESS read-write                
        STATUS current
        DESCRIPTION
            "For some applications, serial devices must obtain
            the Ethernet link status from the DTR signal sent by the
            NPort 6000 series device server. If this setting is
            set to 'goes low,' DTR will change the state to
            low if the Ethernet link is off."
        ::= { socketEntry 11 }

	socketResponseTimeout OBJECT-TYPE
        SYNTAX INTEGER
        MAX-ACCESS read-write                
        STATUS current
        DESCRIPTION
            "After sending a command to the serial device, the NPort 
            will wait for a response. If no response is received from 
            the serial device within the specified time, the NPort will 
            give up and continue to the next command."
        ::= { socketEntry 12 }	
	
	socketNonRequestSerialData OBJECT-TYPE
        SYNTAX INTEGER { discard(0), forward-to-last-requester(1), forward-to-all-open-connections(2) }
        MAX-ACCESS read-write                
        STATUS current
        DESCRIPTION
            "This specifies how the NPort will handle data that is 
            received from a serial device that is not a response to 
            a command. The NPort can either discard such data, forward 
            the data to the network host that sent the most recent request, 
            or forward the data to all open host connections."
        ::= { socketEntry 13 }

    socketTcpClientDestinationAddress1 OBJECT-TYPE
		SYNTAX DisplayString (SIZE(0..40))
		MAX-ACCESS read-write                
		STATUS current
		DESCRIPTION
			"The NPort 6000 series device server can connect actively 
			to a remote host that has this IP address."
		::= { socketEntry 14 }       
		
	socketTcpClientDestinationPort1 OBJECT-TYPE
		SYNTAX INTEGER
		MAX-ACCESS read-write                
		STATUS current
		DESCRIPTION
			"The NPort 6000 series device server can connect actively 
			to a remote host that has this TCP port number."
		::= { socketEntry 15 }    
		
	socketTcpClientDestinationAddress2 OBJECT-TYPE
		SYNTAX DisplayString (SIZE(0..40))
		MAX-ACCESS read-write                
		STATUS current
		DESCRIPTION
			"The NPort 6000 series device server can
			connect actively to a remote host that has this IP
			address."
		::= { socketEntry 16 }       
		
	socketTcpClientDestinationPort2 OBJECT-TYPE
		SYNTAX INTEGER
		MAX-ACCESS read-write                
		STATUS current
		DESCRIPTION
			"The NPort 6000 series device server can
			connect actively to a remote host that
			has this TCP port number."
		::= { socketEntry 17 }   
		
	socketTcpClientDestinationAddress3 OBJECT-TYPE
		SYNTAX DisplayString (SIZE(0..40))
		MAX-ACCESS read-write                
		STATUS current
		DESCRIPTION
			"The NPort 6000 series device server can
			connect actively to a remote host that 
                        has this IP address."
		::= { socketEntry 18 }       
		
	socketTcpClientDestinationPort3 OBJECT-TYPE
		SYNTAX INTEGER
		MAX-ACCESS read-write                
		STATUS current
		DESCRIPTION
			"The NPort 6000 series device server can
			connect actively to a remote host that
                        has this port number."
		::= { socketEntry 19 } 
		
	socketTcpClientDestinationAddress4 OBJECT-TYPE
		SYNTAX DisplayString (SIZE(0..40))
		MAX-ACCESS read-write                
		STATUS current
		DESCRIPTION
			"The NPort 6000 series device server can
			connect actively to a remote host that
                        has this IP address."
		::= { socketEntry 20 }       
		
	socketTcpClientDestinationPort4 OBJECT-TYPE
		SYNTAX INTEGER
		MAX-ACCESS read-write                
		STATUS current
		DESCRIPTION
			"The NPort 6000 series device server can
			connect actively to a remote host that 
                        has this port number."
		::= { socketEntry 21 } 
		
	socketTcpClientDesignatedLocalPort1 OBJECT-TYPE
		SYNTAX INTEGER
		MAX-ACCESS read-write                
		STATUS current
		DESCRIPTION
			"The local TCP port used to connect actively to the
			remote host."
		::= { socketEntry 22 } 
		
	socketTcpClientDesignatedLocalPort2 OBJECT-TYPE
		SYNTAX INTEGER
		MAX-ACCESS read-write                
		STATUS current
		DESCRIPTION
			"The local TCP port used to connect actively to the
			remote host."
		::= { socketEntry 23 }
		
	socketTcpClientDesignatedLocalPort3 OBJECT-TYPE
		SYNTAX INTEGER
		MAX-ACCESS read-write                
		STATUS current
		DESCRIPTION
			"The local TCP port used to connect actively to the
			remote host."
		::= { socketEntry 24 }
		
	socketTcpClientDesignatedLocalPort4 OBJECT-TYPE
		SYNTAX INTEGER
		MAX-ACCESS read-write                
		STATUS current
		DESCRIPTION
			"The local TCP port used to connect actively to the
			remote host."
		::= { socketEntry 25 }
		
	socketTcpClientConnectionControl OBJECT-TYPE
		SYNTAX INTEGER {
			startup-None(257),
			anyCharacter-None(258),
			anyCharacter-InactivityTime(514),
			dsrOn-DSR-Off(1028),
			dsrOn-None(260),
			dcdOn-DCD-Off(2056),
			dcdOn-None(264) 
		}
		MAX-ACCESS read-write                
		STATUS current
		DESCRIPTION
			"Events that cause the TCP client to drop the
			connection."
		::= { socketEntry 26 }
	
	socketUdpDestinationAddress1Begin OBJECT-TYPE
		SYNTAX DisplayString (SIZE(0..40))
		MAX-ACCESS read-write                
		STATUS current
		DESCRIPTION
			"The NPort 6000 series device server can actively send
			UDP packets to remote hosts whose IP
			addresses are in the range between this parameter and
			socketUdpDestinationAddress1End."
		::= { socketEntry 27 }     
		
	socketUdpDestinationAddress1End OBJECT-TYPE
		SYNTAX DisplayString (SIZE(0..40))
		MAX-ACCESS read-write                
		STATUS current
		DESCRIPTION
			"The NPort 6000 series device server can actively send
			UDP packets to remote hosts whose IP
			addresses are in the range between
			socketUdpDestinationAddress1Begin and this parameter."
		::= { socketEntry 28 }    
		
	socketUdpDestinationPort1 OBJECT-TYPE
		SYNTAX INTEGER
		MAX-ACCESS read-write                
		STATUS current
		DESCRIPTION
			"The NPort 6000 series device server can actively send
			UDP packets to remote hosts that have this port
			number."
		::= { socketEntry 29 }    
		
	socketUdpDestinationAddress2Begin OBJECT-TYPE
		SYNTAX DisplayString (SIZE(0..40))
		MAX-ACCESS read-write                
		STATUS current
		DESCRIPTION
			"The NPort 6000 series device server can actively send
			UDP packets to remote hosts whose IP
			addresses are in the range between this parameter and
			socketUdpDestinationAddress2End."
		::= { socketEntry 30 }     
		
	socketUdpDestinationAddress2End OBJECT-TYPE
		SYNTAX DisplayString (SIZE(0..40))
		MAX-ACCESS read-write                
		STATUS current
		DESCRIPTION
			"The NPort 6000 series device server can actively send
			UDP packets to the remote hosts whose IP
			addresses are in the range between
			socketUdpDestinationAddress2Begin and this parameter."
		::= { socketEntry 31 }    
		
	socketUdpDestinationPort2 OBJECT-TYPE
		SYNTAX INTEGER
		MAX-ACCESS read-write                
		STATUS current
		DESCRIPTION
			"The NPort 6000 series device server can actively send
			UDP packets to the remote hosts that have this 
                        TCP port number."
		::= { socketEntry 32 } 
	
	socketUdpDestinationAddress3Begin OBJECT-TYPE
		SYNTAX DisplayString (SIZE(0..40))
		MAX-ACCESS read-write                
		STATUS current
		DESCRIPTION
			"The NPort 6000 series device server can actively send
			UDP packets to remote hosts whose IP
			addresses are in the range between this parameter and
			socketUdpDestinationAddress3End."
		::= { socketEntry 33 }     
		
	socketUdpDestinationAddress3End OBJECT-TYPE
		SYNTAX DisplayString (SIZE(0..40))
		MAX-ACCESS read-write                
		STATUS current
		DESCRIPTION
			"The NPort 6000 series device server can actively send
			UDP packets to remote hosts whose IP
			addresses are in the range between
			socketUdpDestinationAddress3Begin and this parameter."
		::= { socketEntry 34 }    
		
	socketUdpDestinationPort3 OBJECT-TYPE
		SYNTAX INTEGER
		MAX-ACCESS read-write                
		STATUS current
		DESCRIPTION
			"The NPort 6000 series device server can actively send
			UDP packets to remote hosts that have this 
                        TCP port number."
		::= { socketEntry 35 } 
		
	socketUdpDestinationAddress4Begin OBJECT-TYPE
		SYNTAX DisplayString (SIZE(0..40))
		MAX-ACCESS read-write                
		STATUS current
		DESCRIPTION
			"The NPort 6000 series device server can actively send
			UDP packets to remote hosts whose IP
			addresses are in the range between this parameter and
			socketUdpDestinationAddress4End."
		::= { socketEntry 36 }     
		
	socketUdpDestinationAddress4End OBJECT-TYPE
		SYNTAX DisplayString (SIZE(0..40))
		MAX-ACCESS read-write                
		STATUS current
		DESCRIPTION
			"The NPort 6000 series device server can actively send
			UDP packets to remote hosts whose IP
			addresses are in the range between
			socketUdpDestinationAddress4Begin and this parameter."
		::= { socketEntry 37 }    
		
	socketUdpDestinationPort4 OBJECT-TYPE
		SYNTAX INTEGER
		MAX-ACCESS read-write                
		STATUS current
		DESCRIPTION
			"The NPort 6000 series device server can actively send
			UDP packets to remote hosts that have this 
                        TCP port number."
		::= { socketEntry 38 } 
		
	socketUdpLocalListenPort OBJECT-TYPE
		SYNTAX INTEGER
		MAX-ACCESS read-write                
		STATUS current
		DESCRIPTION
			"The UDP port that the NPort 6000 series device
			server listens to and that other devices must use
			to contact the NPort 6000 series device server."
		::= { socketEntry 39 } 

	socketUDPDynamicDst OBJECT-TYPE
        SYNTAX INTEGER { disable(0), enable(1) }
        MAX-ACCESS read-write                
        STATUS current
        DESCRIPTION
            "If enable Dynamic Destination, 
	     the target address is decieded by the source 
             address of the last received data."
        ::= { socketEntry 40 }

	socketUDPDynamicDstTimeout OBJECT-TYPE
        SYNTAX INTEGER
        MAX-ACCESS read-write                
        STATUS current
        DESCRIPTION
            "0 ms: The target address will be changed every time.
            1-65535 ms: The target address will be occupied before the
	    source address idle for a period of time."
        ::= { socketEntry 41 }

-- --------------------------------------------------------------------------------------
-- Serial port settings -> Operation Modes settings -> Pair Connection
-- --------------------------------------------------------------------------------------

	pairConnection OBJECT IDENTIFIER ::= { application 3 }
	
	pairConnectionTable OBJECT-TYPE
        SYNTAX SEQUENCE OF PairConnectionEntry
        MAX-ACCESS not-accessible               
        STATUS current
        DESCRIPTION
            "The Pair Connection table."
        ::= { pairConnection 1 }
    
    pairConnectionEntry OBJECT-TYPE
        SYNTAX PairConnectionEntry
        MAX-ACCESS not-accessible               
        STATUS current
        DESCRIPTION
            "The Pair Connection entry."
        INDEX { portIndex }
        ::= { pairConnectionTable 1 }
        
    PairConnectionEntry ::=
        SEQUENCE {
        	pairConnectionTcpAliveCheck
        		INTEGER,
        	pairConnectionSecure
        		INTEGER,
            pairConnectionDestinationAddress
            	DisplayString,
            pairConnectionDestinationPort
            	INTEGER,
            pairConnectionTcpPort
            	INTEGER
        }
       	
    pairConnectionTcpAliveCheck OBJECT-TYPE
        SYNTAX INTEGER
        MAX-ACCESS read-write                
        STATUS current
        DESCRIPTION
            "The TCP alive check time.
            0 min: TCP connection will not be closed if the
            TCP connection becomes idle.
            1 to 99 min: The NPort 6000 series device server
            automatically closes the TCP connection if there is
            no TCP activity for the given time. After the
            connection is closed, the NPort 6000 series device
            server starts listening for another Real COM driver
            Connection."
        ::= { pairConnectionEntry 1 }
        
    pairConnectionSecure OBJECT-TYPE
        SYNTAX INTEGER { disable(0), enable(1) }
        MAX-ACCESS read-write                
        STATUS current
        DESCRIPTION
            "If Secure is enabled, the Ethernet data will be
            encrypted using SSL."
        ::= { pairConnectionEntry 2 }
        
	pairConnectionDestinationAddress OBJECT-TYPE
		SYNTAX DisplayString (SIZE(0..40))
		MAX-ACCESS read-write                
		STATUS current
		DESCRIPTION
			"The Pair Connection 'Master' will contact the
			network host that has the specified IP address."
		::= { pairConnectionEntry 3 }    
		
	pairConnectionDestinationPort OBJECT-TYPE
		SYNTAX INTEGER
		MAX-ACCESS read-write                
		STATUS current
		DESCRIPTION
			"Data will be transmitted through the specified port
			number. Note that you must configure the same TCP
			port number for the device server acting as the Pair
			Connection 'Slave.'"
		::= { pairConnectionEntry 4 } 
		
	pairConnectionTcpPort OBJECT-TYPE
		SYNTAX INTEGER
		MAX-ACCESS read-write                
		STATUS current
		DESCRIPTION
			"This port number must be the same port number that was
			set up for the Pair Connection 'Master' device
			server."
		::= { pairConnectionEntry 5 }       	
        
        
-- --------------------------------------------------------------------------------------
-- Serial port settings -> Operation Modes settings -> Ethernet Modem
-- --------------------------------------------------------------------------------------

	ethernetModem OBJECT IDENTIFIER ::= { application 4 }
	
	ethernetModemTable OBJECT-TYPE
        SYNTAX SEQUENCE OF EthernetModemEntry
        MAX-ACCESS not-accessible               
        STATUS current
        DESCRIPTION
            "The Ethernet Modem table."
        ::= { ethernetModem 1 }
    
    ethernetModemEntry OBJECT-TYPE
        SYNTAX EthernetModemEntry
        MAX-ACCESS not-accessible               
        STATUS current
        DESCRIPTION
            "The Ethernet Modem entry."
        INDEX { portIndex }
        ::= { ethernetModemTable 1 }
        
    EthernetModemEntry ::=
        SEQUENCE {      
        	ethernetModemTcpAliveCheck
        		INTEGER,
            ethernetModemTcpPort
            	INTEGER
        }
        
	ethernetModemTcpAliveCheck OBJECT-TYPE
        SYNTAX INTEGER
        MAX-ACCESS read-write                
        STATUS current
        DESCRIPTION
            "The TCP alive check time.
            0 min: TCP connection will not be closed if the 
            TCP connection becomes idle.
            1 to 99 min: The NPort 6000 series device server
            automatically closes the TCP connection if there is
            no TCP activity for the given time. After the
            connection is closed, the NPort 6000 series device
            server starts listening for another Real COM driver
            Connection."
        ::= { ethernetModemEntry 1 }
        
	ethernetModemTcpPort OBJECT-TYPE
		SYNTAX INTEGER
		MAX-ACCESS read-write                
		STATUS current
		DESCRIPTION
			"The local TCP port used to listen for incoming calls
			from a remote ethernet modem."
		::= { ethernetModemEntry 2 } 
           
-- --------------------------------------------------------------------------------------
-- Serial port settings -> Operation Modes settings -> Application -> Terminal
-- --------------------------------------------------------------------------------------

	terminal OBJECT IDENTIFIER ::= { application 5 }
	
	terminalTable OBJECT-TYPE
        SYNTAX SEQUENCE OF TerminalEntry
        MAX-ACCESS not-accessible               
        STATUS current
        DESCRIPTION
            "The Terminal Application table."
        ::= { terminal 1 }
    
    terminalEntry OBJECT-TYPE
        SYNTAX TerminalEntry
        MAX-ACCESS not-accessible               
        STATUS current
        DESCRIPTION
            "The Terminal Application entry."
        INDEX { portIndex }
        ::= { terminalTable 1 }
        
    TerminalEntry ::=
        SEQUENCE {
        	terminalTcpAliveCheck
        		INTEGER,
        	terminalInactivityTime
        		INTEGER,
        	terminalAutoLinkProtocol
            	INTEGER,
            terminalPrimaryHostAddress
            	DisplayString,
            terminalSecondHostAddress
            	DisplayString,
            terminalTelnetTcpPort
            	INTEGER,
            terminalSshTcpPort
            	INTEGER,
            terminalType
                DisplayString,
            terminalMaxSessions
            	INTEGER,
            terminalChangeSession
            	DisplayString,
            terminalQuit
            	DisplayString,
            terminalBreak
            	DisplayString,
            terminalInterrupt
            	DisplayString,
            terminalAuthenticationType
            	INTEGER,
            terminalTryNextAuth
            	INTEGER,	
            terminalAutoLoginPrompt
            	DisplayString,
            terminalPasswordPrompt
            	DisplayString,
            terminalLoginUserName
            	DisplayString,
            terminalLoginPassword
            	DisplayString
        }
    
	terminalTcpAliveCheck OBJECT-TYPE
        SYNTAX INTEGER
        MAX-ACCESS read-write                
        STATUS current
        DESCRIPTION
            "The TCP alive check time.
            0 min: TCP connection will not be closed if the 
            TCP connection becomes idle.
            1 to 99 min: The NPort 6000 series device server
            automatically closes the TCP connection if there is
            no TCP activity for the given time. After the
            connection is closed, the NPort 6000 series device
            server starts listening for another Real COM driver
            Connection from another host."
        ::= { terminalEntry 1 }
        
	terminalInactivityTime OBJECT-TYPE
        SYNTAX INTEGER
        MAX-ACCESS read-write                
        STATUS current
        DESCRIPTION
            "0 min: TCP connection will not be closed if the 
            serial line becomes idle.
            0-99 min: The NPort 6000 series device server
            automatically closes the TCP connection if there is
            no serial data activity for the given time. After
            the connection is closed, the NPort 6000 series
            device server starts listening for another host's
            TCP connection."
        ::= { terminalEntry 2 }
    
    terminalAutoLinkProtocol OBJECT-TYPE
		SYNTAX INTEGER {none(0), telnet(1), rlogin(2)}
		MAX-ACCESS read-write                
		STATUS current
		DESCRIPTION
			"If Auto-Link protocol is set to 'None,' the NPort
			6000 series device server will not connect to the
			host automatically. If Auto-Link protocol is set to
			'Telnet,' the NPort 6000 series device server will
			connect to the host automatically using Telnet. If
			Auto-Link protocol is set to 'Rlogin,' the NPort
			6000 series device server will connect to the host
			automatically using rlogin."
		::= { terminalEntry 3 } 
		
	terminalPrimaryHostAddress OBJECT-TYPE
		SYNTAX DisplayString (SIZE(0..40))
		MAX-ACCESS read-write                
		STATUS current
		DESCRIPTION
			"If specified, designates a 'permanent' host to
			which the terminal will always be connected."
		::= { terminalEntry 4 }   
		
	terminalSecondHostAddress OBJECT-TYPE
		SYNTAX DisplayString (SIZE(0..40))
		MAX-ACCESS read-write                
		STATUS current
		DESCRIPTION
			"If specified, designates a 'permanent' host to
			which the terminal will always be connected."
		::= { terminalEntry 5 }  
		
	terminalTelnetTcpPort OBJECT-TYPE
		SYNTAX INTEGER
		MAX-ACCESS read-write                
		STATUS current
		DESCRIPTION
			"By default, the Telnet TCP port number is set to
			23, which is the default TCP port number for Telnet.
			If you need to telnet to this NPort 6000 series
			device server's serial port, set the Telnet TCP port
			to a different number."
		::= { terminalEntry 6 }  
		
	terminalSshTcpPort OBJECT-TYPE
		SYNTAX INTEGER
		MAX-ACCESS read-write                
		STATUS current
		DESCRIPTION
			"By default, the SSH TCP port number is set to 22,
			which is the default TCP port number for SSH. If
			you need to use SSH to connect to this NPort 6000
			series device server's serial port, set the Telnet
			TCP port to a different number."
		::= { terminalEntry 7 }  

	terminalType OBJECT-TYPE
		SYNTAX DisplayString (SIZE(0..8))
		MAX-ACCESS read-write                
		STATUS current
		DESCRIPTION
			"Defines the terminal type for outgoing connections."
		::= { terminalEntry 8 } 
		
	terminalMaxSessions OBJECT-TYPE
        SYNTAX INTEGER (1..8)
        MAX-ACCESS read-write                
        STATUS current
        DESCRIPTION
            "Configure the max. number of sessions."
        ::= { terminalEntry 9 }  
        
    terminalChangeSession OBJECT-TYPE
		SYNTAX DisplayString (SIZE(0..2))
		MAX-ACCESS read-write                
		STATUS current
		DESCRIPTION
			"Defines the control character used to change the terminal
			session."
		::= { terminalEntry 10 }    
		
	terminalQuit OBJECT-TYPE
		SYNTAX DisplayString (SIZE(0..2))
		MAX-ACCESS read-write                
		STATUS current
		DESCRIPTION
			"Defines the control character used to quit a terminal
			session."
		::= { terminalEntry 11 } 
		
	terminalBreak OBJECT-TYPE
		SYNTAX DisplayString (SIZE(0..2))
		MAX-ACCESS read-write                
		STATUS current
		DESCRIPTION
			"Defines the control character used to send a Telnet
			BREAK message."
		::= { terminalEntry 12 } 
	
	terminalInterrupt OBJECT-TYPE
		SYNTAX DisplayString (SIZE(0..2))
		MAX-ACCESS read-write                
		STATUS current
		DESCRIPTION
			"Defines the control character used to send a Telnet
			INTERRUPT message."
		::= { terminalEntry 13 } 
		
	terminalAuthenticationType OBJECT-TYPE
        SYNTAX INTEGER  { none(0), local(1), radius(2), radius-local(3), local-radius(4), tacacsPlus(5), tacacsPlus-local(6), local-tacacsPlus(7)}
        MAX-ACCESS read-write                
        STATUS current
        DESCRIPTION
            "The terminal authentication type."
        ::= { terminalEntry 14 }

	terminalTryNextAuth OBJECT-TYPE
        SYNTAX INTEGER { disable(0), enable(1)}
        MAX-ACCESS read-write               
        STATUS current
        DESCRIPTION
            "Try next type on authentication denied or not"
		::= { terminalEntry 15 }    
        
    terminalAutoLoginPrompt OBJECT-TYPE
		SYNTAX DisplayString (SIZE(0..16))
		MAX-ACCESS read-write                
		STATUS current
		DESCRIPTION
			"The prompt string for the automatic login ID. When the
			NPort 6000 series device server receives this string
			from a remote telnet/rlogin server, it will
			automatically reply with the user ID."
		::= { terminalEntry 16 } 
		
	terminalPasswordPrompt OBJECT-TYPE
		SYNTAX DisplayString (SIZE(0..16))
		MAX-ACCESS read-write                
		STATUS current
		DESCRIPTION
			"The prompt string for the automatic login password.
			When the NPort 6000 series device server receives this
			string from a remote telnet/rlogin server, it will
			automatically reply with the user password."
		::= { terminalEntry 17 } 
		
	terminalLoginUserName OBJECT-TYPE
		SYNTAX DisplayString (SIZE(0..16))
		MAX-ACCESS read-write                
		STATUS current
		DESCRIPTION
			"Terminal login ID for automatic login."
		::= { terminalEntry 18 } 
		
	terminalLoginPassword OBJECT-TYPE
		SYNTAX DisplayString (SIZE(0..16))
		MAX-ACCESS read-write                
		STATUS current
		DESCRIPTION
			"Terminal login password for automatic login."
		::= { terminalEntry 19 } 

-- --------------------------------------------------------------------------------------
-- Serial port settings -> Operation Modes settings -> Application -> Reverse Terminal
-- --------------------------------------------------------------------------------------

	reverseTerminal OBJECT IDENTIFIER ::= { application 6 }
	
	reverseTerminalTable OBJECT-TYPE
        SYNTAX SEQUENCE OF ReverseTerminalEntry
        MAX-ACCESS not-accessible               
        STATUS current
        DESCRIPTION
            "The Reverse Terminal Application table."
        ::= { reverseTerminal 1 }
    
    reverseTerminalEntry OBJECT-TYPE
        SYNTAX ReverseTerminalEntry
        MAX-ACCESS not-accessible               
        STATUS current
        DESCRIPTION
            "The Reverse Terminal Application entry."
        INDEX { portIndex }
        ::= { reverseTerminalTable 1 }
        
    ReverseTerminalEntry ::=
        SEQUENCE {
        	reverseTerminalTcpAliveCheck
        		INTEGER,
        	reverseTerminalInactivityTime
        		INTEGER,
            reverseTerminalTcpPort
            	INTEGER,
            reverseTerminalAuthenticationType
            	INTEGER,
            reverseTerminalTryNextAuth
            	INTEGER,	
            reverseTerminalMapKeys
            	INTEGER
        }
        
	reverseTerminalTcpAliveCheck OBJECT-TYPE
        SYNTAX INTEGER
        MAX-ACCESS read-write                
        STATUS current
        DESCRIPTION
            "The TCP alive check time.
            0 min: TCP connection will not be closed when the
            TCP connection becomes idle.
            1 to 99 min: The NPort 6000 series device server
            automatically closes the TCP connection if there is
            no TCP activity for the given time. After the
            connection is closed, the NPort 6000 series device
            server starts listening for another Real COM driver
            Connection."
        ::= { reverseTerminalEntry 1 }
        
	reverseTerminalInactivityTime OBJECT-TYPE
        SYNTAX INTEGER
        MAX-ACCESS read-write                
        STATUS current
        DESCRIPTION
            "0 min: TCP connection will not be closed if the 
            serial line becomes idle.
            0-99 min: The NPort 6000 series device server
            automatically closes the TCP connection if there is
            no serial data activity for the given time. After
            the connection is closed, the NPort 6000 series
            device server starts listening for another
            TCP connection."
        ::= { reverseTerminalEntry 2 }
		        
	reverseTerminalTcpPort OBJECT-TYPE
		SYNTAX INTEGER
		MAX-ACCESS read-write                
		STATUS current
		DESCRIPTION
			"Each of the NPort 6000 series device server's serial
			ports are mapped to a TCP port."
		::= { reverseTerminalEntry 3 }   
		
	reverseTerminalAuthenticationType OBJECT-TYPE
		SYNTAX INTEGER  { none(0), local(1), radius(2), radius-local(3), local-radius(4), tacacsPlus(5), tacacsPlus-local(6), local-tacacsPlus(7)}
		MAX-ACCESS read-write                
		STATUS current
		DESCRIPTION
			"The reverse terminal authentication type."
		::= { reverseTerminalEntry 4 } 
	
	reverseTerminalTryNextAuth OBJECT-TYPE
        SYNTAX INTEGER { disable(0), enable(1)}
        MAX-ACCESS read-write               
        STATUS current
        DESCRIPTION
            "Try next type on authentication denied or not"
		::= { reverseTerminalEntry 5 }    
		
	reverseTerminalMapKeys OBJECT-TYPE
		SYNTAX INTEGER  { cr-lf(0), cr(1), lf(2) }
		MAX-ACCESS read-write                
		STATUS current
		DESCRIPTION
			"If data received through NPort 6000 series device
			server's Ethernet port is sent using the 'enter'
			command, the data will be transmitted out through
			the serial port with an added
			1. 'carriage return + line feed' if you select the
			'cr-lf' option (i.e., the cursor will jump to the
			next line, and return to the first character of the
			line)
			2. 'carriage return' if you select the 'cr' option
			(i.e., the cursor will return to the first character
			of the line
			3. 'line feed' if you select the 'lf' option. (i.e.,
			the cursor will jump to the next line, but not move
			horizontally)"
		::= { reverseTerminalEntry 6 } 
		
		
-- --------------------------------------------------------------------------------------
-- Serial port settings -> Operation Modes settings -> Application -> Printer
-- --------------------------------------------------------------------------------------

	printer OBJECT IDENTIFIER ::= { application 7 }
	
	printerTable OBJECT-TYPE
        SYNTAX SEQUENCE OF PrinterEntry
        MAX-ACCESS not-accessible               
        STATUS current
        DESCRIPTION
            "The Printer Application table."
        ::= { printer 1 }
    
    printerEntry OBJECT-TYPE
        SYNTAX PrinterEntry
        MAX-ACCESS not-accessible               
        STATUS current
        DESCRIPTION
            "The Printer Application entry."
        INDEX { portIndex }
        ::= { printerTable 1 }
        
    PrinterEntry ::=
        SEQUENCE {
        	printerTcpAliveCheck
        		INTEGER,
			printerTcpPort
            	INTEGER,
            printerGroup
            	INTEGER,
            printerQueueNameRaw
            	DisplayString,
            printerQueueNameASCII
            	DisplayString,
            printerAppendFormFeed
            	INTEGER
       }
    
	printerTcpAliveCheck OBJECT-TYPE
        SYNTAX INTEGER
        MAX-ACCESS read-write                
        STATUS current
        DESCRIPTION
            "The TCP alive check time.
            0 min: TCP connection will not be closed if the
            TCP connection becomes idle.
            1 to 99 min: The NPort 6000 series device server
            automatically closes the TCP connection if there is
            no TCP activity for the given time. After the
            connection is closed, the NPort 6000 series device
            server starts listening for another Real COM driver
            Connection."
        ::= { printerEntry 1 }
       
	printerTcpPort OBJECT-TYPE
		SYNTAX INTEGER
		MAX-ACCESS read-only                
		STATUS current
		DESCRIPTION
			"The host uses this value to determine the Group to
			which the printer attached to this serial port
			belongs. These values are fixed, and cannot be
			changed by the user."
		::= { printerEntry 2 } 
		
	printerGroup OBJECT-TYPE
		SYNTAX INTEGER {
			group1(0),
			group2(1),
			group3(2),
			group4(3),
			group5(4),
			group6(5),
			group7(6),
			group8(7),
			group9(8),
			group10(9),
			group11(10),
			group12(11),
			group13(12),
			group14(13),
			group15(14),
			group16(15),
			group17(16),
			group18(17),
			group19(18),
			group20(19),
			group21(20),
			group22(21),
			group23(22),
			group24(23),
			group25(24),
			group26(25),
			group27(26), 
			group28(27), 
			group29(28), 
			group30(29), 
			group31(30),
			group32(31)
		}
		MAX-ACCESS read-write                
		STATUS current
		DESCRIPTION
			"Groups printers attached to different ports.
			Printers in the same group will share the printing
			load for printing requests to that group of
			printers. E.g., setting the NPort 6000 series device
			server's serial ports 1, 3, and 6 for 'Group01' will
			allow the printers attached to these three ports to
			act essentially as one printer."
		::= { printerEntry 3 } 
		
	printerQueueNameRaw OBJECT-TYPE
		SYNTAX DisplayString (SIZE(0..16))
		MAX-ACCESS read-write                
		STATUS current
		DESCRIPTION
			"Specify the name of the print queue (in RAW mode)."
		::= { printerEntry 4 }
		
	printerQueueNameASCII OBJECT-TYPE
		SYNTAX DisplayString (SIZE(0..16))
		MAX-ACCESS read-write                
		STATUS current
		DESCRIPTION
			"Specify the name of the print queue (in ASCII mode)."
		::= { printerEntry 5 }
		
	printerAppendFormFeed OBJECT-TYPE
		SYNTAX INTEGER { disable(0), enable(1)}
		MAX-ACCESS read-write                
		STATUS current
		DESCRIPTION
			"Specify paging."
		::= { printerEntry 6 } 
        
-- --------------------------------------------------------------------------------------
-- Serial port settings -> Operation Modes settings -> Application -> Dial In/Out
-- --------------------------------------------------------------------------------------

	dial OBJECT IDENTIFIER ::= { application 8 }
	
	dialTable OBJECT-TYPE
        SYNTAX SEQUENCE OF DialEntry
        MAX-ACCESS not-accessible               
        STATUS current
        DESCRIPTION
            "The Dial In/Out table."
        ::= { dial 1 }
    
    dialEntry OBJECT-TYPE
        SYNTAX DialEntry
        MAX-ACCESS not-accessible               
        STATUS current
        DESCRIPTION
            "The Dial In/Out entry."
        INDEX { portIndex }
        ::= { dialTable 1 }
        
    DialEntry ::=
        SEQUENCE { 
			dialTERMBINMode
            	INTEGER,
            dialPPPDMode
            	INTEGER,
            dialSLIPDMode
            	INTEGER,
            dialAuthType
            	INTEGER,
            dialTryNextAuth
            	INTEGER,	
            dialDisconnectBy
            	INTEGER,
            dialDestinationIpAddress
            	IpAddress,
            dialSourceIpAddress
            	IpAddress,
            dialIpNetmask
            	IpAddress,
            dialTcpIpCompression
            	INTEGER,
            dialInactivityTime
            	INTEGER,
            dialLinkQualityReport
            	INTEGER,
            dialUsername
            	DisplayString,
            dialPassword
            	DisplayString,
            dialIncomingPAPCheck
            	INTEGER,
            dialIncomingTryNextAuth
            	INTEGER	
        }
	
	dialTERMBINMode OBJECT-TYPE
        SYNTAX INTEGER  { disable(0), enable(1) }
        MAX-ACCESS read-write                
        STATUS current
        DESCRIPTION
            "Select Yes to enable a Binary Terminal connection."
        ::= { dialEntry 1 }
        
    dialPPPDMode OBJECT-TYPE
        SYNTAX INTEGER  { disable(0), enable(1) }
        MAX-ACCESS read-write                
        STATUS current
        DESCRIPTION
            "Select Yes to enable a PPPD connection."
        ::= { dialEntry 2 }
    
    dialSLIPDMode OBJECT-TYPE
        SYNTAX INTEGER  { disable(0), enable(1) }
        MAX-ACCESS read-write                
        STATUS current
        DESCRIPTION
            "Select Yes to enable a SLIPD Terminal connection."
        ::= { dialEntry 3 }
    
    dialAuthType OBJECT-TYPE
        SYNTAX INTEGER  { none(0), local(1), radius(2), radius-local(3), local-radius(4), tacacsPlus(5), tacacsPlus-local(6), local-tacacsPlus(7)}
        MAX-ACCESS read-write                
        STATUS current
        DESCRIPTION
            "The dial in/out authentication type."
        ::= { dialEntry 4 }
    
    dialTryNextAuth OBJECT-TYPE
        SYNTAX INTEGER { disable(0), enable(1)}
        MAX-ACCESS read-write               
        STATUS current
        DESCRIPTION
            "Try next type on authentication denied or not"
		::= { dialEntry 5 }    
        
    dialDisconnectBy OBJECT-TYPE
        SYNTAX INTEGER  { none(0), dcd-off(2), dsr-off(4) }
        MAX-ACCESS read-write                
        STATUS current
        DESCRIPTION
            "If this field is set to 'dcd-off,' the connection
            will be disconnected when the DCD signal is off.
            If this field is set to 'dsr-off,' the connection
            will be disconnected when the DSR signal is off."
        ::= { dialEntry 6 }
	
	dialDestinationIpAddress OBJECT-TYPE
		SYNTAX IpAddress
		MAX-ACCESS read-write                
		STATUS current
		DESCRIPTION
			"Destination IP address is the IP address of the
			remote dial-in/dial-out server."
		::= { dialEntry 7 }    
		
	dialSourceIpAddress OBJECT-TYPE
		SYNTAX IpAddress
		MAX-ACCESS read-write                
		STATUS current
		DESCRIPTION
			"Source IP address is IP address of this serial
			port. The NPort 6000 series device server will
			automatically assign an IP address for the port.
			We recommend leaving this field blank."
		::= { dialEntry 8 }    
		
	dialIpNetmask OBJECT-TYPE
		SYNTAX IpAddress
		MAX-ACCESS read-write                
		STATUS current
		DESCRIPTION
			"The IP netmask used for dial-in/dial-out networks
			(PPP or SLIP)."
		::= { dialEntry 9 } 
		
	dialTcpIpCompression OBJECT-TYPE
		SYNTAX INTEGER { disable(0), enable(1)}
		MAX-ACCESS read-write                
		STATUS current
		DESCRIPTION
			"Depends on whether the remote user's application
			requests compression."
		::= { dialEntry 10 } 
	
	dialInactivityTime OBJECT-TYPE
        SYNTAX INTEGER
        MAX-ACCESS read-write                
        STATUS current
        DESCRIPTION
            "0 ms: TCP connection will not be closed if the 
            serial line becomes idle.
            1-65535 ms: The NPort 6000 series device server
            automatically closes the TCP connection if there is
            no serial data activity for the given time. After
            the connection is closed, the NPort 6000 series
            device server starts listening for another
            TCP connection."
        ::= { dialEntry 11 }
		
	dialLinkQualityReport OBJECT-TYPE
		SYNTAX INTEGER { disable(0), enable(1)}
		MAX-ACCESS read-write                
		STATUS current
		DESCRIPTION
			"Choose YES if you are using software to collect Link quality
			information."
		::= { dialEntry 12 } 
		
	dialUsername OBJECT-TYPE
		SYNTAX DisplayString (SIZE(0..16))
		MAX-ACCESS read-write                
		STATUS current
		DESCRIPTION
			"Dial-out user ID account."
		::= { dialEntry 13 }
		
	dialPassword OBJECT-TYPE
		SYNTAX DisplayString (SIZE(0..16))
		MAX-ACCESS read-write                
		STATUS current
		DESCRIPTION
			"Dial-out user password."
		::= { dialEntry 14 }
		
	dialIncomingPAPCheck OBJECT-TYPE
        SYNTAX INTEGER  { none(0), local(1), radius(2), radius-local(3), local-radius(4), tacacsPlus(5), tacacsPlus-local(6), local-tacacsPlus(7)}
        MAX-ACCESS read-write                
        STATUS current
        DESCRIPTION
            "The Dial in/out incoming PAP check type."
        ::= { dialEntry 15 }

	dialIncomingTryNextAuth OBJECT-TYPE
        SYNTAX INTEGER { disable(0), enable(1)}
        MAX-ACCESS read-write               
        STATUS current
        DESCRIPTION
            "Try next type on authentication denied or not"
		::= { dialEntry 16 }    
        
-- --------------------------------------------------------------------------------------
-- Serial port settings -> Operation Modes settings -> Data Packing
-- --------------------------------------------------------------------------------------

	dataPacking OBJECT IDENTIFIER ::= { opModeSetting 3 }
	
	dataPackingPortTable OBJECT-TYPE
        SYNTAX SEQUENCE OF DataPackingPortEntry
        MAX-ACCESS not-accessible               
        STATUS current
        DESCRIPTION
            "The Data Packing table."
        ::= { dataPacking 1 }
    
    dataPackingPortEntry OBJECT-TYPE
        SYNTAX DataPackingPortEntry
        MAX-ACCESS not-accessible               
        STATUS current
        DESCRIPTION
            "The Data Packing entry."
        INDEX { portIndex }
        ::= { dataPackingPortTable 1 }
        
    DataPackingPortEntry ::=
        SEQUENCE {
            portPacketLength
                INTEGER,
            portDelimiter1Enable
                INTEGER,
            portDelimiter1
            	DisplayString,
            portDelimiter2Enable
                INTEGER,
            portDelimiter2
            	DisplayString,
            portDelimiterProcess
            	INTEGER,
            portForceTransmit
            	INTEGER
        }
        
	portPacketLength OBJECT-TYPE
        SYNTAX INTEGER 
        MAX-ACCESS read-write                
        STATUS current
        DESCRIPTION
            "If the value is 0, the Delimiter Process will be
            used, regardless of the length of the data
            packet. If the data length (in bytes) matches the
            configured value, the data will be forced out. The
            data length can be configured from 0 to 1024 bytes.
            Set to 0 if you do not need to limit the length."
        ::= { dataPackingPortEntry 1 }
        
    portDelimiter1Enable OBJECT-TYPE
		SYNTAX INTEGER {disable(0), enable(1)}
		MAX-ACCESS read-write                
		STATUS current
		DESCRIPTION
			"Enable the first delimiter character."
		::= { dataPackingPortEntry 2 }
	
	portDelimiter1 OBJECT-TYPE
		SYNTAX DisplayString (SIZE(0..2))
		MAX-ACCESS read-write                
		STATUS current
		DESCRIPTION
			"The first delimiter character, in hex decimal."
		::= { dataPackingPortEntry 3 }	
		
	portDelimiter2Enable OBJECT-TYPE
		SYNTAX INTEGER {disable(0), enable(1)}
		MAX-ACCESS read-write                
		STATUS current
		DESCRIPTION
			"Enable the second delimiter character."
		::= { dataPackingPortEntry 4 }
	
	portDelimiter2 OBJECT-TYPE
		SYNTAX DisplayString (SIZE(0..2))
		MAX-ACCESS read-write                
		STATUS current
		DESCRIPTION
			"The second delimiter character, in hex decimal."
		::= { dataPackingPortEntry 5 }	
	
	portDelimiterProcess OBJECT-TYPE
		SYNTAX INTEGER {
			doNothing(1), 
			delimiterAddOne(2),
			delimiterAddTwo(4),
			stripDelimiter(8)
			}
		MAX-ACCESS read-write                
		STATUS current
		DESCRIPTION
			"'delimiterAddOne' or 'delimiterAddTwo': The data
			will be transmitted when an additional byte (for
			'delimiterAddOne'), or an additional 2 bytes (for
			'delimiterAddTwo') of data is received after
			receiving the Delimiter.
			'stripDelimiter': When the delimiter is received,
			the Delimiter is deleted (i.e., stripped), and the
			remaining data is transmitted.
			'doNothing': The data will be transmitted when the
			delimiter is received."
		::= { dataPackingPortEntry 6 }
		
	portForceTransmit OBJECT-TYPE
		SYNTAX INTEGER
		MAX-ACCESS read-write                
		STATUS current
		DESCRIPTION
			"0: Disable the force transmit timeout.
			1 to 65535: Forces the NPort 6000 series device
			server's TCP/IP protocol software to try to pack
			serial data received during the specified time into
			the same data frame."
		::= { dataPackingPortEntry 7 }

-- -------------------------------------------------------------
-- Serial port settings -> Communication Parameters settings
-- -------------------------------------------------------------

	comParamSetting OBJECT IDENTIFIER ::= { portSetting 2 }
	
    comParamPortTable OBJECT-TYPE
        SYNTAX SEQUENCE OF ComParamPortEntry
        MAX-ACCESS not-accessible               
        STATUS current
        DESCRIPTION
            "The Communication Parameters table."
        ::= { comParamSetting 1 }
    
    comParamPortEntry OBJECT-TYPE
        SYNTAX ComParamPortEntry
        MAX-ACCESS not-accessible
        STATUS current
        DESCRIPTION
            "The Communication Parameters entry."
        INDEX { portIndex }
        ::= { comParamPortTable 1 }
        
    ComParamPortEntry ::=
        SEQUENCE {
            portAlias
                DisplayString,
            portInterface
            	INTEGER,
            portBaudRate
                INTEGER,
            portBaudRateManual
                INTEGER,
            portDataBits
                INTEGER,
            portStopBits
				INTEGER,
			portParity
				INTEGER,
			portFlowControl
				INTEGER,
			portFIFO
				INTEGER,
			portOnDelay
				INTEGER,
			portOffDelay
				INTEGER
        }
    
    portAlias OBJECT-TYPE
		SYNTAX DisplayString (SIZE(0..16))
		MAX-ACCESS read-write                
		STATUS current
		DESCRIPTION
		"Port alias is included to allow easy identification of
		the serial devices that are connected to NPort 6000
		series device server's serial port."
		::= { comParamPortEntry 1 }
        
    portInterface OBJECT-TYPE
		SYNTAX INTEGER  { 
			rs-232(0), 
			rs-422(1), 
			rs-485-2-wire(2),
			rs-485-4-wire(3) 
		}
		MAX-ACCESS read-write                
		STATUS current
		DESCRIPTION
			"The serial interface that the port works on."
		::= { comParamPortEntry 2 }
     
	portBaudRate OBJECT-TYPE
		SYNTAX INTEGER  { 
			b50(0), 
			b75(1), 
			b110(2),
			b134(3), 
			b150(4), 
			b300(5), 
			b600(6),
			b1200(7), 
			b1800(8),
			b2400(9), 
			b4800(10), 
			b7200(11), 
			b9600(12),
			b19200(13),
			b38400(14),
			b57600(15),
			b115200(16),
			b230400(17),
			b460800(18),
			b921600(19)
		}
		MAX-ACCESS read-write                
		STATUS current
		DESCRIPTION
			"The port's speed in bits per second. You can choose
			a standard baud rate by indexing."
		::= { comParamPortEntry 3 }   
		
	portBaudRateManual OBJECT-TYPE
        SYNTAX INTEGER (50..921600)
        MAX-ACCESS read-write                
        STATUS current
        DESCRIPTION
            "The port's speed in bits per second. You can
            specify a baud rate manually."
        ::= { comParamPortEntry 4 }
        
    portDataBits OBJECT-TYPE
		SYNTAX INTEGER  { 
			bits-5(0), 
			bits-6(1), 
			bits-7(2),
			bits-8(3) 
		}
		MAX-ACCESS read-write
		STATUS current
		DESCRIPTION
			"The number of bits in a character for the port."
		::= { comParamPortEntry 5 }
		
	portStopBits OBJECT-TYPE
		SYNTAX INTEGER  {
			bits-1(0),
			bits-1dot5(1),
			bits-2(2)
		}
		MAX-ACCESS read-write
		STATUS current
		DESCRIPTION
			"The number of stop bits for the port."
		::= { comParamPortEntry 6 }
		
	portParity OBJECT-TYPE
		SYNTAX INTEGER  { 
			none(0), 
			odd(1), 
			even(2),
			mark(3), 
			space(4)
		}
		MAX-ACCESS read-write                
		STATUS current
		DESCRIPTION
			"The parity bit for the port."
		::= { comParamPortEntry 7 }
				
	portFlowControl OBJECT-TYPE
		SYNTAX INTEGER  { 
			none(0),
			rts-cts(1),
			xon-xoff(2),
			dtr-dsr(3),
			rts-toggle(4)
		}
		MAX-ACCESS read-write                
		STATUS current
		DESCRIPTION
			"The flow-control method for the port."
		::= { comParamPortEntry 8 }
		
	portFIFO OBJECT-TYPE
		SYNTAX INTEGER  { 
			disable(0), 
			enable(1)
		}
		MAX-ACCESS read-write                
		STATUS current
		DESCRIPTION
			"Enable or disable the port's FIFO."
		::= { comParamPortEntry 9 }

	portOnDelay OBJECT-TYPE
        SYNTAX INTEGER 
        MAX-ACCESS read-write                
        STATUS current
        DESCRIPTION
            "The port's RTS toggle On delay time (ms)."
        ::= { comParamPortEntry 10 }

	portOffDelay OBJECT-TYPE
        SYNTAX INTEGER 
        MAX-ACCESS read-write                
        STATUS current
        DESCRIPTION
            "The port's RTS toggle Off delay time (ms)."
        ::= { comParamPortEntry 11 }

-- --------------------------------------------------------------------------------------
-- Serial port settings -> Data Buffering/Log 
-- --------------------------------------------------------------------------------------

	dataBuffering OBJECT IDENTIFIER ::= { portSetting 3 }
	
	dataBufferingPortTable OBJECT-TYPE
        SYNTAX SEQUENCE OF DataBufferingPortEntry
        MAX-ACCESS not-accessible               
        STATUS current
        DESCRIPTION
            "The Data Buffering/Log table."
        ::= { dataBuffering 1 }
    
    dataBufferingPortEntry OBJECT-TYPE
        SYNTAX DataBufferingPortEntry
        MAX-ACCESS not-accessible               
        STATUS current
        DESCRIPTION
            "The Data Buffering/Log entry."
        INDEX { portIndex }
        ::= { dataBufferingPortTable 1 }
        
    DataBufferingPortEntry ::=
        SEQUENCE {
            portBufferingEnable
                INTEGER,
            portBufferingLocation
                INTEGER,
            portBufferingSDFileSize
                INTEGER,
            portSerialDataLoggingEnable
            	INTEGER
        }
        
	portBufferingEnable OBJECT-TYPE
		SYNTAX INTEGER {disable(0), enable(1)}
		MAX-ACCESS read-write                
		STATUS current
		DESCRIPTION
			"Enable off-line port buffering."
		::= { dataBufferingPortEntry 1 }
        
	portBufferingLocation OBJECT-TYPE
		SYNTAX INTEGER {memory(0), sdCard(1)}
		MAX-ACCESS read-write                
		STATUS current
		DESCRIPTION
			"The location of off-line port buffering.
       Note: NPort 6150 can not be set as sdCard."
		::= { dataBufferingPortEntry 2 }
		
	portBufferingSDFileSize OBJECT-TYPE
		SYNTAX INTEGER
		MAX-ACCESS read-write                
		STATUS current
		DESCRIPTION
			"The maximum file size of off-line port buffering,
			in MBytes, if the location is set to 'sdCard.'
			Note: NPort 6150 do not support write access."
		::= { dataBufferingPortEntry 3 }
		
	portSerialDataLoggingEnable OBJECT-TYPE
		SYNTAX INTEGER {disable(0), enable(1)}
		MAX-ACCESS read-write                
		STATUS current
		DESCRIPTION
			"Enable or disable serial data logging for the port."
		::= { dataBufferingPortEntry 4 }

-- --------------------------------------------------------------------------------------
-- Serial port settings -> Modem Settings
-- --------------------------------------------------------------------------------------
		
	modemSettings OBJECT IDENTIFIER ::= { portSetting 4 }
	
	modemSettingsPortTable OBJECT-TYPE
        SYNTAX SEQUENCE OF ModemSettingsPortEntry
        MAX-ACCESS not-accessible               
        STATUS current
        DESCRIPTION
            "The Modem Settings table."
        ::= { modemSettings 1 }
    
    modemSettingsPortEntry OBJECT-TYPE
        SYNTAX ModemSettingsPortEntry
        MAX-ACCESS not-accessible               
        STATUS current
        DESCRIPTION
            "The Modem Settings entry."
        INDEX { portIndex }
        ::= { modemSettingsPortTable 1 }
        
    ModemSettingsPortEntry ::=
        SEQUENCE {
            portEnableModem
				INTEGER,
			portInitialString
				DisplayString,
			portDialUp
				DisplayString,
			portPhoneNumber
				DisplayString
        }
        
	portEnableModem OBJECT-TYPE
		SYNTAX INTEGER  { disable(0), enable(1) }
		MAX-ACCESS read-write                
		STATUS current
		DESCRIPTION
			"Enable or disable modem for this port."
		::= { modemSettingsPortEntry 1 }
		
	portInitialString OBJECT-TYPE
		SYNTAX DisplayString (SIZE(0..24))
		MAX-ACCESS read-write                
		STATUS current
		DESCRIPTION
		"Set the modem's initial string to establish the
		connection. E.g., 'AT&S0=1' for auto-answer."
		::= { modemSettingsPortEntry 2 }
		
	portDialUp OBJECT-TYPE
		SYNTAX DisplayString (SIZE(0..8))
		MAX-ACCESS read-write                
		STATUS current
		DESCRIPTION
		"Set the modem's dial-up AT command string."
		::= { modemSettingsPortEntry 3 }
	
	portPhoneNumber OBJECT-TYPE
		SYNTAX DisplayString (SIZE(0..16))
		MAX-ACCESS read-write                
		STATUS current
		DESCRIPTION
		"Set the number used to dial out."
		::= { modemSettingsPortEntry 4 }

-- --------------------------------------------------------------------------------------
-- Serial port settings -> Cipher Sorting
-- --------------------------------------------------------------------------------------
		
	cipherSettings OBJECT IDENTIFIER ::= { portSetting 5 }
	
	cipherSettingsPortTable OBJECT-TYPE
        SYNTAX SEQUENCE OF CipherSettingsPortEntry
        MAX-ACCESS not-accessible               
        STATUS current
        DESCRIPTION
            "The Cipher Settings table."
        ::= { cipherSettings 1 }
    
    cipherSettingsPortEntry OBJECT-TYPE
        SYNTAX CipherSettingsPortEntry
        MAX-ACCESS not-accessible               
        STATUS current
        DESCRIPTION
            "The Cipher Settings entry."
        INDEX { portIndex }
        ::= { cipherSettingsPortTable 1 }
        
    CipherSettingsPortEntry ::=
        SEQUENCE {
			sslCipherSort
				DisplayString,
			sshCipherSort
				DisplayString
        }
        
	sslCipherSort OBJECT-TYPE
		SYNTAX DisplayString (SIZE(53..53))
		MAX-ACCESS read-write                
		STATUS current
		DESCRIPTION
			"SSL cipher sorting. The format is '2,0,1,3,5,6,8,9,4,7' for example.
             The index mapping of each cipher method is shown blow. EDH-RSA-DES-CBC3-SHA(2) has
             the highest priority in this example.
				DHE-RSA-AES256-SHA(0),
				AES256-SHA(1),
				EDH-RSA-DES-CBC3-SHA(2),
				DES-CBC3-SHA(3),
				DES-CBC3-MD5(SSL2)(4),
				DHE-RSA-AES128-SHA(5),
				AES128-SHA(6),
				RC4-SHA(7),
				RC4-MD5(8),
				EDH-RSA-DES-CBC-SHA(9),
				DES-CBC-SHA(10),
				DES-CBC-MD5(SSL2)(11)"
		::= { cipherSettingsPortEntry 1 }
		
	sshCipherSort OBJECT-TYPE
		SYNTAX DisplayString (SIZE(16..16))
		MAX-ACCESS read-write                
		STATUS current
		DESCRIPTION
			"SSL cipher sorting. The format is '2,0,1,3,5,4,6,7' for example.
             The index mapping of each cipher method is shown blow. aes192-cbc(2) has
             the highest priority in this example.
				aes128-cbc(0),
				3dec-cbc(1),
				aes192-cbc(2),
				aes256-cbc(3),
				twofish256-cbc(4),
				twofish-cbc(5),
				twofish128-cbc(6),
				blowfish-cbc(7)"
		::= { cipherSettingsPortEntry 2 }	

-- --------------------------------------------------------------------------------------
-- Serial port settings -> Welcome Message
-- --------------------------------------------------------------------------------------
	
	welcomeMessage OBJECT IDENTIFIER ::= { portSetting 6 }
	
	portEnableWelcomeMessage OBJECT-TYPE
		SYNTAX INTEGER  { disable(0), enable(1) }
		MAX-ACCESS read-write                
		STATUS current
		DESCRIPTION
			"Enable or disable the welcome message."
		::= { welcomeMessage 1 }
		
	portMessage OBJECT-TYPE
		SYNTAX DisplayString (SIZE(0..1280))
		MAX-ACCESS read-write                
		STATUS current
		DESCRIPTION
		"Set up a welcome message to greet dial-in users."
		::= { welcomeMessage 2 }
        
-- -------------------------------------------------------------
-- System Management
-- -------------------------------------------------------------

	sysManagement OBJECT IDENTIFIER ::= { swMgmt 5 }
	
-- -------------------------------------------------------------
-- System Management -> Misc. Network Settings
-- -------------------------------------------------------------

	miscNetworkSettings OBJECT IDENTIFIER ::= { sysManagement 1 }
	
-- ----------------------------------------------------------------------------
-- System Management -> Misc. Network Settings -> Accessible IP List
-- ----------------------------------------------------------------------------

	accessibleIp OBJECT IDENTIFIER ::= { miscNetworkSettings 1 }
	
	enableAccessibleIpList  OBJECT-TYPE
        SYNTAX INTEGER { disable(0), enable(1)}
        MAX-ACCESS read-write               
        STATUS current
        DESCRIPTION
            "Enable or disable the entire accessible IP list."
		::= { accessibleIp 1 }
	
	accessibleIpListTable OBJECT-TYPE
        SYNTAX SEQUENCE OF AccessibleIpListEntry
        MAX-ACCESS not-accessible               
        STATUS current
        DESCRIPTION
            "Accessible IP List table."
        ::= { accessibleIp 2 }
    
    accessibleIpListEntry OBJECT-TYPE
        SYNTAX AccessibleIpListEntry
        MAX-ACCESS not-accessible
        STATUS current
        DESCRIPTION
            "Accessible IP List entry."
        INDEX { accessibleIpListIndex }
        ::= { accessibleIpListTable 1 }
        
    AccessibleIpListEntry ::=
        SEQUENCE {
        	accessibleIpListIndex
       			INTEGER,
            activeAccessibleIpList
            	INTEGER,
            accessibleIpListAddress
                DisplayString,
            accessibleIpListNetmask
                DisplayString
        }
	
	accessibleIpListIndex OBJECT-TYPE
        SYNTAX INTEGER
        MAX-ACCESS read-only                
        STATUS current
        DESCRIPTION
            "Accessible IP List index."
        ::= { accessibleIpListEntry 1 }
		
	activeAccessibleIpList  OBJECT-TYPE
        SYNTAX INTEGER { disable(0), enable(1)}
        MAX-ACCESS read-write               
        STATUS current
        DESCRIPTION
            "Enable or disable this accessible IP entry."
		::= { accessibleIpListEntry 2 }
		
	accessibleIpListAddress  OBJECT-TYPE
        SYNTAX DisplayString (SIZE(0..40))
        MAX-ACCESS read-write
        STATUS current
        DESCRIPTION
            "Accessible IP address. This value can be the IP address of a
	    single host if the netmask is set to '255.255.255.255,'
            or it can be a network address."
		::= { accessibleIpListEntry 3 }
		
	accessibleIpListNetmask  OBJECT-TYPE
        SYNTAX DisplayString (SIZE(0..15))
        MAX-ACCESS read-write
        STATUS current
        DESCRIPTION
            "Accessible IP address netmask. The IP address and
            netmask are used to specify a group of remote hosts."
		::= { accessibleIpListEntry 4 }
	
-- ----------------------------------------------------------------------------
-- System Management -> Misc. Network Settings -> SNMP Agent Settings
-- ----------------------------------------------------------------------------

	snmpAgentSettings OBJECT IDENTIFIER ::= { miscNetworkSettings 2 }
	
	snmpEnable  OBJECT-TYPE
        SYNTAX INTEGER { disable(0), enable(1)}
        MAX-ACCESS read-write               
        STATUS current
        DESCRIPTION
            "Enable or disable SNMP agent."
		::= { snmpAgentSettings 1 }
    
	snmpContactName OBJECT-TYPE
        SYNTAX DisplayString (SIZE(0..40))
        MAX-ACCESS read-write
        STATUS current
        DESCRIPTION
            "The SNMP contact information usually includes an
            emergency contact name and telephone or pager
            number."
        ::= { snmpAgentSettings 2 }
        
    snmpLocation OBJECT-TYPE
        SYNTAX DisplayString (SIZE(0..40))
        MAX-ACCESS read-write
        STATUS current
        DESCRIPTION
            "Specify the location string for SNMP agents, such as
            the NPort 6000 series device server. This string is
            usually set to the street address where the NPort
            6000 series device server is physically located."
        ::= { snmpAgentSettings 3 }
        
-- ----------------------------------------------------------------------------
-- System Management -> Misc. Network Settings -> DDNS Settings
-- ----------------------------------------------------------------------------

	dDNS OBJECT IDENTIFIER ::= { miscNetworkSettings 3 }
	
	dDNSEnable  OBJECT-TYPE
        SYNTAX INTEGER {disable(0), enable(1)}
        MAX-ACCESS read-write               
        STATUS current
        DESCRIPTION
            "Enable or disable the DDNS function."
		::= { dDNS 1 }
		
	dDNSServerAddress  OBJECT-TYPE
        SYNTAX INTEGER { dynDns-org(0) }
        MAX-ACCESS read-write               
        STATUS current
        DESCRIPTION
            "The DDNS server address. The DDNS is serviced by a
            3-party provider. To use the DDNS function, you may
            need to obtain a user account from the server."
		::= { dDNS 2 }
		
	dDNSHostName  OBJECT-TYPE
        SYNTAX DisplayString (SIZE(0..60))
        MAX-ACCESS read-write               
        STATUS current
        DESCRIPTION
            "The host name of the machine to be registered to
            the DDNS server."
		::= { dDNS 3 }
		
	dDNSUserName  OBJECT-TYPE
        SYNTAX DisplayString (SIZE(0..60))
        MAX-ACCESS read-write               
        STATUS current
        DESCRIPTION
            "The user account provided by the DDNS server."
		::= { dDNS 4 }
		
	dDNSPassword  OBJECT-TYPE
        SYNTAX DisplayString (SIZE(0..60))
        MAX-ACCESS read-write               
        STATUS current
        DESCRIPTION
            "The user password provided by the DDNS server."
		::= { dDNS 5 }
		
-- ----------------------------------------------------------------------------
-- System Management -> Misc. Network Settings -> Host Table
-- ----------------------------------------------------------------------------

	hostTable OBJECT IDENTIFIER ::= { miscNetworkSettings 4 }
	
	hostTableTable OBJECT-TYPE
        SYNTAX SEQUENCE OF HostTableEntry
        MAX-ACCESS not-accessible               
        STATUS current
        DESCRIPTION
            "Host Table."
        ::= { hostTable 1 }
    
    hostTableEntry OBJECT-TYPE
        SYNTAX HostTableEntry
        MAX-ACCESS not-accessible
        STATUS current
        DESCRIPTION
            "Host Table entry."
        INDEX { hostTableIndex }
        ::= { hostTableTable 1 }
        
    HostTableEntry ::=
        SEQUENCE {
        	hostTableIndex
        		INTEGER,
            hostName
                DisplayString,
            hostIpAddress
            	DisplayString
        }
       
	hostTableIndex OBJECT-TYPE
        SYNTAX INTEGER
        MAX-ACCESS read-only                
        STATUS current
        DESCRIPTION
            "The Host Table index."
        ::= { hostTableEntry 1 } 
    
	hostName  OBJECT-TYPE
        SYNTAX DisplayString (SIZE(0..16))
        MAX-ACCESS read-write               
        STATUS current
        DESCRIPTION
            "The host name of the host table entry."
		::= { hostTableEntry 2 }
		
	hostIpAddress  OBJECT-TYPE
        SYNTAX DisplayString (SIZE(0..40))
        MAX-ACCESS read-write
        STATUS current
        DESCRIPTION
            "Related IP address of the host table entry."
		::= { hostTableEntry 3 }
		
-- ----------------------------------------------------------------------------
-- System Management -> Misc. Network Settings -> Route Table
-- ----------------------------------------------------------------------------

	routeTable OBJECT IDENTIFIER ::= { miscNetworkSettings 5 }
	
	routeTableTable OBJECT-TYPE
        SYNTAX SEQUENCE OF RouteTableEntry
        MAX-ACCESS not-accessible               
        STATUS current
        DESCRIPTION
            "Route Table."
        ::= { routeTable 1 }
    
    routeTableEntry OBJECT-TYPE
        SYNTAX RouteTableEntry
        MAX-ACCESS not-accessible
        STATUS current
        DESCRIPTION
            "Route Table entry."
        INDEX { routeTableIndex }
        ::= { routeTableTable 1 }
        
    RouteTableEntry ::=
        SEQUENCE {
        	routeTableIndex
        		INTEGER,
            gatewayRouteTable
                IpAddress,
            destinationRouteTable
            	IpAddress,
            netmaskRouteTable
            	IpAddress,
            metricRouteTable
            	INTEGER,
            interfaceRouteTable
            	INTEGER	
        }
		
	routeTableIndex OBJECT-TYPE
        SYNTAX INTEGER
        MAX-ACCESS read-only                
        STATUS current
        DESCRIPTION
            "The Route Table index."
        ::= { routeTableEntry 1 } 
	
	gatewayRouteTable  OBJECT-TYPE
        SYNTAX IpAddress
        MAX-ACCESS read-write
        STATUS current
        DESCRIPTION
            "The gateway property of the route table entry."
		::= { routeTableEntry 2 }
		
	destinationRouteTable  OBJECT-TYPE
        SYNTAX IpAddress
        MAX-ACCESS read-write
        STATUS current
        DESCRIPTION
            "The destination IP address of the route table entry.
            This value can be the IP address of a single host if
	    the netmask set to
            '255.255.255.255,' or it can be a network address."
		::= { routeTableEntry 3 }
		
	netmaskRouteTable  OBJECT-TYPE
        SYNTAX IpAddress
        MAX-ACCESS read-write
        STATUS current
        DESCRIPTION
            "The destination netmask of the route table entry."
		::= { routeTableEntry 4 }
	
	metricRouteTable  OBJECT-TYPE
        SYNTAX INTEGER
        MAX-ACCESS read-write
        STATUS current
        DESCRIPTION
            "The routing metric for this route. The semantics of
            this metric are determined by the routing-protocol.
            Normally, it represents the cost for the destination."
		::= { routeTableEntry 5 }
		
	interfaceRouteTable  OBJECT-TYPE
        SYNTAX INTEGER {
        	port1(0),
        	port2(1),
        	port3(2),
        	port4(3),
        	port5(4),
        	port6(5),
        	port7(6),
        	port8(7),
        	port9(8),
        	port10(9),
        	port11(10),
        	port12(11),
        	port13(12),
        	port14(13),
        	port15(14),
        	port16(15),
        	port17(16),
        	port18(17),
        	port19(18),
        	port20(19),
        	port21(20),
        	port22(21),
        	port23(22),
        	port24(23),
        	port25(24),
        	port26(25),
        	port27(26),
        	port28(27),
        	port29(28),
        	port30(29),
        	port31(30),
        	port32(31),
        	lan(256)
        }
        MAX-ACCESS read-write
        STATUS current
        DESCRIPTION
            "The value that identifies the local interface
            through which the next hop of this route should be
            reached."
		::= { routeTableEntry 6 }
	
-- ----------------------------------------------------------------------------
-- System Management -> Misc. Network Settings -> User Table
-- ----------------------------------------------------------------------------

	userTable OBJECT IDENTIFIER ::= { miscNetworkSettings 6 }
	
	userTableTable OBJECT-TYPE
        SYNTAX SEQUENCE OF UserTableEntry
        MAX-ACCESS not-accessible               
        STATUS current
        DESCRIPTION
            "User Table."
        ::= { userTable 1 }
    
    userTableEntry OBJECT-TYPE
        SYNTAX UserTableEntry
        MAX-ACCESS not-accessible
        STATUS current
        DESCRIPTION
            "User Table entry."
        INDEX { userTableIndex }
        ::= { userTableTable 1 }
        
    UserTableEntry ::=
        SEQUENCE {
        	userTableIndex
        		INTEGER,
            userNameUserTable
                DisplayString,
            passwordUserTable
            	DisplayString,
            phoneNumberUserTable
            	DisplayString
        }
    
    userTableIndex OBJECT-TYPE
        SYNTAX INTEGER
        MAX-ACCESS read-only                
        STATUS current
        DESCRIPTION
            "The User Table index."
        ::= { userTableEntry 1 } 
        
	userNameUserTable  OBJECT-TYPE
        SYNTAX DisplayString (SIZE(0..16))
        MAX-ACCESS read-write               
        STATUS current
        DESCRIPTION
            "The user name of this entry."
		::= { userTableEntry 2 }
		
	passwordUserTable  OBJECT-TYPE
        SYNTAX DisplayString (SIZE(0..16))
        MAX-ACCESS read-write               
        STATUS current
        DESCRIPTION
            "The password of this user entry."
		::= { userTableEntry 3 }
		
	phoneNumberUserTable  OBJECT-TYPE
        SYNTAX DisplayString (SIZE(0..16))
        MAX-ACCESS read-write               
        STATUS current
        DESCRIPTION
            "The phone number of this user entry."
		::= { userTableEntry 4 }
		
-- ----------------------------------------------------------------------------
-- System Management -> Misc. Network Settings -> Authentication Server
-- ----------------------------------------------------------------------------

	authenticationServer OBJECT IDENTIFIER ::= { miscNetworkSettings 7 }
	
	radiusServerIp  OBJECT-TYPE
        SYNTAX DisplayString (SIZE(0..40))
        MAX-ACCESS read-write               
        STATUS current
        DESCRIPTION
            "The IP address or domain name of the RADIUS server."
		::= { authenticationServer 1 }
		
	radiusKey  OBJECT-TYPE
        SYNTAX DisplayString (SIZE(0..16))
        MAX-ACCESS read-write               
        STATUS current
        DESCRIPTION
            "RADIUS password. Must be the same as in the RADIUS
            server."
		::= { authenticationServer 2 }
		
	udpPortAuthenticationServer  OBJECT-TYPE
        SYNTAX INTEGER { port1645(1645), port1812(1812)}
        MAX-ACCESS read-write               
        STATUS current
        DESCRIPTION
            "The UDP port of the RADIUS server."
		::= { authenticationServer 3 }
		
	radiusAccounting  OBJECT-TYPE
        SYNTAX INTEGER { disable(0), enable(1)}
        MAX-ACCESS read-write               
        STATUS current
        DESCRIPTION
            "Enable or disable RADIUS accounting."
		::= { authenticationServer 4 }	
	
	tacacsPlusServerIp  OBJECT-TYPE
        SYNTAX DisplayString (SIZE(0..40))
        MAX-ACCESS read-write               
        STATUS current
        DESCRIPTION
            "The IP address or domain name of the TACACS+ server."
		::= { authenticationServer 5 }
		
	tacacsPlusSecret  OBJECT-TYPE
        SYNTAX DisplayString (SIZE(0..16))
        MAX-ACCESS read-write               
        STATUS current
        DESCRIPTION
            "TACACS+ shared secret. Must be the same as in the TACACS+
            server."
		::= { authenticationServer 6 }
	
	tacacsPlusAccounting  OBJECT-TYPE
        SYNTAX INTEGER { disable(0), enable(1)}
        MAX-ACCESS read-write               
        STATUS current
        DESCRIPTION
            "Enable or disable TACACS+ accounting."
		::= { authenticationServer 7 }
		
-- ----------------------------------------------------------------------------
-- System Management -> Misc. Network Settings -> System Log Settings
-- ----------------------------------------------------------------------------

	sysLogSettings OBJECT IDENTIFIER ::= { miscNetworkSettings 8 }
	
	sysLocalLog  OBJECT-TYPE
        SYNTAX INTEGER { disable(0), enable(1)}
        MAX-ACCESS read-write               
        STATUS current
        DESCRIPTION
            "Log the following events to the system log: System Cold
            Start, System Warm Start."
		::= { sysLogSettings 1 }
		
	networkLocalLog  OBJECT-TYPE
        SYNTAX INTEGER { disable(0), enable(1)}
        MAX-ACCESS read-write               
        STATUS current
        DESCRIPTION
            "Log the following events to the system log:
            DHCP/BOOTP/PPPoE Get IP/Renew, NTP, Mail Fail, NTP
            Connect Fail, DHCP Fail, IP Conflict, Ethernet Link
            Down."
		::= { sysLogSettings 2 }
		
	configLocalLog  OBJECT-TYPE
        SYNTAX INTEGER { disable(0), enable(1)}
        MAX-ACCESS read-write               
        STATUS current
        DESCRIPTION
            "Log the following events to the system log: Login Fail, IP
            Changed, Password Changed, Config Changed, Firmware
            Upgrade, SSL Key Import, Config Import, Config
            Export."
		::= { sysLogSettings 3 }
		
	opModeLocalLog  OBJECT-TYPE
        SYNTAX INTEGER { disable(0), enable(1)}
        MAX-ACCESS read-write               
        STATUS current
        DESCRIPTION
            "Log the following op-mode events to the system log:
            Connect, Disconnect, Authentication Fail, Restart."
		::= { sysLogSettings 4 }
	
	sysRemoteLog  OBJECT-TYPE
        SYNTAX INTEGER { disable(0), enable(1)}
        MAX-ACCESS read-write               
        STATUS current
        DESCRIPTION
            "Log the following events to the remote log server: System Cold
            Start, System Warm Start."
		::= { sysLogSettings 5 }
		
	networkRemoteLog  OBJECT-TYPE
        SYNTAX INTEGER { disable(0), enable(1)}
        MAX-ACCESS read-write               
        STATUS current
        DESCRIPTION
            "Log the following events to the remote log server:
            DHCP/BOOTP/PPPoE Get IP/Renew, NTP, Mail Fail, NTP
            Connect Fail, DHCP Fail, IP Conflict, Ethernet Link
            Down."
		::= { sysLogSettings 6 }
		
	configRemoteLog  OBJECT-TYPE
        SYNTAX INTEGER { disable(0), enable(1)}
        MAX-ACCESS read-write               
        STATUS current
        DESCRIPTION
            "Log the following events to the remote log server: Login Fail, IP
            Changed, Password Changed, Config Changed, Firmware
            Upgrade, SSL Key Import, Config Import, Config
            Export."
		::= { sysLogSettings 7 }
		
	opModeRemoteLog  OBJECT-TYPE
        SYNTAX INTEGER { disable(0), enable(1)}
        MAX-ACCESS read-write               
        STATUS current
        DESCRIPTION
            "Log the following op-mode events to the remote log server:
            Connect, Disconnect, Authentication Fail, Restart."
		::= { sysLogSettings 8 }	

-- ----------------------------------------------------------------------------
-- System Management -> Misc. Network Settings -> Remote Log Server
-- ----------------------------------------------------------------------------

	remoteLogServer OBJECT IDENTIFIER ::= { miscNetworkSettings 9 }
	
	syslogServerIp  OBJECT-TYPE
        SYNTAX DisplayString (SIZE(0..40))
        MAX-ACCESS read-write               
        STATUS current
        DESCRIPTION
            "The IP address or domain name of the SYSLOG server."
		::= { remoteLogServer 1 }

	syslogFacility  OBJECT-TYPE
        SYNTAX INTEGER { local-use-0(0), local-use-1(1), local-use-2(2), local-use-3(3), local-use-4(4), local-use-5(5), local-use-6(6), local-use-7(7)}
        MAX-ACCESS read-write               
        STATUS current
        DESCRIPTION
            "The SYSLOG facility level."
		::= { remoteLogServer 2 }
		
	syslogSeverity  OBJECT-TYPE
        SYNTAX INTEGER { emergency(0), alert(1), critical(2), error(3), warning(4), notice(5), informational(6), debug(7)}
        MAX-ACCESS read-write               
        STATUS current
        DESCRIPTION
            "The SYSLOG severity level."
		::= { remoteLogServer 3 }
	
-- -------------------------------------------------------------
-- System Management -> Auto Warning Settings
-- -------------------------------------------------------------

	autoWarningSettings OBJECT IDENTIFIER ::= { sysManagement 2 }
		
-- -------------------------------------------------------------
-- System Management -> Auto Warning Settings -> Event Settings
-- -------------------------------------------------------------

	eventSettings OBJECT IDENTIFIER ::= { autoWarningSettings 1 }
	
	mailWarningColdStart OBJECT-TYPE
        SYNTAX INTEGER  { disable(0), enable(1) }
        MAX-ACCESS read-write
        STATUS current
        DESCRIPTION
            "Refers to starting the system from power off
            (contrast this with warm start). When performing a
            cold start, the NPort 6000 series device server will
            automatically issue an auto warning message by
            e-mail after booting up."
        ::= { eventSettings 1 }
        
    mailWarningWarmStart OBJECT-TYPE
        SYNTAX INTEGER  { disable(0), enable(1) }
        MAX-ACCESS read-write
        STATUS current
        DESCRIPTION
            "Refers to restarting the NPort 6000 without
            turning the power off. When performing a warm start,
            the NPort 6000 series device server will
            automatically send an e-mail after rebooting."
        ::= { eventSettings 2 }
        
    mailWarningAuthFailure OBJECT-TYPE
        SYNTAX INTEGER  { disable(0), enable(1) }
        MAX-ACCESS read-write
        STATUS current
        DESCRIPTION
            "The user inputs a wrong password from the Console
            or Administrator. When authentication failure
            occurs, the NPort 6000 series device server will
            immediately send an e-mail."
        ::= { eventSettings 3 }
        
    mailWarningIpChanged OBJECT-TYPE
        SYNTAX INTEGER  { disable(0), enable(1) }
        MAX-ACCESS read-write
        STATUS current
        DESCRIPTION
            "The user has changed the NPort 6000 series device
            server's IP address. When the IP address changes,
            the NPort 6000 series device server will send an
            e-mail with the new IP address before it reboots.
            If the NPort 6000 series device server is unable to
            send an e-mail message to the mail server within 15
            seconds, it will reboot anyway, and abort the e-mail
            auto warning."
        ::= { eventSettings 4 }
        
    mailWarningPasswordChanged OBJECT-TYPE
        SYNTAX INTEGER  { disable(0), enable(1) }
        MAX-ACCESS read-write
        STATUS current
        DESCRIPTION
            "The user has changed the NPort 6000 series device
            server's password. When the password changes, the
            NPort 6000 series device server will send an e-mail
            with the password changed notice before it reboots.
            If the NPort 6000 series device server is unable to
            send an e-mail message to the mail server within 15
            seconds, it will reboot anyway, and abort the e-mail
            auto warning."
        ::= { eventSettings 5 }
		
	trapServerColdStart OBJECT-TYPE
        SYNTAX INTEGER  { disable(0), enable(1) }
        MAX-ACCESS read-write
        STATUS current
        DESCRIPTION
            "Refers to starting the system from power off
            (contrast this with warm start). When performing a
            cold start, the NPort 6000 series device server will
            automatically issue an auto warning message by sending
            an SNMP trap after booting up."
        ::= { eventSettings 6 }
        
    trapServerWarmStart OBJECT-TYPE
        SYNTAX INTEGER  { disable(0), enable(1) }
        MAX-ACCESS read-write
        STATUS current
        DESCRIPTION
            "Refers to restarting the NPort 6000 without
            turning the power off. When performing a warm start,
            the NPort 6000 series device server will
            automatically send an SNMP trap after rebooting."
        ::= { eventSettings 7 }
        
    trapServerAuthFailure OBJECT-TYPE
        SYNTAX INTEGER  { disable(0), enable(1) }
        MAX-ACCESS read-write
        STATUS current
        DESCRIPTION
            "The user inputs a wrong password from the Console
            or Administrator. When authentication failure
            occurs, the NPort 6000 series device server will
            immediately send an SNMP trap."
        ::= { eventSettings 8 }
        
    alarmServerEthernet1LinkDown OBJECT-TYPE
        SYNTAX INTEGER  { disable(0), enable(1) }
        MAX-ACCESS read-write
        STATUS current
        DESCRIPTION
            "When the built-in link1 port is off, the NPort 6000
            series device server will automatically raise a
            d-out alarm.
            Note: NPort 6150, 6250, 6250-S-SC, 6250-M-SC 
            do not support write access."
        ::= { eventSettings 9 }
        
    alarmServerEthernet2LinkDown OBJECT-TYPE
        SYNTAX INTEGER  { disable(0), enable(1) }
        MAX-ACCESS read-write
        STATUS current
        DESCRIPTION
            "The 
            
            
            
             6000 series device server can provide an
            extra Ethernet port via the network module. When the
            first port on the network module is off, the NPort 6000
            series device server will automatically raise a
            d-out alarm.
            Note: NPort 6150, 6250, 6250-S-SC, 6250-M-SC 
            do not support write access."
        ::= { eventSettings 10 }
    
    alarmServerEthernet3LinkDown OBJECT-TYPE
        SYNTAX INTEGER  { disable(0), enable(1) }
        MAX-ACCESS read-write
        STATUS current
        DESCRIPTION
            "The NPort 6000 series device server can provide an
            extra Ethernet port via the network module. When the
            second port on the network module is off, the NPort 6000
            series device server will automatically raise a
            d-out alarm.
            Note: NPort 6150, 6250, 6250-S-SC, 6250-M-SC 
            do not support write access."
        ::= { eventSettings 11 }
        
	smsServerColdStart OBJECT-TYPE
        SYNTAX INTEGER  { disable(0), enable(1) }
        MAX-ACCESS read-write
        STATUS current
        DESCRIPTION
            "Refers to starting the system from power off
            (contrast this with warm start). When performing a
            cold start, the NPort 6000 series device server will
            automatically issue an auto warning message by
            SMS after booting up.
            Note: NPort 6150, 6250, 6250-S-SC, 6250-M-SC 
            do not support write access."
        ::= { eventSettings 12 }
        
    smsServerWarmStart OBJECT-TYPE
        SYNTAX INTEGER  { disable(0), enable(1) }
        MAX-ACCESS read-write
        STATUS current
        DESCRIPTION
            "Refers to restarting the NPort 6000 without
            turning the power off. When performing a warm start,
            the NPort 6000 series device server will
            automatically send a SMS after rebooting.
            Note: NPort 6150, 6250, 6250-S-SC, 6250-M-SC 
            do not support write access."
        ::= { eventSettings 13 }  
        
    smsServerEthernet1LinkDown OBJECT-TYPE
        SYNTAX INTEGER  { disable(0), enable(1) }
        MAX-ACCESS read-write
        STATUS current
        DESCRIPTION
            "When the built-in link1 port is off, the NPort 6000
            series device server will automatically send a
            SMS alarm.
            Note: NPort 6150, 6250, 6250-S-SC, 6250-M-SC 
            do not support write access."
        ::= { eventSettings 14 }
        
    smsServerEthernet2LinkDown OBJECT-TYPE
        SYNTAX INTEGER  { disable(0), enable(1) }
        MAX-ACCESS read-write
        STATUS current
        DESCRIPTION
            "The NPort 6000 series device server can provide an
            extra Ethernet port via the network module. When the
            first port on the network module is off, the NPort 6000
            series device server will automatically send a
            SMS alarm.
            Note: NPort 6150, 6250, 6250-S-SC, 6250-M-SC 
            do not support write access."
        ::= { eventSettings 15 }
    
    smsServerEthernet3LinkDown OBJECT-TYPE
        SYNTAX INTEGER  { disable(0), enable(1) }
        MAX-ACCESS read-write
        STATUS current
        DESCRIPTION
            "The NPort 6000 series device server can provide an
            extra Ethernet port via the network module. When the
            second port on the network module is off, the NPort 6000
            series device server will automatically send a
            SMS alarm.
            Note: NPort 6150, 6250, 6250-S-SC, 6250-M-SC 
            do not support write access."
        ::= { eventSettings 16 }
	
    smsServerAuthFailure OBJECT-TYPE
        SYNTAX INTEGER  { disable(0), enable(1) }
        MAX-ACCESS read-write
        STATUS current
        DESCRIPTION
            "The user inputs a wrong password from the Console
            or Administrator. When authentication failure
            occurs, the NPort 6000 series device server will
            immediately send a SMS.
            Note: NPort 6150, 6250, 6250-S-SC, 6250-M-SC 
            do not support write access."
        ::= { eventSettings 17 }
        
    smsServerIpChanged OBJECT-TYPE
        SYNTAX INTEGER  { disable(0), enable(1) }
        MAX-ACCESS read-write
        STATUS current
        DESCRIPTION
            "The user has changed the NPort 6000 series device
            server's IP address. When the IP address changes,
            the NPort 6000 series device server will send a
            SMS with the new IP address before it reboots.
            Note: NPort 6150, 6250, 6250-S-SC, 6250-M-SC 
            do not support write access."
        ::= { eventSettings 18 }
        
    smsServerPasswordChanged OBJECT-TYPE
        SYNTAX INTEGER  { disable(0), enable(1) }
        MAX-ACCESS read-write
        STATUS current
        DESCRIPTION
            "The user has changed the NPort 6000 series device
            server's password. When the password changes, the
            NPort 6000 series device server will send a SMS
            with the password changed notice before it reboots.
            Note: NPort 6150, 6250, 6250-S-SC, 6250-M-SC 
            do not support write access."
        ::= { eventSettings 19 }

-- -------------------------------------------------------------
-- System Management -> Auto Warning Settings -> Serial Event Settings
-- -------------------------------------------------------------

	serialEventSettings OBJECT IDENTIFIER ::= { autoWarningSettings 2 }
	
	portEventSettingsTable OBJECT-TYPE
        SYNTAX SEQUENCE OF PortEventSettingsEntry
        MAX-ACCESS not-accessible
        STATUS current
        DESCRIPTION
            "Port Event Settings Table."
        ::= { serialEventSettings 1 }
    
    portEventSettingsEntry OBJECT-TYPE
        SYNTAX PortEventSettingsEntry
        MAX-ACCESS not-accessible
        STATUS current
        DESCRIPTION
            "Port Event Settings entry."
        INDEX { portIndex }
        ::= { portEventSettingsTable 1 }
        
    PortEventSettingsEntry ::=
        SEQUENCE {
        	mailDCDchange
        		INTEGER,
            trapDCDchange
                INTEGER,
            alarmDCDchange
                INTEGER,
            smsDCDchange
                INTEGER,
            mailDSRchange
        		INTEGER,
            trapDSRchange
                INTEGER,
            alarmDSRchange
                INTEGER,
            smsDSRchange
                INTEGER
        }
	
	mailDCDchange OBJECT-TYPE
        SYNTAX INTEGER { disable(0), enable(1)}
        MAX-ACCESS read-write
        STATUS current
        DESCRIPTION
            "A change in the DCD (Data Carrier Detect) signal
            indicates that the modem connection status has
            changed. For example, if the DCD signal changes to
            low, it indicates that the connection line is down.
            When the DCD signal changes to low, the NPort 6000
            series device server will immediately send an e-mail
            message."
        ::= { portEventSettingsEntry 1 }
        
	trapDCDchange OBJECT-TYPE
		SYNTAX INTEGER { disable(0), enable(1)}
		MAX-ACCESS read-write
		STATUS current
		DESCRIPTION
			"A change in the DCD (Data Carrier Detect) signal
            indicates that the modem connection status has
            changed. For example, if the DCD signal changes to
            low, it indicates that the connection line is down.
            When the DCD signal changes to low, the NPort 6000
            series device server will immediately send an SNMP
            trap."
		::= { portEventSettingsEntry 2 }
		
	alarmDCDchange OBJECT-TYPE
		SYNTAX INTEGER { disable(0), enable(1)}
		MAX-ACCESS read-write
		STATUS current
		DESCRIPTION
			"A change in the DCD (Data Carrier Detect) signal
            indicates that the modem connection status has
            changed. For example, if the DCD signal changes to
            low, it indicates that the connection line is down.
            When the DCD signal changes to low, the NPort 6000
            series device server will immediately raise a d-out
            alarm.
            Note: NPort 6150, 6250, 6250-S-SC, 6250-M-SC 
            do not support write access."
		::= { portEventSettingsEntry 3 }

	smsDCDchange OBJECT-TYPE
		SYNTAX INTEGER { disable(0), enable(1)}
		MAX-ACCESS read-write
		STATUS current
		DESCRIPTION
			"A change in the DCD (Data Carrier Detect) signal
            indicates that the modem connection status has
            changed. For example, if the DCD signal changes to
            low, it indicates that the connection line is down.
            When the DCD signal changes to low, the NPort 6000
            series device server will automatically send a SMS
            alarm.
            Note: NPort 6150, 6250, 6250-S-SC, 6250-M-SC 
            do not support write access."
		::= { portEventSettingsEntry 4 }
		
	mailDSRchange OBJECT-TYPE
        SYNTAX INTEGER { disable(0), enable(1)}
        MAX-ACCESS read-write
        STATUS current
        DESCRIPTION
            "A change in the DSR (Data Set Ready) signal
            indicates that the data communication equipment is
            powered off. For example, if the DSR signal changes
            to low, it indicates that the data communication
            equipment is powered down. When the DSR signal
            changes to low, the NPort 6000 series device server
            will immediately send an e-mail message."
        ::= { portEventSettingsEntry 5 }
        
	trapDSRchange OBJECT-TYPE
		SYNTAX INTEGER { disable(0), enable(1)}
		MAX-ACCESS read-write
		STATUS current
		DESCRIPTION
			"A change in the DSR (Data Set Ready) signal
            indicates that the data communication equipment is
            powered off. For example, if the DSR signal changes
            to low, it indicates that the data communication
            equipment is powered down. When the DSR signal
            changes to low, the NPort 6000 series device server
            will immediately send an SNMP trap."
		::= { portEventSettingsEntry 6 }
		
	alarmDSRchange OBJECT-TYPE
		SYNTAX INTEGER { disable(0), enable(1)}
		MAX-ACCESS read-write
		STATUS current
		DESCRIPTION
			"A change in the DSR (Data Set Ready) signal
            indicates that the data communication equipment is
            powered off. For example, if the DSR signal changes
            to low, it indicates that the data communication
            equipment is powered down. When the DSR signal
            changes to low, the NPort 6000 series device server
            will immediately raise a d-out alarm.
            Note: NPort 6150, 6250, 6250-S-SC, 6250-M-SC 
            do not support write access."
		::= { portEventSettingsEntry 7 }

	smsDSRchange OBJECT-TYPE
		SYNTAX INTEGER { disable(0), enable(1)}
		MAX-ACCESS read-write
		STATUS current
		DESCRIPTION
			"A change in the DSR (Data Set Ready) signal
            indicates that the data communication equipment is
            powered off. For example, if the DSR signal changes
            to low, it indicates that the data communication
            equipment is powered down. When the DSR signal
            changes to low, the NPort 6000 series device server
            will automatically send a SMS alarm.
            Note: NPort 6150, 6250, 6250-S-SC, 6250-M-SC 
            do not support write access."
		::= { portEventSettingsEntry 8 }

-- -------------------------------------------------------------
-- System Management -> Auto Warning Settings -> E-mail Alert
-- -------------------------------------------------------------

	emailAlert OBJECT IDENTIFIER ::= { autoWarningSettings 3 }
	
	emailWarningMailServer OBJECT-TYPE
        SYNTAX DisplayString
        MAX-ACCESS read-write
        STATUS current
        DESCRIPTION
            "The e-mail server's IP address or domain name of
            the e-mail warning function."
        ::= { emailAlert 1 }
        
    emailRequiresAuthentication  OBJECT-TYPE
        SYNTAX INTEGER { non-require(0), require(1)}
        MAX-ACCESS read-write
        STATUS current
        DESCRIPTION
            "Set if the mail server requires user login."
        ::= { emailAlert 2 }
        
    emailWarningUserName OBJECT-TYPE
        SYNTAX DisplayString (SIZE(0..64))
        MAX-ACCESS read-write
        STATUS current
        DESCRIPTION
            "The user name used to log into the mail server if 
            authentication is required."
        ::= { emailAlert 3 }
        
    emailWarningPassword OBJECT-TYPE
        SYNTAX DisplayString (SIZE(0..16))
        MAX-ACCESS read-write
        STATUS current
        DESCRIPTION
            "The password used to log into the mail server if
            authentication is required."
        ::= { emailAlert 4 }
        
    emailWarningFromEmail OBJECT-TYPE
        SYNTAX DisplayString
        MAX-ACCESS read-write
        STATUS current
        DESCRIPTION
            "The e-mail address to be filled in the 'From' field of
            the auto-warning e-mail."
        ::= { emailAlert 5 }
        
    emailWarningFirstEmailAddr OBJECT-TYPE
        SYNTAX DisplayString
        MAX-ACCESS read-write
        STATUS current
        DESCRIPTION
            "The first email address to where the auto-warning
            e-mail is to be sent."
        ::= { emailAlert 6 }
        
    emailWarningSecondEmailAddr OBJECT-TYPE
        SYNTAX DisplayString
        MAX-ACCESS read-write
        STATUS current
        DESCRIPTION
            "The second email address to where the auto-warning
            e-mail is to be sent."
        ::= { emailAlert 7 }
        
    emailWarningThirdEmailAddr OBJECT-TYPE
        SYNTAX DisplayString
        MAX-ACCESS read-write
        STATUS current
        DESCRIPTION
            "The third email address to where the auto-warning
            e-mail is to be sent."
        ::= { emailAlert 8 }
        
    emailWarningFourthEmailAddr OBJECT-TYPE
        SYNTAX DisplayString
        MAX-ACCESS read-write
        STATUS current
        DESCRIPTION
            "The fourth email address to where the auto-warning
            e-mail is to be sent."
        ::= { emailAlert 9 }
	
-- -------------------------------------------------------------
-- System Management -> Auto Warning Settings -> SNMP Trap
-- -------------------------------------------------------------

	snmpTrap OBJECT IDENTIFIER ::= { autoWarningSettings 4 }
	
	snmpTrapReceiverIp  OBJECT-TYPE
        SYNTAX DisplayString
        MAX-ACCESS read-write               
        STATUS current
        DESCRIPTION
            "SNMP trap server IP address or domain name."
		::= { snmpTrap 1 }
		
	trapVersion  OBJECT-TYPE
        SYNTAX INTEGER { v1(0), v2c(1)}
        MAX-ACCESS read-write               
        STATUS current
        DESCRIPTION
            "SNMP trap version used for the auto-warning function."
		::= { snmpTrap 2 }

-- -------------------------------------------------------------
-- System Management -> Auto Warning Settings -> SMS Alert
-- -------------------------------------------------------------

	smsAlert OBJECT IDENTIFIER ::= { autoWarningSettings 5 }
	    
    smsAlertFirstPhoneNumber OBJECT-TYPE
        SYNTAX DisplayString (SIZE(0..20))
        MAX-ACCESS read-write
        STATUS current
        DESCRIPTION
            "The first phone number to where the auto-warning
            SMS is to be sent.
            Note: NPort 6150, 6250, 6250-S-SC, 6250-M-SC 
            do not support write access."
        ::= { smsAlert 1 }

    smsAlertSecondPhoneNumber OBJECT-TYPE
        SYNTAX DisplayString (SIZE(0..16))
        MAX-ACCESS read-write
        STATUS current
        DESCRIPTION
            "The second phone number to where the auto-warning
            SMS is to be sent.
            Note: NPort 6150, 6250, 6250-S-SC, 6250-M-SC 
            do not support write access."
        ::= { smsAlert 2 }
        
    smsAlertThirdPhoneNumber OBJECT-TYPE
        SYNTAX DisplayString (SIZE(0..16))
        MAX-ACCESS read-write
        STATUS current
        DESCRIPTION
            "The third phone number to where the auto-warning
            SMS is to be sent.
            Note: NPort 6150, 6250, 6250-S-SC, 6250-M-SC 
            do not support write access."
        ::= { smsAlert 3 }

    smsAlertFourthPhoneNumber OBJECT-TYPE
        SYNTAX DisplayString (SIZE(0..16))
        MAX-ACCESS read-write
        STATUS current
        DESCRIPTION
            "The fourth phone number to where the auto-warning
            SMS is to be sent.
            Note: NPort 6150, 6250, 6250-S-SC, 6250-M-SC 
            do not support write access."
        ::= { smsAlert 4 }

-- -------------------------------------------------------------
-- System Management -> Auto Warning Settings -> Event Log Setting
-- -------------------------------------------------------------

    eventLogSettings OBJECT IDENTIFIER ::= { autoWarningSettings 6 }
        
    currentLogCapacityRatio OBJECT-TYPE
        SYNTAX DisplayString
        MAX-ACCESS read-only
        STATUS current
        DESCRIPTION
            "The current usage ratio of log capacity."
        ::= { eventLogSettings 1 }

    logCapacityWarningEnable OBJECT-TYPE
        SYNTAX INTEGER { disable(0), enable(1)}
        MAX-ACCESS read-write
        STATUS current
        DESCRIPTION
            "Enable/disable the log capacity warning."
        ::= { eventLogSettings 2 }
        
    logCapacityWarningThreshold OBJECT-TYPE
        SYNTAX INTEGER (0..100)
        MAX-ACCESS read-write
        STATUS current
        DESCRIPTION
            "The log capacity warning threshold."
        ::= { eventLogSettings 3 }

    mailLogCapacity OBJECT-TYPE
        SYNTAX INTEGER { disable(0), enable(1)}
        MAX-ACCESS read-write
        STATUS current
        DESCRIPTION
            "The log capacity warning which alerts 
            user by mail message."
        ::= { eventLogSettings 4 }

    trapLogCapacity OBJECT-TYPE
        SYNTAX INTEGER { disable(0), enable(1)}
        MAX-ACCESS read-write
        STATUS current
        DESCRIPTION
            "The log capacity warning which alerts 
            user by SNMP trap."
        ::= { eventLogSettings 5 }

    logOversizeAction OBJECT-TYPE
        SYNTAX INTEGER { overwriteTheOldestEventLog(0), stopRecordingEventLog(1) }
        MAX-ACCESS read-write
        STATUS current
        DESCRIPTION
            "The event log oversize actions."
        ::= { eventLogSettings 6 }
        
-- -------------------------------------------------------------
-- System Management -> Maintenance
-- -------------------------------------------------------------

	maintenance OBJECT IDENTIFIER ::= { sysManagement 3 }
	
-- ----------------------------------------------------------------------------
-- System Management -> Maintenance -> Console Settings
-- ----------------------------------------------------------------------------

	consoleSettings OBJECT IDENTIFIER ::= { maintenance 1 }
	
	httpConsole OBJECT-TYPE
        SYNTAX INTEGER { disable(0), enable(1)}
        MAX-ACCESS read-write               
        STATUS current
        DESCRIPTION
            "Enable or disable HTTP console."
        ::= { consoleSettings 1 }
        
    httpsConsole OBJECT-TYPE
        SYNTAX INTEGER { disable(0), enable(1)}
        MAX-ACCESS read-write               
        STATUS current
        DESCRIPTION
            "Enable or disable HTTPS console."
		::= { consoleSettings 2 }
	
	telnetConsole OBJECT-TYPE
        SYNTAX INTEGER { disable(0), enable(1)}
        MAX-ACCESS read-write               
        STATUS current
        DESCRIPTION
            "Enable or disable Telnet console."
		::= { consoleSettings 3 }
		
	sshConsole OBJECT-TYPE
        SYNTAX INTEGER { disable(0), enable(1)}
        MAX-ACCESS read-write               
        STATUS current
        DESCRIPTION
            "Enable or disable SSH console."
		::= { consoleSettings 4 }
	
	consoleAuthenticationType OBJECT-TYPE
        SYNTAX INTEGER  { local(0), radius(1), radius-local(2), local-radius(3), tacacsPlus(4), tacacsPlus-local(5), local-tacacsPlus(6) }
        MAX-ACCESS read-write                
        STATUS current
        DESCRIPTION
            "The console authentication type."
        ::= { consoleSettings 5 }
        
    tryNextTypeOnAuthDenied OBJECT-TYPE
        SYNTAX INTEGER { disable(0), enable(1)}
        MAX-ACCESS read-write               
        STATUS current
        DESCRIPTION
            "Try next type on authentication denied or not"
		::= { consoleSettings 6 }    
		
	resetButtonFunction OBJECT-TYPE
        SYNTAX INTEGER { disable-after-60-sec(0), always-enable(1)}
        MAX-ACCESS read-write               
        STATUS current
        DESCRIPTION
            "Enable or disable reset button protection. You can
            disable the hardware reset button after the NPort 6000
            series device server has been restarted for 60 seconds."
		::= { consoleSettings 7 }
	
	lcmReadOnlyProtect OBJECT-TYPE
        SYNTAX INTEGER { readonly(0), writable(1)}
        MAX-ACCESS read-write               
        STATUS current
        DESCRIPTION
            "Enable or disable LCM read-only protection. If the LCM
            panel is under read-only protection, users can only
            view the configurations from the LCM panel. Otherwise,
            by default, users can modify the settings directly
            on the LCM panel."
		::= { consoleSettings 8 }

	maxHttpLoginUsers OBJECT-TYPE
        SYNTAX INTEGER (1..10)
        MAX-ACCESS read-write                
        STATUS current
        DESCRIPTION
            "The maximum login users for HTTP/HTTPS."
        ::= { consoleSettings 9 }

	autoLogoutSetting OBJECT-TYPE
        SYNTAX INTEGER (1..1440)
        MAX-ACCESS read-write                
        STATUS current
        DESCRIPTION
            "Auto logout setting (ms)"
        ::= { consoleSettings 10 }

-- ----------------------------------------------------------------------------
-- System Management -> Maintenance -> Load Factory Default
-- ----------------------------------------------------------------------------

	loadFactoryDefault OBJECT IDENTIFIER ::= { maintenance 2 }
			
	loadFactoryDefaultSetting  OBJECT-TYPE
        SYNTAX INTEGER { 
        	resetToFactoryDefault-ExcludingIpConfiguration (0), 
        	resetToFactoryDefault (1)
        }
        MAX-ACCESS write-only               
        STATUS current
        DESCRIPTION
            "This function will reset all of the NPort 6000 series
            device server's settings to the factory default
            values. Be aware that previous settings will be
            lost. Selecting Reset to factory default
            (excluding IP configuration) will reset all settings
            except the IP configuration to factory defaults.
            Selecting Reset to factory default will reset all
            settings including the IP configuration to factory
            defaults."
		::= { loadFactoryDefault 1 }

-- -------------------------------------------------------------
-- System Management -> Account Management
-- -------------------------------------------------------------

    accountManagement OBJECT IDENTIFIER ::= { sysManagement 4 }   
    
-- -------------------------------------------------------------
-- System Management -> Account Management -> Notification Message
-- -------------------------------------------------------------

    notificationMessage OBJECT IDENTIFIER ::= { accountManagement 1 }   

    loginNotificationMessage  OBJECT-TYPE
        SYNTAX DisplayString (SIZE(0..240))
        MAX-ACCESS read-write               
        STATUS current
        DESCRIPTION
            "Login notification message."
        ::= { notificationMessage 1 }

    loginFailureMessage  OBJECT-TYPE
        SYNTAX DisplayString (SIZE(0..240))
        MAX-ACCESS read-write               
        STATUS current
        DESCRIPTION
            "Login failure message."
        ::= { notificationMessage 2 }

-- -------------------------------------------------------------
-- System Management -> Account Management -> User Account
-- -------------------------------------------------------------

    userAccount OBJECT IDENTIFIER ::= { accountManagement 2 }   

    userAccountTable OBJECT-TYPE
        SYNTAX SEQUENCE OF UserAccountEntry
        MAX-ACCESS not-accessible               
        STATUS current
        DESCRIPTION
            "User account list"
        ::= { userAccount 1 }
    
    userAccountEntry OBJECT-TYPE
        SYNTAX UserAccountEntry
        MAX-ACCESS not-accessible
        STATUS current
        DESCRIPTION
            "User account list entry"
        INDEX { userAccountIndex }
        ::= { userAccountTable 1 }
        
    UserAccountEntry ::=
        SEQUENCE {
            userAccountIndex
                INTEGER,
            activeUserAccount
                INTEGER,
            accountName
                DisplayString,
            accountGroupName
                DisplayString,
        }
       
    userAccountIndex OBJECT-TYPE
        SYNTAX INTEGER
        MAX-ACCESS read-only                
        STATUS current
        DESCRIPTION
            "The Host Table index."
        ::= { userAccountEntry 1 } 
    
    activeUserAccount OBJECT-TYPE
        SYNTAX INTEGER { non_active(0), avtive(1)}
        MAX-ACCESS read-write                
        STATUS current
        DESCRIPTION
            "The user account is activate or not."
        ::= { userAccountEntry 2 } 

    accountName  OBJECT-TYPE
        SYNTAX DisplayString (SIZE(1..16))
        MAX-ACCESS read-write               
        STATUS current
        DESCRIPTION
            "Name of user account"
        ::= { userAccountEntry 3 }
        
    accountGroupName  OBJECT-TYPE
        SYNTAX DisplayString (SIZE(1..16))
        MAX-ACCESS read-write
        STATUS current
        DESCRIPTION
            "Group name of user account"
        ::= { userAccountEntry 4 }

-- -------------------------------------------------------------
-- System Management -> Account Management -> Access Permission
-- -------------------------------------------------------------

    accessPermission OBJECT IDENTIFIER ::= { accountManagement 3 }   

    accessPermissionTable OBJECT-TYPE
        SYNTAX SEQUENCE OF AccessPermissionEntry
        MAX-ACCESS not-accessible               
        STATUS current
        DESCRIPTION
            "Access permission list"
        ::= { accessPermission 1 }
    
    accessPermissionEntry OBJECT-TYPE
        SYNTAX AccessPermissionEntry
        MAX-ACCESS not-accessible
        STATUS current
        DESCRIPTION
            "Access permission list entry"
        INDEX { groupName }
        ::= { accessPermissionTable 1 }
        
    AccessPermissionEntry ::=
        SEQUENCE {
            groupName
                DisplayString,
            networkConfig
                INTEGER,
            serialConfig
                INTEGER,
            systemConfig
                INTEGER,
            adminConfig
                INTEGER,
            monitorLogWarning
                INTEGER,
            commonSetting
                INTEGER
        }
       
    groupName OBJECT-TYPE
        SYNTAX DisplayString (SIZE(1..16))
        MAX-ACCESS read-write                
        STATUS current
        DESCRIPTION
            "Group name"
        ::= { accessPermissionEntry 1 } 
    
    networkConfig  OBJECT-TYPE
        SYNTAX  INTEGER {no-display(0), read-only(1), read-write(2)}
        MAX-ACCESS read-write               
        STATUS current
        DESCRIPTION
            "Access permission of network configuration group"
        ::= { accessPermissionEntry 2 }
        
    serialConfig  OBJECT-TYPE
        SYNTAX  INTEGER {no-display(0), read-only(1), read-write(2)}
        MAX-ACCESS read-write
        STATUS current
        DESCRIPTION
            "Access permission of serial configuration group"
        ::= { accessPermissionEntry 3 }

    systemConfig  OBJECT-TYPE
        SYNTAX  INTEGER {no-display(0), read-only(1), read-write(2)}
        MAX-ACCESS read-write
        STATUS current
        DESCRIPTION
            "Access permission of system configuration group"
        ::= { accessPermissionEntry 4 }

    adminConfig  OBJECT-TYPE
        SYNTAX  INTEGER {no-display(0), read-only(1), read-write(2)}
        MAX-ACCESS read-write
        STATUS current
        DESCRIPTION
            "Access permission of administration group"
        ::= { accessPermissionEntry 5 }

    monitorLogWarning  OBJECT-TYPE
        SYNTAX  INTEGER {no-display(0), read-only(1), read-write(2)}
        MAX-ACCESS read-write
        STATUS current
        DESCRIPTION
            "Access permission of log monitoring group"
        ::= { accessPermissionEntry 6 }

    commonSetting  OBJECT-TYPE
        SYNTAX  INTEGER {no-display(0), read-only(1), read-write(2)}
        MAX-ACCESS read-write
        STATUS current
        DESCRIPTION
            "Access permission of common setting group"
        ::= { accessPermissionEntry 7 }

-- ----------------------------------------------------------------------
-- System Management -> Account Management -> Password and Login Management
-- ----------------------------------------------------------------------

    accountPasswordAndLoginMgmt OBJECT IDENTIFIER ::= { accountManagement 4 }   

-- -----------------------------------------------------------------------------------------
-- System Management -> Account Management -> Password and Login Management -> Password Policy
-- -----------------------------------------------------------------------------------------

    accountPasswordPolicy OBJECT IDENTIFIER ::= { accountPasswordAndLoginMgmt 1 }  

    pwdMinLength  OBJECT-TYPE
        SYNTAX INTEGER (4..16)
        MAX-ACCESS read-write               
        STATUS current
        DESCRIPTION
            "The minimum length of password."
        ::= { accountPasswordPolicy 1 }

    pwdComplexityCheckEnable  OBJECT-TYPE
        SYNTAX INTEGER { disable(0), enable(1)}
        MAX-ACCESS read-write               
        STATUS current
        DESCRIPTION
            "Enable or disable password complexity check"
        ::= { accountPasswordPolicy 2 }

    pwdComplexityCheckDigitEnable  OBJECT-TYPE
        SYNTAX INTEGER { disable(0), enable(1)}
        MAX-ACCESS read-write               
        STATUS current
        DESCRIPTION
            "Enable or disable digit check"
        ::= { accountPasswordPolicy 3 }

    pwdComplexityCheckAlphabetEnable  OBJECT-TYPE
        SYNTAX INTEGER { disable(0), enable(1)}
        MAX-ACCESS read-write               
        STATUS current
        DESCRIPTION
            "Enable or disable alphabet check"
        ::= { accountPasswordPolicy 4 }        

    pwdComplexityCheckSpecialCharEnable  OBJECT-TYPE
        SYNTAX INTEGER { disable(0), enable(1)}
        MAX-ACCESS read-write               
        STATUS current
        DESCRIPTION
            "Enable or disable special letter check"
        ::= { accountPasswordPolicy 5 }

    pwdLifetime  OBJECT-TYPE
        SYNTAX INTEGER (90..180)
        MAX-ACCESS read-write               
        STATUS current
        DESCRIPTION
            "Password life time"
        ::= { accountPasswordPolicy 6 }
                        
-- -------------------------------------------------------------
-- System Management -> Account Management -> Password and Login Management -> Login Failure Lockout
-- -------------------------------------------------------------

    accountLoginFailureLockout OBJECT IDENTIFIER ::= { accountPasswordAndLoginMgmt 2 }  

    loginFailureLockoutEnable  OBJECT-TYPE
        SYNTAX INTEGER { disable(0), enable(1)}
        MAX-ACCESS read-write               
        STATUS current
        DESCRIPTION
            "Enable or disable lockout when login failure"
        ::= { accountLoginFailureLockout 1 }

    loginFailureLockoutRetrys  OBJECT-TYPE
        SYNTAX INTEGER (1..10)
        MAX-ACCESS read-write               
        STATUS current
        DESCRIPTION
            "The login lockout after fail retry over the count."
        ::= { accountLoginFailureLockout 2 }

    loginFailureLockoutTime  OBJECT-TYPE
        SYNTAX INTEGER (1..60)
        MAX-ACCESS read-write               
        STATUS current
        DESCRIPTION
            "The lockout time after fail retry over the count."
        ::= { accountLoginFailureLockout 3 }		

-- -------------------------------------------------------------
-- System Status
-- -------------------------------------------------------------

	sysStatus OBJECT IDENTIFIER ::= { swMgmt 6 }
	
-- -------------------------------------------------------------
-- System Status -> Serial to Network Connections
-- -------------------------------------------------------------

	s2eConnections OBJECT IDENTIFIER ::= { sysStatus 1 }

	monitorRemoteIpTable OBJECT-TYPE
        SYNTAX SEQUENCE OF MonitorRemoteIpEntry
        MAX-ACCESS not-accessible
        STATUS current
        DESCRIPTION
            "Serial to Network Connections Remote IP table."
        ::= { s2eConnections 1 }
    
    monitorRemoteIpEntry OBJECT-TYPE
        SYNTAX MonitorRemoteIpEntry
        MAX-ACCESS not-accessible
        STATUS current
        DESCRIPTION
            "Serial to Network Connections Remote IP entry."
        INDEX { portIndex, remoteIpIndex }
        ::= { monitorRemoteIpTable 1 }
        
    MonitorRemoteIpEntry ::=
        SEQUENCE {
        	remoteIpIndex
        		INTEGER,
            monitorRemoteIp
                DisplayString,
            monitorCipher
            	DisplayString   
        }
    
    remoteIpIndex  OBJECT-TYPE
        SYNTAX INTEGER
        MAX-ACCESS read-only               
        STATUS current
        DESCRIPTION
            "Serial to Network Connections Remote IP index."
		::= { monitorRemoteIpEntry 1 }
   	    
	monitorRemoteIp  OBJECT-TYPE
        SYNTAX DisplayString
        MAX-ACCESS read-only               
        STATUS current
        DESCRIPTION
            "The remote IP currently connecting to this port."
		::= { monitorRemoteIpEntry 2 }

	monitorCipher  OBJECT-TYPE
        SYNTAX DisplayString
        MAX-ACCESS read-only               
        STATUS current
        DESCRIPTION
            "Currently used cipher for this connection if secure mode is enabled."
		::= { monitorRemoteIpEntry 3 }
	
-- -------------------------------------------------------------
-- System Status -> Serial Port Status
-- -------------------------------------------------------------

	serialPortStatus OBJECT IDENTIFIER ::= { sysStatus 2 }
	
	monitorSerialPortStatusTable OBJECT-TYPE
        SYNTAX SEQUENCE OF MonitorSerialPortStatusEntry
        MAX-ACCESS not-accessible
        STATUS current
        DESCRIPTION
            "Serial Port Status table."
        ::= { serialPortStatus 1 }
    
    monitorSerialPortStatusEntry OBJECT-TYPE
        SYNTAX MonitorSerialPortStatusEntry
        MAX-ACCESS not-accessible
        STATUS current
        DESCRIPTION
            "Serial Port Status entry."
        INDEX { portIndex }
        ::= { monitorSerialPortStatusTable 1 }
        
    MonitorSerialPortStatusEntry ::=
        SEQUENCE {
            monitorTxCount
				INTEGER,
			monitorRxCount
				INTEGER,
			monitorTxTotalCount
				INTEGER,
			monitorRxTotalCount
				INTEGER,
			monitorDSR
				INTEGER,
			monitorDTR
				INTEGER,
			monitorRTS
				INTEGER,
			monitorCTS
				INTEGER,
			monitorDCD
				INTEGER
        }

	monitorTxCount  OBJECT-TYPE
        SYNTAX INTEGER
        MAX-ACCESS read-only
        STATUS current
        DESCRIPTION
            "View the number of bytes transmitted from the port
            since the last time the port was initialized."
		::= { monitorSerialPortStatusEntry 1 }
		
	monitorRxCount  OBJECT-TYPE
        SYNTAX INTEGER
        MAX-ACCESS read-only
        STATUS current
        DESCRIPTION
            "View the number of bytes received by the port since
            the last time the port was initialized."
		::= { monitorSerialPortStatusEntry 2 }
		
	monitorTxTotalCount  OBJECT-TYPE
        SYNTAX INTEGER
        MAX-ACCESS read-only
        STATUS current
        DESCRIPTION
            "View the number of bytes transmitted from the port
            since the last time the system was initialized."
		::= { monitorSerialPortStatusEntry 3 }
		
	monitorRxTotalCount  OBJECT-TYPE
        SYNTAX INTEGER
        MAX-ACCESS read-only
        STATUS current
        DESCRIPTION
            "View the number of bytes received by the port since
            the last time the system was initialized."
		::= { monitorSerialPortStatusEntry 4 }
		
	monitorDSR  OBJECT-TYPE
        SYNTAX INTEGER { off(0), on(1)}
        MAX-ACCESS read-only
        STATUS current
        DESCRIPTION
            "View the current DSR status of this port."
		::= { monitorSerialPortStatusEntry 5 }
		
	monitorDTR  OBJECT-TYPE
        SYNTAX INTEGER { off(0), on(1)}
        MAX-ACCESS read-only
        STATUS current
        DESCRIPTION
            "View the current DTR status of this port."
		::= { monitorSerialPortStatusEntry 6 }
		
	monitorRTS  OBJECT-TYPE
        SYNTAX INTEGER { off(0), on(1)}
        MAX-ACCESS read-only
        STATUS current
        DESCRIPTION
            "View the current RTS status of this port."
		::= { monitorSerialPortStatusEntry 7 }
		
	monitorCTS  OBJECT-TYPE
        SYNTAX INTEGER { off(0), on(1)}
        MAX-ACCESS read-only
        STATUS current
        DESCRIPTION
            "View the current CTS status of this port."
		::= { monitorSerialPortStatusEntry 8 }
		
	monitorDCD  OBJECT-TYPE
        SYNTAX INTEGER { off(0), on(1)}
        MAX-ACCESS read-only
        STATUS current
        DESCRIPTION
            "View the current DCD status of this port."
		::= { monitorSerialPortStatusEntry 9 }
		
-- -------------------------------------------------------------
-- System Status -> Serial Port Error Count
-- -------------------------------------------------------------

	serialPortErrorCount OBJECT IDENTIFIER ::= { sysStatus 3 }
	
	monitorSerialPortErrorCountTable OBJECT-TYPE
        SYNTAX SEQUENCE OF MonitorSerialPortErrorCountEntry
        MAX-ACCESS not-accessible
        STATUS current
        DESCRIPTION
            "Serial Port Error Count table."
        ::= { serialPortErrorCount 1 }
    
    monitorSerialPortErrorCountEntry OBJECT-TYPE
        SYNTAX MonitorSerialPortErrorCountEntry
        MAX-ACCESS not-accessible
        STATUS current
        DESCRIPTION
            "Serial Port Error Count entry."
        INDEX { portIndex }
        ::= { monitorSerialPortErrorCountTable 1 }
        
    MonitorSerialPortErrorCountEntry ::=
        SEQUENCE {
            monitorErrorCountFrame
				INTEGER,
			monitorErrorCountParity
				INTEGER,
			monitorErrorCountOverrun
				INTEGER,
			monitorErrorCountBreak
				INTEGER
        }

	monitorErrorCountFrame  OBJECT-TYPE
        SYNTAX INTEGER
        MAX-ACCESS read-only
        STATUS current
        DESCRIPTION
            "View the number of 'Frame' errors for this port."
		::= { monitorSerialPortErrorCountEntry 1 }
		
	monitorErrorCountParity  OBJECT-TYPE
        SYNTAX INTEGER
        MAX-ACCESS read-only
        STATUS current
        DESCRIPTION
            "View the number of 'Parity' errors for this port."
		::= { monitorSerialPortErrorCountEntry 2 }
		
	monitorErrorCountOverrun  OBJECT-TYPE
        SYNTAX INTEGER
        MAX-ACCESS read-only
        STATUS current
        DESCRIPTION
            "View the number of 'Overrun' errors for this port."
		::= { monitorSerialPortErrorCountEntry 3 }
		
	monitorErrorCountBreak  OBJECT-TYPE
        SYNTAX INTEGER
        MAX-ACCESS read-only
        STATUS current
        DESCRIPTION
            "View the number of 'Break' errors for this port."
		::= { monitorSerialPortErrorCountEntry 4 }
	
-- -------------------------------------------------------------
-- System Status -> Serial Port Settings
-- -------------------------------------------------------------

	serialPortSettings OBJECT IDENTIFIER ::= { sysStatus 4 }
	
	monitorSerialPortSettingsTable OBJECT-TYPE
        SYNTAX SEQUENCE OF MonitorSerialPortSettingsEntry
        MAX-ACCESS not-accessible
        STATUS current
        DESCRIPTION
            "Serial Port Settings table."
        ::= { serialPortSettings 1 }
    
    monitorSerialPortSettingsEntry OBJECT-TYPE
        SYNTAX MonitorSerialPortSettingsEntry
        MAX-ACCESS not-accessible
        STATUS current
        DESCRIPTION
            "Serial Port Settings entry."
        INDEX { portIndex }
        ::= { monitorSerialPortSettingsTable 1 }
        
    MonitorSerialPortSettingsEntry ::=
        SEQUENCE {
            monitorBaudRate
				INTEGER,
			monitorDataBits
				INTEGER,
			monitorStopBits
				DisplayString,
			monitorParity
				INTEGER,
			monitorRTSCTSFlowControl
				INTEGER,
			monitorXONXOFFFlowControl
				INTEGER,
			monitorDTRDSRFlowControl
				INTEGER,
			monitorRTSToggleFlowControl
				INTEGER,	
			monitorFIFO
				INTEGER,
			monitorInterface
				INTEGER
        }

	monitorBaudRate  OBJECT-TYPE
        SYNTAX INTEGER
        MAX-ACCESS read-only
        STATUS current
        DESCRIPTION
            "View the current baudrate of the port."
		::= { monitorSerialPortSettingsEntry 1 }
		
	monitorDataBits  OBJECT-TYPE
		SYNTAX INTEGER  { 
			bits-5(0), 
			bits-6(1), 
			bits-7(2),
			bits-8(3) 
		}
        MAX-ACCESS read-only
        STATUS current
        DESCRIPTION
            "View the number of bits per byte for the port."
		::= { monitorSerialPortSettingsEntry 2 }
		
	monitorStopBits  OBJECT-TYPE
        SYNTAX DisplayString
        MAX-ACCESS read-only
        STATUS current
        DESCRIPTION
            "View the number of stop bits for the port."
		::= { monitorSerialPortSettingsEntry 3 }
	
	monitorParity  OBJECT-TYPE
        SYNTAX INTEGER {
        	none(0),
			odd(8),
			even(24),
			mark(40),
			space(56)
        }
        MAX-ACCESS read-only
        STATUS current
        DESCRIPTION
            "View the parity bit for the port."
		::= { monitorSerialPortSettingsEntry 4 }
		
	monitorRTSCTSFlowControl  OBJECT-TYPE
        SYNTAX INTEGER { off(0), on(1) }
        MAX-ACCESS read-only
        STATUS current
        DESCRIPTION
            "View if the port is using RTS/CTS flow control."
		::= { monitorSerialPortSettingsEntry 5 }
		
	monitorXONXOFFFlowControl  OBJECT-TYPE
        SYNTAX INTEGER { off(0), on(1) }
        MAX-ACCESS read-only
        STATUS current
        DESCRIPTION
            "View if the port is using XON/XOFF flow control."
		::= { monitorSerialPortSettingsEntry 6 }
		
	monitorDTRDSRFlowControl  OBJECT-TYPE
        SYNTAX INTEGER { off(0), on(1) }
        MAX-ACCESS read-only
        STATUS current
        DESCRIPTION
            "View if the port is using DTR/DSR flow control."
		::= { monitorSerialPortSettingsEntry 7 }
		
	monitorRTSToggleFlowControl  OBJECT-TYPE
        SYNTAX INTEGER { off(0), on(1) }
        MAX-ACCESS read-only
        STATUS current
        DESCRIPTION
            "View if the port is using RTS toggle flow control."
		::= { monitorSerialPortSettingsEntry 8 }	
		
	monitorFIFO  OBJECT-TYPE
        SYNTAX INTEGER {
        	disable(0),
			enable(1)
        }
        MAX-ACCESS read-only
        STATUS current
        DESCRIPTION
            "View FIFO status of this port."
		::= { monitorSerialPortSettingsEntry 9 }
		
	monitorInterface  OBJECT-TYPE
        SYNTAX INTEGER {
        	rs-232(0),
			rs-422(1),
			rs-485-2-wire(2),
			rs-485-4-wire(3)
        }
        MAX-ACCESS read-only
        STATUS current
        DESCRIPTION
            "View the serial interface that the port is using."
		::= { monitorSerialPortSettingsEntry 10 }

-- -------------------------------------------------------------
-- System Status -> Buffering
-- -------------------------------------------------------------

	serialPortBuffering OBJECT IDENTIFIER ::= { sysStatus 5 }
	
	monitorSerialPortBufferingTable OBJECT-TYPE
        SYNTAX SEQUENCE OF MonitorSerialPortBufferingEntry
        MAX-ACCESS not-accessible
        STATUS current
        DESCRIPTION
            "Serial Port Buffering table."
        ::= { serialPortBuffering 1 }
    
    monitorSerialPortBufferingEntry OBJECT-TYPE
        SYNTAX MonitorSerialPortBufferingEntry
        MAX-ACCESS not-accessible
        STATUS current
        DESCRIPTION
            "Serial Port Settings entry."
        INDEX { portIndex }
        ::= { monitorSerialPortBufferingTable 1 }
        
    MonitorSerialPortBufferingEntry ::=
        SEQUENCE {
            monitorBuffering
				INTEGER
        }
        
	monitorBuffering  OBJECT-TYPE
        SYNTAX INTEGER
        MAX-ACCESS read-only
        STATUS current
        DESCRIPTION
            "View length of buffered data for the port. The length unit is byte."
		::= { monitorSerialPortBufferingEntry 1 }

-- -------------------------------------------------------------
-- System Status -> Relay Output Status 
-- -------------------------------------------------------------

	relayOutputStatus  OBJECT IDENTIFIER ::= { sysStatus 6 }
	
	relayOutputEthernet1LinkDown  OBJECT-TYPE
        SYNTAX INTEGER {
        	none(0),
        	alarm(1),
        	alarm-Acked(2)
        }
        MAX-ACCESS read-only
        STATUS current
        DESCRIPTION
            "The relay dout status of the event that the built-
            in LAN port is off."
		::= { relayOutputStatus 1 }
		
	ethernet1LinkDownAcknowledge OBJECT-TYPE
        SYNTAX INTEGER {
        	acked(0)
        }
        MAX-ACCESS write-only
        STATUS current
        DESCRIPTION
            "Acknowledge the event that the built-in LAN port is
            off. Acknowledgement will clear the d-out alarm
            before you can actually fix the problem."
		::= { relayOutputStatus 2 }
		
	relayOutputEthernet2LinkDown  OBJECT-TYPE
        SYNTAX INTEGER {
        	none(0),
        	alarm(1),
        	alarm-Acked(2)
        }
        MAX-ACCESS read-only
        STATUS current
        DESCRIPTION
            "The relay dout status of the event that the first LAN
            port of the network module is off."
		::= { relayOutputStatus 3 }
		
	ethernet2LinkDownAcknowledge  OBJECT-TYPE
        SYNTAX INTEGER {
        	acked(0)
        }
        MAX-ACCESS write-only
        STATUS current
        DESCRIPTION
            "Acknowledge the event that the first LAN port of
            the network module is off. Acknowledgement will clear
            the d-out alarm before you can actually fix the
            problem."
		::= { relayOutputStatus 4 }
	
	relayOutputEthernet3LinkDown  OBJECT-TYPE
        SYNTAX INTEGER {
        	none(0),
        	alarm(1),
        	alarm-Acked(2)
        }
        MAX-ACCESS read-only
        STATUS current
        DESCRIPTION
            "The relay dout status of the event that the second
            LAN port of the network module is off."
		::= { relayOutputStatus 5 }
		
	ethernet3LinkDownAcknowledge  OBJECT-TYPE
        SYNTAX INTEGER {
        	acked(0)
        }
        MAX-ACCESS write-only
        STATUS current
        DESCRIPTION
            "Acknowledge the event that the second LAN port of
            the network module is off. Acknowledgement will clear
            the d-out alarm before you can actually fix the
            problem."
		::= { relayOutputStatus 6 }
	
	portDCDChangedStatusTable OBJECT-TYPE
        SYNTAX SEQUENCE OF PortDCDChangedStatusEntry
        MAX-ACCESS not-accessible
        STATUS current
        DESCRIPTION
            "DCD changed table."
        ::= { relayOutputStatus 7 }
    
    portDCDChangedStatusEntry OBJECT-TYPE
        SYNTAX PortDCDChangedStatusEntry
        MAX-ACCESS not-accessible
        STATUS current
        DESCRIPTION
            "DCD changed entry."
        INDEX { portIndex }
        ::= { portDCDChangedStatusTable 1 }
        
    PortDCDChangedStatusEntry ::=
        SEQUENCE {
            portDCDChangedStatus
				INTEGER,
			portDCDChangedAcknowledge
				INTEGER
        }

	portDCDChangedStatus  OBJECT-TYPE
        SYNTAX INTEGER {
        	none(0),
        	alarm(1),
        	alarm-Acked(2)
        }
        MAX-ACCESS read-only
        STATUS current
        DESCRIPTION
            "The relay dout status of the event that the DCD signal
            of the port is changed."
		::= { portDCDChangedStatusEntry 1 }
		
	portDCDChangedAcknowledge  OBJECT-TYPE
        SYNTAX INTEGER {
        	acked(0)
        }
        MAX-ACCESS write-only
        STATUS current
        DESCRIPTION
            "Acknowledge the event that the DCD signal of the port
            is changed. Acknowledgement will clear the d-out
            alarm before you can actually fix the problem."
		::= { portDCDChangedStatusEntry 2 }
		
		
	portDSRChangedStatusTable OBJECT-TYPE
        SYNTAX SEQUENCE OF PortDSRChangedStatusEntry
        MAX-ACCESS not-accessible
        STATUS current
        DESCRIPTION
            "DSR changed Table."
        ::= { relayOutputStatus 8 }
    
    portDSRChangedStatusEntry OBJECT-TYPE
        SYNTAX PortDSRChangedStatusEntry
        MAX-ACCESS not-accessible
        STATUS current
        DESCRIPTION
            "DSR changed entry."
        INDEX { portIndex }
        ::= { portDSRChangedStatusTable 1 }
        
    PortDSRChangedStatusEntry ::=
        SEQUENCE {
            portDSRChangedStatus
				INTEGER,
			portDSRChangedAcknowledge
				INTEGER
        }

	portDSRChangedStatus  OBJECT-TYPE
        SYNTAX INTEGER {
        	none(0),
        	alarm(1),
        	alarm-Acked(2)
        }
        MAX-ACCESS read-only
        STATUS current
        DESCRIPTION
            "The relay dout status of the event that the DSR signal
            of the port is changed."
		::= { portDSRChangedStatusEntry 1 }
		
	portDSRChangedAcknowledge  OBJECT-TYPE
        SYNTAX INTEGER {
        	acked(0)
        }
        MAX-ACCESS write-only
        STATUS current
        DESCRIPTION
            "Acknowledge the event that the DSR signal of the port
            is changed. Acknowledgement will clear the d-out
            alarm before you can actually fix the problem."
		::= { portDSRChangedStatusEntry 2 }

-- -------------------------------------------------------------
-- Module Status
-- -------------------------------------------------------------
        
    moduleStatus OBJECT IDENTIFIER ::= { sysStatus 7 } 
        
-- -------------------------------------------------------------
-- Redundancy Status
-- -------------------------------------------------------------
        
    redundancyStatus OBJECT IDENTIFIER ::= { moduleStatus 1 }        
    
    activeRedundancyProtocol OBJECT-TYPE
        SYNTAX INTEGER  { none(0), spanningTree(1), turboRing(2), turboRingV2(3) }
        MAX-ACCESS read-only
        STATUS current
        DESCRIPTION
        "This shows the active redundancy protocol. The none(0) stauts will be showed
         if only if the redundancy protocol is set to spanning tree and none of
         ports enable spanning tree."
        ::= { redundancyStatus 1 }
    
    spanningTreeStatus OBJECT IDENTIFIER ::= { redundancyStatus 2 }
        
    spanningTreeBridgeRole OBJECT-TYPE
        SYNTAX DisplayString
        MAX-ACCESS read-only                
        STATUS current
        DESCRIPTION
            "This displays NPort's bridge role (root/not-root) in spanning tree."
        ::= { spanningTreeStatus 1 }

    spanningTreeRootBridge OBJECT-TYPE
        SYNTAX DisplayString
        MAX-ACCESS read-only                
        STATUS current
        DESCRIPTION
            "This displays root bridge identifier of spanning tree."
        ::= { spanningTreeStatus 2 }

    spanningTreeRootPathCost OBJECT-TYPE
        SYNTAX DisplayString
        MAX-ACCESS read-only                
        STATUS current
        DESCRIPTION
            "The root path cost of NPort."
        ::= { spanningTreeStatus 3 }

    spanningTreePortStatusTable OBJECT-TYPE
        SYNTAX SEQUENCE OF SpanningTreePortStatusEntry
        MAX-ACCESS not-accessible               
        STATUS current
        DESCRIPTION
            "The spanning tree port status table."
        ::= { spanningTreeStatus 4 }
    
    spanningTreePortStatusEntry OBJECT-TYPE
        SYNTAX SpanningTreePortStatusEntry
        MAX-ACCESS not-accessible               
        STATUS current
        DESCRIPTION
            "The spanning tree port entry."
        INDEX { spanningTreePortStatusIndex }
        ::= { spanningTreePortStatusTable 1 }
        
    SpanningTreePortStatusEntry ::=
        SEQUENCE {
            spanningTreePortStatusIndex
                INTEGER,
            spanningTreePortEnableStatus
                INTEGER,
            spanningTreePortRole
                DisplayString,
            spanningTreePortDesignatedBridge
                DisplayString,
            spanningTreePortStatus
                DisplayString
        }

    spanningTreePortStatusIndex OBJECT-TYPE
        SYNTAX INTEGER 
        MAX-ACCESS read-only                
        STATUS current
        DESCRIPTION
            "The index of spanning tree table."
        ::= { spanningTreePortStatusEntry 1 }

    spanningTreePortEnableStatus OBJECT-TYPE
        SYNTAX INTEGER { disable(0), enable(1) }
        MAX-ACCESS read-only           
        STATUS current
        DESCRIPTION
            "This displays whether or not spanning tree protocol is enabled for this port."
        ::= { spanningTreePortStatusEntry 2 }
    
    spanningTreePortRole OBJECT-TYPE
        SYNTAX DisplayString
        MAX-ACCESS read-only               
        STATUS current
        DESCRIPTION
            "This port's role in spanning tree protocol."
        ::= { spanningTreePortStatusEntry 3 }
    
    spanningTreePortDesignatedBridge OBJECT-TYPE
        SYNTAX DisplayString 
        MAX-ACCESS read-only             
        STATUS current
        DESCRIPTION
            "This port's designated bridge ID."
        ::= { spanningTreePortStatusEntry 4 }
    
    spanningTreePortStatus OBJECT-TYPE
        SYNTAX DisplayString
        MAX-ACCESS read-only                
        STATUS current
        DESCRIPTION
            "The port status of spanning tree protocol."
        ::= { spanningTreePortStatusEntry 5 } 

    turboRingStatus OBJECT IDENTIFIER ::= { redundancyStatus 3}
    
    turboRingBrokenStatus OBJECT-TYPE
        SYNTAX INTEGER
            {
            notTurboRingV2(0),
            healthy(1),
            break(2)
            }
        MAX-ACCESS read-only
        STATUS current
        DESCRIPTION
            "Turbo Ring V2 status."
        ::= { turboRingStatus 1 }
        
    turboRingMaster OBJECT-TYPE
        SYNTAX INTEGER  { no(0), yes(1) }
        MAX-ACCESS read-only
        STATUS current
        DESCRIPTION
            "Is this a Master or Slave of Turbo Ring or Turbo Ring V2."
        ::= { turboRingStatus 2 }

    turboRingPort1 OBJECT-TYPE
        SYNTAX  INTEGER
        ACCESS  read-only
        STATUS  current
        DESCRIPTION
             "The port number of 1st Redundant Port on the Turbo Ring or Turbo Ring V2.
              Return 0 if not Turbo Ring or Turbo Ring V2."
        ::= { turboRingStatus 3 }

    turboRingPort2 OBJECT-TYPE
        SYNTAX  INTEGER
        ACCESS  read-only
        STATUS  current
        DESCRIPTION
             "The port number of 2nd Redundant Port on the Turbo Ring or Turbo Ring V2.
              Return 0 if not Turbo Ring or Turbo Ring V2."
        ::= { turboRingStatus 4 }

    turboRingPort1Status OBJECT-TYPE
        SYNTAX DisplayString
        ACCESS  read-only
        STATUS  current
        DESCRIPTION
             "The port status of 1st Redundant Port on the Turbo Ring or Turbo Ring V2."
        ::= { turboRingStatus 5 }

    turboRingPort2Status OBJECT-TYPE
        SYNTAX DisplayString
        ACCESS  read-only
        STATUS  current
        DESCRIPTION
             "The port status of 2nd Redundant Port on the Turbo Ring or Turbo Ring V2."
        ::= { turboRingStatus 6 }

-- -------------------------------------------------------------
-- Save Configuration
-- -------------------------------------------------------------

	saveConfiguration OBJECT IDENTIFIER ::= { swMgmt 7 }	
	
	saveConfig  OBJECT-TYPE
        SYNTAX INTEGER { 
        	save(1)
        }
        MAX-ACCESS write-only               
        STATUS current
        DESCRIPTION
            "Save the applied configuration to the NPort 6000
            series device server."
		::= { saveConfiguration 1 }
	
-- -------------------------------------------------------------
-- Restart
-- -------------------------------------------------------------

	restart OBJECT IDENTIFIER ::= { swMgmt 8 }
	
	restartPorts  OBJECT-TYPE
        SYNTAX INTEGER { 
        	port1(0), 
        	port2(1),
        	port3(2), 
        	port4(3),
        	port5(4), 
        	port6(5),
        	port7(6), 
        	port8(7),
        	port9(8), 
        	port10(9),
        	port11(10), 
        	port12(11),
        	port13(12), 
        	port14(13),
        	port15(14), 
        	port16(15),
        	port17(16),
        	port18(17),
        	port19(18),
        	port20(19),
        	port21(20),
        	port22(21),
        	port23(22),
        	port24(23),
        	port25(24),
        	port26(25),
        	port27(26),
        	port28(27),
        	port29(28),
        	port30(29),
        	port31(30),
        	port32(31)
        }
        MAX-ACCESS write-only               
        STATUS current
        DESCRIPTION
            "Restart serial port. Restarting will cause port
            reseting."
		::= { restart 1 }
		
	restartSystem  OBJECT-TYPE
        SYNTAX INTEGER { 
        	restart(1)
        }
        MAX-ACCESS write-only               
        STATUS current
        DESCRIPTION
            "Restart the NPort 6000 series device server. Be sure
            to save all of your configuration changes before
            you restart the system. Otherwise, all of the changes will be
            lost."
		::= { restart 2 }

END
