-- *****************************************************************
-- Moxa NPort S8000 MIB
--
-- Copyright (c) 2008 by Moxa Inc.
-- All rights reserved.
--
-- Version: 1.4
-- Date: 2011/05/13
-- *****************************************************************

MOXA-NPS8000-MIB DEFINITIONS ::= BEGIN
    IMPORTS
        enterprises, IpAddress, OBJECT-TYPE
        	FROM SNMPv2-SMI
          DateAndTime, TEXTUAL-CONVENTION, MacAddress, DisplayString  
        	FROM SNMPv2-TC;
        
    moxa 	OBJECT IDENTIFIER ::= { enterprises 8691 }               -- 1.3.6.1.4.1.8691
    
    nport	OBJECT IDENTIFIER ::= { moxa 2 }                         -- 1.3.6.1.4.1.8691.2
    
    nps8000   MODULE-IDENTITY
	    LAST-UPDATED "201105130000Z"
	    ORGANIZATION "Moxa Inc."
	    CONTACT-INFO
	            "Postal: Moxa Inc.
	             Fl.4, No.135,Lane 235,Pao-Chiao Rd.
	             Shing Tien City,Taipei,Taiwan,R.O.C
	          
	             Tel: +866-2-89191230 "
	             
	    DESCRIPTION
	            "The MIB module for Moxa NPort S8000 series specific information."

	    ::= { nport 12 }                                             -- 1.3.6.1.4.1.8691.2.12
    
-- ------------------------------------------------------------------------------------------------
-- groups in the MOXA-NPortS8000 MIB
-- ------------------------------------------------------------------------------------------------

swMgmt		OBJECT IDENTIFIER ::= { nps8000 1 }                      -- 1.3.6.1.4.1.8691.2.12.1    

-- ------------------------------------------------------------------------------------------------
-- Textual Conventions
-- ------------------------------------------------------------------------------------------------

PortList ::= TEXTUAL-CONVENTION
	STATUS			current
	DESCRIPTION		
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING
	
-- ------------------------------------------------------------------------------------------------
-- swMgmt group
-- ------------------------------------------------------------------------------------------------

-- ------------------------------------------------------------------------------------------------
-- overview                                                                    1.1
-- ------------------------------------------------------------------------------------------------
	
	overview OBJECT IDENTIFIER ::= { swMgmt 1 }

	modelName OBJECT-TYPE
        SYNTAX DisplayString
        MAX-ACCESS read-only
        STATUS current
        DESCRIPTION
            "NPort S8455 series: Combo switch/serial device with 4 serial ports, 3 Ethernet ports, 2 fiber ports.
             NPort S8458 series: Combo switch/serial device with 4 serial ports, 4 Ethernet ports, 4 fiber ports."
    ::= { overview 1 }

	serialNo OBJECT-TYPE
        SYNTAX DisplayString
        MAX-ACCESS read-only                
        STATUS current
        DESCRIPTION
            "The serial number of the NPort. Every NPort S8000
            series device server is assigned a unique serial
            number before it is shipped."
        ::= { overview 2 }

	firmwareVersion OBJECT-TYPE
        SYNTAX DisplayString
        MAX-ACCESS read-only                
        STATUS current
        DESCRIPTION
            "The version of the firmware currently running on
            the NPort."
        ::= { overview 3 }

    viewIpAddr OBJECT-TYPE
        SYNTAX IpAddress
        MAX-ACCESS read-only                
        STATUS current
        DESCRIPTION
            "The version of the firmware currently running on
            the NPort."
        ::= { overview 4 }

	macAddress OBJECT-TYPE
        SYNTAX DisplayString
        MAX-ACCESS read-only                
        STATUS current
        DESCRIPTION
        	"The MAC address of the NPort's Ethernet interface."
        ::= { overview 5 }
        
    upTime OBJECT-TYPE
        SYNTAX DisplayString
        MAX-ACCESS read-only               
        STATUS current
        DESCRIPTION
            "The time (in human-readable notation) since the
            system was last re-initialized."
        ::= { overview 6 }


-- ------------------------------------------------------------------------------------------------
-- Basic settings                                                              1.2
-- ------------------------------------------------------------------------------------------------
	basicSettings OBJECT IDENTIFIER ::= { swMgmt 2 }

-- ------------------------------------------------------------------------------------------------
-- Basic settings -> General Settings                                          1.2.1
-- ------------------------------------------------------------------------------------------------
	generalSettings OBJECT IDENTIFIER ::= { basicSettings 1 }

 	serverName OBJECT-TYPE
        SYNTAX DisplayString (SIZE(0..39))
        MAX-ACCESS read-write                
        STATUS current
        DESCRIPTION
        	"A text string used to identify the NPort."
        ::= { generalSettings 1 }

	serverLocation OBJECT-TYPE
        SYNTAX DisplayString (SIZE(0..80))
        MAX-ACCESS read-write                
        STATUS current
        DESCRIPTION
        	"A text string used to identify the location of the NPort. This
            option is useful for specifying the location or
            application of different NPort device servers."
        ::= { generalSettings 2 }

	serverDescription OBJECT-TYPE
        SYNTAX DisplayString (SIZE(0..39))
        MAX-ACCESS read-write                
        STATUS current
        DESCRIPTION
        	"serverDescription."
        ::= { generalSettings 3 }

	maintainerContactInfo OBJECT-TYPE
        SYNTAX DisplayString (SIZE(0..39))
        MAX-ACCESS read-write                
        STATUS current
        DESCRIPTION
        	"maintainerContactInfo."
        ::= { generalSettings 4 }

	generalSettingActive OBJECT-TYPE
        SYNTAX INTEGER { active(1)}
        MAX-ACCESS read-write                
        STATUS current
        DESCRIPTION
        	"Submit general setting."
        ::= { generalSettings 5 }

-- ------------------------------------------------------------------------------------------------
-- Basic settings -> Time settings                                             1.2.2
-- ------------------------------------------------------------------------------------------------
	timeSetting OBJECT IDENTIFIER ::= { basicSettings 2 }

    sysDateTime OBJECT-TYPE
        SYNTAX DisplayString
        MAX-ACCESS read-write               
        STATUS current
        DESCRIPTION
            "The date time of system"
        ::= { timeSetting 1 }

-- ------------------------------------------------------------------------------------------------
-- Basic settings -> Time settings -> Day Linght Saving                        1.2.2.2
-- ------------------------------------------------------------------------------------------------

    daylightSaving OBJECT IDENTIFIER ::= { timeSetting 2 }
     
    startMonth OBJECT-TYPE
        SYNTAX INTEGER  { na(0), jan(1), feb(2), mar(3), apr(4), may(5), jun(6), jul(7), aug(8), sep(9), oct(10), nov(11), dec(12)  }
        MAX-ACCESS read-write               
        STATUS current
        DESCRIPTION
            "Setting Start Month of Daylight Saving time"
        ::= { daylightSaving 1 }
    
    startWeek OBJECT-TYPE
        SYNTAX INTEGER  { na(0), week-1(1), week-2(2), week-3(3), week-4(4), week-last(6) }
        MAX-ACCESS read-write               
        STATUS current
        DESCRIPTION
            "Setting Start Week of Daylight Saving time"
        ::= { daylightSaving 2 }
        
    startDay OBJECT-TYPE
        SYNTAX INTEGER  { na(0), sun(1), mon(2), tue(3), wed(4), thu(5), fri(6), sat(7)}
        MAX-ACCESS read-write               
        STATUS current
        DESCRIPTION
            "Setting Start Day of Daylight Saving time"
        ::= { daylightSaving 3 }
       
    startHour OBJECT-TYPE
        SYNTAX INTEGER 
        MAX-ACCESS read-write               
        STATUS current
        DESCRIPTION
            "Setting Start Hour of Daylight Saving time"
        ::= { daylightSaving 4 }
        
    endMonth OBJECT-TYPE
        SYNTAX INTEGER  { na(0), jan(1), feb(2), mar(3), apr(4), may(5), jun(6), jul(7), aug(8), sep(9), oct(10), nov(11), dec(12)  }
        MAX-ACCESS read-write               
        STATUS current
        DESCRIPTION
            "Setting End Month of Daylight Saving time"
        ::= { daylightSaving 5 }
    
    endWeek OBJECT-TYPE
        SYNTAX INTEGER  { na(0), week-1(1), week-2(2), week-3(3), week-4(4), week-last(6) }
        MAX-ACCESS read-write               
        STATUS current
        DESCRIPTION
            "Setting End Week of Daylight Saving time"
        ::= { daylightSaving 6 }
        
    endDay OBJECT-TYPE
        SYNTAX INTEGER  { na(0), sun(1), mon(2), tue(3), wed(4), thu(5), fri(6), sat(7)}
        MAX-ACCESS read-write               
        STATUS current
        DESCRIPTION
            "Setting End Day of Daylight Saving time"
        ::= { daylightSaving 7 }
       
    endHour OBJECT-TYPE
        SYNTAX INTEGER
        MAX-ACCESS read-write               
        STATUS current
        DESCRIPTION
            "Setting End Hour of Daylight Saving time"
        ::= { daylightSaving 8 }
    
    offsetHours OBJECT-TYPE
        SYNTAX INTEGER  
        MAX-ACCESS read-write               
        STATUS current
        DESCRIPTION
            "Setting Offset Hours of Daylight Saving time"
        ::= { daylightSaving 9 }

-- ------------------------------------------------------------------------------------------------
-- End of Day Linght Saving
-- ------------------------------------------------------------------------------------------------

   timeZone OBJECT-TYPE
        SYNTAX INTEGER
        MAX-ACCESS read-write                
        STATUS current
        DESCRIPTION
            "The time-zone index of the NPort."
        ::= { timeSetting 3 }
            
    timeServer1 OBJECT-TYPE
        SYNTAX DisplayString
        MAX-ACCESS read-write               
        STATUS current
        DESCRIPTION
            "The first time server"
        ::= { timeSetting 4 }
    
    timeServer2 OBJECT-TYPE
        SYNTAX DisplayString
        MAX-ACCESS read-write               
        STATUS current
        DESCRIPTION
            "The second time server"
        ::= { timeSetting 5 }

    calibratePeriod OBJECT-TYPE
        SYNTAX INTEGER
        MAX-ACCESS read-write               
        STATUS current
        DESCRIPTION
            "The period (seconds) that calibrate with time server"
        ::= { timeSetting 6 }
 
 	timeSettingActive OBJECT-TYPE
        SYNTAX INTEGER { active(1)}
        MAX-ACCESS read-write                
        STATUS current
        DESCRIPTION
        	"Submit time setting."
        ::= { timeSetting 7 }


-- ------------------------------------------------------------------------------------------------
-- Basic settings -> Network settings                                          1.2.3
-- ------------------------------------------------------------------------------------------------
	networkSettings OBJECT IDENTIFIER ::= { basicSettings 3 }

	autoIPConfig OBJECT-TYPE
        SYNTAX INTEGER { disable(0), dhcp(1), bootp(2) }
        MAX-ACCESS read-write                
        STATUS current
        DESCRIPTION
            "The auto IP config."
        ::= { networkSettings 1 }
        
	serverIpAddr OBJECT-TYPE
        SYNTAX IpAddress
        MAX-ACCESS read-write                
        STATUS current
        DESCRIPTION
            "The IP Address of this server."
        ::= { networkSettings 2 }

	subMask OBJECT-TYPE
        SYNTAX IpAddress
        MAX-ACCESS read-write                
        STATUS current
        DESCRIPTION
            "The Subnet Mask of this server."
        ::= { networkSettings 3 }

	gateway OBJECT-TYPE
        SYNTAX IpAddress
        MAX-ACCESS read-write                
        STATUS current
        DESCRIPTION
            "The gateway of this server."
        ::= { networkSettings 4 }

    dnsServer1IPAddr OBJECT-TYPE
        SYNTAX IpAddress
        MAX-ACCESS read-write                
        STATUS current
        DESCRIPTION
            "The first DNS Server address."
        ::= { networkSettings 5 }

	 dnsServer2IPAddr OBJECT-TYPE
        SYNTAX IpAddress
        MAX-ACCESS read-write                
        STATUS current
        DESCRIPTION
            "The first DNS Server address."
        ::= { networkSettings 6 }

	 tcpAliveChkTime OBJECT-TYPE
        SYNTAX INTEGER
        MAX-ACCESS read-write                
        STATUS current
        DESCRIPTION
            "The TCP alive check time."
        ::= { networkSettings 7 }

	 networkSettingActive OBJECT-TYPE
        SYNTAX INTEGER { active(1)}
        MAX-ACCESS read-write                
        STATUS current
        DESCRIPTION
        	"Submit network setting."
        ::= { networkSettings 8 }

-- ------------------------------------------------------------------------------------------------
-- Serial settings                                                             1.3
-- ------------------------------------------------------------------------------------------------

    portSetting OBJECT IDENTIFIER ::= { swMgmt 3 }
  
-- ------------------------------------------------------------------------------------------------
-- Serial settings -> Operation Modes settings                                 1.3.1
-- ------------------------------------------------------------------------------------------------

	opModeSetting OBJECT IDENTIFIER ::= { portSetting 1 }

-- ------------------------------------------------------------------------------------------------
-- Serial settings -> Operation Modes settings -> Operation Modes              1.3.1.1
-- ------------------------------------------------------------------------------------------------

	opMode OBJECT IDENTIFIER ::= { opModeSetting 1 }

	opModePortTable OBJECT-TYPE							             -- 1.3.1.1.1
        SYNTAX SEQUENCE OF OpModePortEntry
        MAX-ACCESS not-accessible               
        STATUS current
        DESCRIPTION
            "The serial ports' operation mode table."
        ::= { opMode 1 }
    
    opModePortEntry OBJECT-TYPE							             -- 1.3.1.1.1.1
        SYNTAX OpModePortEntry
        MAX-ACCESS not-accessible               
        STATUS current
        DESCRIPTION
            "The serial port's operation mode entry."
        INDEX { portIndex }
        ::= { opModePortTable 1 }
        
    OpModePortEntry ::=
        SEQUENCE {
        	portIndex
        		INTEGER,
        	portMode
            	INTEGER
        }
        
    portIndex OBJECT-TYPE						
        SYNTAX INTEGER
        MAX-ACCESS read-only                
        STATUS current
        DESCRIPTION
            "The serial port index."
        ::= { opModePortEntry 1 }
        
    portMode OBJECT-TYPE	
        SYNTAX INTEGER { 
        	disable(0), 
			realCom(1),
			rfc2217(2),
			tcp-Server(3),
			tcp-Client(4),
			udp(5)
        }
        MAX-ACCESS read-write                
        STATUS current
        DESCRIPTION
            "The application of the serial port.
            Note that changing this setting may also change the
            operation mode."
        ::= { opModePortEntry 2 }
    
-- --------------------------------------------------------------------------------------
-- Serial settings -> Operation Modes settings -> application					1.3.1.2
-- --------------------------------------------------------------------------------------

	application OBJECT IDENTIFIER ::= { opModeSetting 2 }

-- --------------------------------------------------------------------------------------
-- Serial settings -> Operation Modes settings -> application -> realCom		1.3.1.2.1
-- --------------------------------------------------------------------------------------

	realcom OBJECT IDENTIFIER ::= { application 1 }

	realComTable OBJECT-TYPE	
        SYNTAX SEQUENCE OF RealComEntry
        MAX-ACCESS not-accessible               
        STATUS current
        DESCRIPTION
            "The serial ports' operation mode table."
        ::= { realcom 1 }
    
    realComEntry OBJECT-TYPE						
        SYNTAX RealComEntry
        MAX-ACCESS not-accessible               
        STATUS current
        DESCRIPTION
            "The serial port's operation mode entry."
        INDEX { portIndex }
        ::= { realComTable 1 }
        
	RealComEntry ::=
        SEQUENCE {
        	realcomMaxConnection
        		INTEGER,
        	realcomIgnoreJammedIp
            	INTEGER,
            realcomAllowDriverControl
            	INTEGER,
            realcomConnectionDownRTS
            	INTEGER,
            realcomConnectionDownDTR
            	INTEGER,
            realcomTcpAliveChkTime
            	INTEGER
        }

	realcomMaxConnection OBJECT-TYPE
        SYNTAX INTEGER
        MAX-ACCESS read-write                
        STATUS current
        DESCRIPTION
            "Max connection is usually used when the user needs
            to receive data from different hosts simultaneously.
            The factory default is 1. In this case, only one
            specific host can access this port of the NPort S8000
            series device server, and the Real COM driver on that
            host will have full control over the port.
            Max. connection = 1:
            Allows only a single host’s Real COM driver to open
            the specific NPort S8000 series device server’s
            serial port.
            Max connection = 2 to 8:
            Allows 2 to 8 hosts’ Real COM drivers to open the
            specific NPort S8000 series device server’s serial
            port, at the same time. When multiple hosts’ Real
            COM drivers open the serial port at the same time,
            the COM driver only provides a pure data tunnel
            without control ability. The serial port parameter
            will use the firmware settings instead of getting
            the settings from your application program (AP)."
        ::= { realComEntry 1 }


    realcomIgnoreJammedIp OBJECT-TYPE
        SYNTAX INTEGER { disable(0), enable(1) }
        MAX-ACCESS read-write                
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { realComEntry 2 }
        
    realcomAllowDriverControl OBJECT-TYPE
        SYNTAX INTEGER { disable(0), enable(1) }
        MAX-ACCESS read-write                
        STATUS current
        DESCRIPTION
            "If Max connection is greater than 1, NPort will
            ignore driver control commands from all connected
            hosts. However, if you set Allow driver control to
            YES, control commands will be accepted. Note that
            since the NPort S8000 series device server may get
            configuration changes from multiple hosts, the most
            recent command received will take precedence."
        ::= { realComEntry 3 }

	realcomConnectionDownRTS OBJECT-TYPE
        SYNTAX INTEGER { always-low(1), always-high(0) }
        MAX-ACCESS read-write                
        STATUS current
        DESCRIPTION
            "For some applications, serial devices must obtain
            the Ethernet link status by reading the RTS signal from the
            NPort S8000 series device server. If this setting is
            set to 'always low,' RTS will change its state to
            low if the Ethernet link is off."
        ::= { realComEntry 4 }
        
    realcomConnectionDownDTR OBJECT-TYPE
        SYNTAX INTEGER { always-low(1), always-high(0) }
        MAX-ACCESS read-write                
        STATUS current
        DESCRIPTION
            "For some applications, serial devices must obtain
            the Ethernet link status by reading the DTR signal from the
            NPort S8000 series device server. If this setting is
            set to 'goes low,' DTR will change its state to
            low if the Ethernet link is off."
        ::= { realComEntry 5 }
	
	 realcomTcpAliveChkTime OBJECT-TYPE
        SYNTAX INTEGER
        MAX-ACCESS read-write                
        STATUS current
        DESCRIPTION
          "The TCP alive check time."
        ::= { realComEntry 6 }
    

-- --------------------------------------------------------------------------------------
-- Serial settings -> Operation Modes settings -> application -> RFC 2217	1.3.1.2.2
-- --------------------------------------------------------------------------------------

	rfc2217 OBJECT IDENTIFIER ::= { application 2 }

	rfc2217Table OBJECT-TYPE							-- 1.3.1.2.2.1
        SYNTAX SEQUENCE OF Rfc2217Entry
        MAX-ACCESS not-accessible               
        STATUS current
        DESCRIPTION
            "The serial ports' operation mode table."
        ::= { rfc2217 1 }
    
    rfc2217Entry OBJECT-TYPE							-- 1.3.1.2.2.1.1
        SYNTAX Rfc2217Entry
        MAX-ACCESS not-accessible               
        STATUS current
        DESCRIPTION
            "The serial port's operation mode entry."
        INDEX { portIndex }
        ::= { rfc2217Table 1 }
        
    Rfc2217Entry ::=
        SEQUENCE {
        	rfc2217TcpPort
        		INTEGER,
        	rfc2217TcpAliveChkTime
        		INTEGER
        }

    rfc2217TcpPort OBJECT-TYPE
        SYNTAX INTEGER
        MAX-ACCESS read-write                
        STATUS current
        DESCRIPTION
            "The 'TCP port' is the TCP port that the NPort
            S8000 series device server uses to listen to
            connections, and that other devices must use to
            contact the NPort S8000 series device server.
            This setting is used in RFC2217 mode."
        ::= { rfc2217Entry 1 }
        
    rfc2217TcpAliveChkTime OBJECT-TYPE
        SYNTAX INTEGER
        MAX-ACCESS read-write                
        STATUS current
        DESCRIPTION
          "The TCP alive check time."
        ::= { rfc2217Entry 2 }
     

-- --------------------------------------------------------------------------------------
-- Serial settings -> Operation Modes settings -> application -> TCP Server	1.3.1.2.3
-- --------------------------------------------------------------------------------------

	tcpServer OBJECT IDENTIFIER ::= { application 3 }

	tcpServerTable OBJECT-TYPE							-- 1.3.1.2.3.1
        SYNTAX SEQUENCE OF TcpServerEntry
        MAX-ACCESS not-accessible               
        STATUS current
        DESCRIPTION
            "The serial ports' operation mode table."
        ::= { tcpServer 1 }
    
    tcpServerEntry OBJECT-TYPE							-- 1.3.1.2.3.1.1
        SYNTAX TcpServerEntry
        MAX-ACCESS not-accessible               
        STATUS current
        DESCRIPTION
            "The serial port's operation mode entry."
        INDEX { portIndex }
        ::= { tcpServerTable 1 }
        
    TcpServerEntry ::=
        SEQUENCE {
        	tcpServerInactivityTime
            	INTEGER,
            tcpServerMaxConnection
            	INTEGER,
            tcpServerIgnoreJammedIp
            	INTEGER,
            tcpServerAllowDriverControl
            	INTEGER,
            tcpServerTcpServerConnectionDownRTS
            	INTEGER,
            tcpServerTcpServerConnectionDownDTR
            	INTEGER,
            tcpServerTcpPort
            	INTEGER,
            tcpServerCmdPort
            	INTEGER,
            tcpServerTcpAliveChkTime
            	INTEGER
        }

    tcpServerInactivityTime OBJECT-TYPE
        SYNTAX INTEGER
        MAX-ACCESS read-write                
        STATUS current
        DESCRIPTION
            "0 ms: TCP connection is not closed when the
            serial line is idle.
            1-65535 ms: The NPort S8000 series device server
            automatically closes the TCP connection if there is
            no serial data activity for the given time. After
            the connection is closed, the NPort S8000 series
            device server starts listening for another
            TCP connection."
        ::= { tcpServerEntry 1 }
        
    tcpServerMaxConnection OBJECT-TYPE
        SYNTAX INTEGER
        MAX-ACCESS read-write                
        STATUS current
        DESCRIPTION
            "Max connection is usually used when the user needs
            to receive data from different hosts simultaneously.
            The factory default is 1. In this case, only one
            specific host can access this port of the NPort S8000
            series device server, and the Real COM driver on that
            host will have full control over the port.
            Max. connection 1:
            Allows only a single host’s Real COM driver to open
            the specific NPort S8000 series device server’s
            serial port.
            Max connection 2 to 8:
            Allows 2 to 8 hosts’ Real COM drivers to open the
            specific NPort S8000 series device server’s serial
            port, at the same time. When multiple hosts’ Real
            COM drivers open the serial port at the same time,
            the COM driver only provides a pure data tunnel
            without control ability. The serial port parameter
            will use the firmware settings instead of depending
            on your application program (AP)."
        ::= { tcpServerEntry 2 }
        
    tcpServerIgnoreJammedIp OBJECT-TYPE
        SYNTAX INTEGER { disable(0), enable(1) }
        MAX-ACCESS read-write                
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { tcpServerEntry 3 }
        
    tcpServerAllowDriverControl OBJECT-TYPE
        SYNTAX INTEGER { disable(0), enable(1) }
        MAX-ACCESS read-write                
        STATUS current
        DESCRIPTION
            "If Max connection is greater than 1, NPort will
            ignore driver control commands from all connected
            hosts. However, if you set Allow driver control to
            YES, control commands will be accepted. Note that
            since the NPort S8000 series device server may get
            configuration changes from multiple hosts, the most
            recent command received will take precedence."
        ::= { tcpServerEntry 4 }

    tcpServerTcpServerConnectionDownRTS OBJECT-TYPE
        SYNTAX INTEGER { always-low(1), always-high(0) }
        MAX-ACCESS read-write                
        STATUS current
        DESCRIPTION
            "For some applications, serial devices must obtain
            the Ethernet link status from the RTS signal sent by the
            NPort S8000 series device server. If this setting is
            set to 'goes low,' RTS will change the state to
            low if the Ethernet link is off."
        ::= { tcpServerEntry 5 }
        
    tcpServerTcpServerConnectionDownDTR OBJECT-TYPE
        SYNTAX INTEGER { always-low(1), always-high(0) }
        MAX-ACCESS read-write                
        STATUS current
        DESCRIPTION
            "For some applications, serial devices must obtain
            the Ethernet link status from the DTR signal sent by the
            NPort S8000 series device server. If this setting is
            set to 'goes low,' DTR will change the state to
            low if the Ethernet link is off."
        ::= { tcpServerEntry 6 }

    tcpServerTcpPort OBJECT-TYPE
        SYNTAX INTEGER
        MAX-ACCESS read-write                
        STATUS current
        DESCRIPTION
            "The 'TCP port' is the TCP port that the NPort
            S8000 series device server uses to listen to
            connections, and that other devices must use to
            contact the NPort S8000 series device server."
        ::= { tcpServerEntry 7 }
        
    tcpServerCmdPort OBJECT-TYPE
        SYNTAX INTEGER
        MAX-ACCESS read-write                
        STATUS current
        DESCRIPTION
            "The 'Command port' is a TCP port used to listen for 
            IP-Serial Lib commands from the host. In order to
            prevent a TCP port conflict with other applications,
            the user can set the Command port to another port
            if needed. IP-Serial Lib will automatically check
            the Command Port on the NPort S8000 series device
            server to avoid the need for the user to configure
            the program."
        ::= { tcpServerEntry 8 }
       
    tcpServerTcpAliveChkTime OBJECT-TYPE
        SYNTAX INTEGER
        MAX-ACCESS read-write                
        STATUS current
        DESCRIPTION
          "The TCP alive check time."
        ::= { tcpServerEntry 9 }


-- --------------------------------------------------------------------------------------
-- Serial settings -> Operation Modes settings -> application -> TCP Client	1.3.1.2.4
-- --------------------------------------------------------------------------------------

	tcpClient OBJECT IDENTIFIER ::= { application 4 }

	tcpClientTable OBJECT-TYPE							-- 1.3.1.2.4.1
        SYNTAX SEQUENCE OF TcpClientEntry
        MAX-ACCESS not-accessible               
        STATUS current
        DESCRIPTION
            "The serial ports' operation mode table."
        ::= { tcpClient 1 }
    
    tcpClientEntry OBJECT-TYPE							-- 1.3.1.2.4.1.1
        SYNTAX TcpClientEntry
        MAX-ACCESS not-accessible               
        STATUS current
        DESCRIPTION
            "The serial port's operation mode entry."
        INDEX { portIndex }
        ::= { tcpClientTable 1 }
        
    TcpClientEntry ::=
        SEQUENCE {
        	tcpClientInactivityTime
            	INTEGER,
            tcpClientIgnoreJammedIp
            	INTEGER,
            tcpClientDestinationAddress1
                DisplayString,
            tcpClientDestinationPort1
                INTEGER,
            tcpClientDestinationAddress2
                DisplayString,
            tcpClientDestinationPort2
            	INTEGER,
            tcpClientDestinationAddress3
                DisplayString,
            tcpClientDestinationPort3
            	INTEGER,
            tcpClientDestinationAddress4
                DisplayString,
            tcpClientDestinationPort4
            	INTEGER,
            tcpClientDesignatedLocalPort1
            	INTEGER,
            tcpClientDesignatedLocalPort2
            	INTEGER,
            tcpClientDesignatedLocalPort3
            	INTEGER,
            tcpClientDesignatedLocalPort4
            	INTEGER,
            tcpClientConnectionControl
            	INTEGER,
            tcpClientTcpAliveChkTime
            	INTEGER
        }

    tcpClientInactivityTime OBJECT-TYPE
        SYNTAX INTEGER
        MAX-ACCESS read-write                
        STATUS current
        DESCRIPTION
            "0 ms: TCP connection is not closed when the
            serial line is idle.
            1-65535 ms: The NPort S8000 series device server
            automatically closes the TCP connection if there is
            no serial data activity for the given time. After
            the connection is closed, the NPort S8000 series
            device server starts listening for another
            TCP connection."
        ::= { tcpClientEntry 1 }
        
    tcpClientIgnoreJammedIp OBJECT-TYPE
        SYNTAX INTEGER { disable(0), enable(1) }
        MAX-ACCESS read-write                
        STATUS current
        DESCRIPTION
            "Previously, when Max connection was set to a value
            greater than 1, and the serial device was
            transmitting data, if any one of the connected hosts
            stopped responding, the serial device would wait
            until the data had been transmitted successfully
            before transmitting the second group of data to all
            hosts. Currently, if you select Yes for 'Ignore
            jammed IP,' the host that is not responding will be
            ignored, but the data will still be transmitted to
            the other hosts."
        ::= { tcpClientEntry 2 }

   tcpClientDestinationAddress1 OBJECT-TYPE
		SYNTAX DisplayString (SIZE(0..40))
		MAX-ACCESS read-write                
		STATUS current
		DESCRIPTION
			"The NPort S8000 series device server can connect actively 
			to a remote host that has this IP address."
		::= { tcpClientEntry 3 }       
		
	tcpClientDestinationPort1 OBJECT-TYPE
		SYNTAX INTEGER
		MAX-ACCESS read-write                
		STATUS current
		DESCRIPTION
			"The NPort S8000 series device server can connect actively 
			to a remote host that has this TCP port number."
		::= { tcpClientEntry 4 }    
		
	tcpClientDestinationAddress2 OBJECT-TYPE
		SYNTAX DisplayString (SIZE(0..40))
		MAX-ACCESS read-write                
		STATUS current
		DESCRIPTION
			"The NPort S8000 series device server can
			connect actively to a remote host that has this IP
			address."
		::= { tcpClientEntry 5 }       
		
	tcpClientDestinationPort2 OBJECT-TYPE
		SYNTAX INTEGER
		MAX-ACCESS read-write                
		STATUS current
		DESCRIPTION
			"The NPort S8000 series device server can
			connect actively to a remote host that
			has this TCP port number."
		::= { tcpClientEntry 6 }   
		
	tcpClientDestinationAddress3 OBJECT-TYPE
		SYNTAX DisplayString (SIZE(0..40))
		MAX-ACCESS read-write                
		STATUS current
		DESCRIPTION
			"The NPort S8000 series device server can
			connect actively to a remote host that 
                        has this IP address."
		::= { tcpClientEntry 7 }       
		
	tcpClientDestinationPort3 OBJECT-TYPE
		SYNTAX INTEGER
		MAX-ACCESS read-write                
		STATUS current
		DESCRIPTION
			"The NPort S8000 series device server can
			connect actively to a remote host that
                        has this port number."
		::= { tcpClientEntry 8 } 
		
	tcpClientDestinationAddress4 OBJECT-TYPE
		SYNTAX DisplayString (SIZE(0..40))
		MAX-ACCESS read-write                
		STATUS current
		DESCRIPTION
			"The NPort S8000 series device server can
			connect actively to a remote host that
                        has this IP address."
		::= { tcpClientEntry 9 }       
		
	tcpClientDestinationPort4 OBJECT-TYPE
		SYNTAX INTEGER
		MAX-ACCESS read-write                
		STATUS current
		DESCRIPTION
			"The NPort S8000 series device server can
			connect actively to a remote host that 
                        has this port number."
		::= { tcpClientEntry 10 } 
		
	tcpClientDesignatedLocalPort1 OBJECT-TYPE
		SYNTAX INTEGER
		MAX-ACCESS read-write                
		STATUS current
		DESCRIPTION
			"The local TCP port used to connect actively to the
			remote host."
		::= { tcpClientEntry 11 } 
		
	tcpClientDesignatedLocalPort2 OBJECT-TYPE
		SYNTAX INTEGER
		MAX-ACCESS read-write                
		STATUS current
		DESCRIPTION
			"The local TCP port used to connect actively to the
			remote host."
		::= { tcpClientEntry 12 }
		
	tcpClientDesignatedLocalPort3 OBJECT-TYPE
		SYNTAX INTEGER
		MAX-ACCESS read-write                
		STATUS current
		DESCRIPTION
			"The local TCP port used to connect actively to the
			remote host."
		::= { tcpClientEntry 13 }
		
	tcpClientDesignatedLocalPort4 OBJECT-TYPE
		SYNTAX INTEGER
		MAX-ACCESS read-write                
		STATUS current
		DESCRIPTION
			"The local TCP port used to connect actively to the
			remote host."
		::= { tcpClientEntry 14 }
		
	tcpClientConnectionControl OBJECT-TYPE
		SYNTAX INTEGER {
			startup-None(257),
			anyCharacter-None(258),
			anyCharacter-InactivityTime(514),
			dsrOn-DSR-Off(1028),
			dsrOn-None(260),
			dcdOn-DCD-Off(2056),
			dcdOn-None(264) 
		}
		MAX-ACCESS read-write                
		STATUS current
		DESCRIPTION
			"Events that cause the TCP client to drop the
			connection."
		::= { tcpClientEntry 15 }
		
	tcpClientTcpAliveChkTime OBJECT-TYPE
        SYNTAX INTEGER
        MAX-ACCESS read-write                
        STATUS current
        DESCRIPTION
          "The TCP alive check time."
        ::= { tcpClientEntry 16 }
	
   
-- --------------------------------------------------------------------------------------
-- Serial settings -> Operation Modes settings -> application -> UDP			1.3.1.2.5
-- --------------------------------------------------------------------------------------

	udp OBJECT IDENTIFIER ::= { application 5 }

	udpTable OBJECT-TYPE								-- 1.3.1.2.5.1
        SYNTAX SEQUENCE OF UdpEntry
        MAX-ACCESS not-accessible               
        STATUS current
        DESCRIPTION
            "The serial ports' operation mode table."
        ::= { udp 1 }
    
    udpEntry OBJECT-TYPE								-- 1.3.1.2.5.1.1
        SYNTAX UdpEntry
        MAX-ACCESS not-accessible               
        STATUS current
        DESCRIPTION
            "The serial port's operation mode entry."
        INDEX { portIndex }
        ::= { udpTable 1 }
        
    UdpEntry ::=
        SEQUENCE {
            udpDestinationAddress1Begin
            	IpAddress,
            udpDestinationAddress1End
            	IpAddress,
            udpDestinationPort1
            	INTEGER,
            udpDestinationAddress2Begin
            	IpAddress,
            udpDestinationAddress2End
            	IpAddress,
            udpDestinationPort2
            	INTEGER,
            udpDestinationAddress3Begin
            	IpAddress,
            udpDestinationAddress3End
            	IpAddress,
            udpDestinationPort3
            	INTEGER,
            udpDestinationAddress4Begin
            	IpAddress,
            udpDestinationAddress4End
            	IpAddress,
            udpDestinationPort4
            	INTEGER,
            udpLocalListenPort
            	INTEGER
        }


	udpDestinationAddress1Begin OBJECT-TYPE
		SYNTAX IpAddress
		MAX-ACCESS read-write                
		STATUS current
		DESCRIPTION
			"The NPort S8000 series device server can actively send
			UDP packets to remote hosts whose IP
			addresses are in the range between this parameter and
			udpDestinationAddress1End."
		::= { udpEntry 1 }     
		
	udpDestinationAddress1End OBJECT-TYPE
		SYNTAX IpAddress
		MAX-ACCESS read-write                
		STATUS current
		DESCRIPTION
			"The NPort S8000 series device server can actively send
			UDP packets to remote hosts whose IP
			addresses are in the range between
			udpDestinationAddress1Begin and this parameter."
		::= { udpEntry 2 }    
		
	udpDestinationPort1 OBJECT-TYPE
		SYNTAX INTEGER
		MAX-ACCESS read-write                
		STATUS current
		DESCRIPTION
			"The NPort S8000 series device server can actively send
			UDP packets to remote hosts that have this port
			number."
		::= { udpEntry 3 }    
		
	udpDestinationAddress2Begin OBJECT-TYPE
		SYNTAX IpAddress
		MAX-ACCESS read-write                
		STATUS current
		DESCRIPTION
			"The NPort S8000 series device server can actively send
			UDP packets to remote hosts whose IP
			addresses are in the range between this parameter and
			udpDestinationAddress2End."
		::= { udpEntry 4 }     
		
	udpDestinationAddress2End OBJECT-TYPE
		SYNTAX IpAddress
		MAX-ACCESS read-write                
		STATUS current
		DESCRIPTION
			"The NPort S8000 series device server can actively send
			UDP packets to the remote hosts whose IP
			addresses are in the range between
			udpDestinationAddress2Begin and this parameter."
		::= { udpEntry 5 }    
		
	udpDestinationPort2 OBJECT-TYPE
		SYNTAX INTEGER
		MAX-ACCESS read-write                
		STATUS current
		DESCRIPTION
			"The NPort S8000 series device server can actively send
			UDP packets to the remote hosts that have this 
                        TCP port number."
		::= { udpEntry 6 } 
	
	udpDestinationAddress3Begin OBJECT-TYPE
		SYNTAX IpAddress
		MAX-ACCESS read-write                
		STATUS current
		DESCRIPTION
			"The NPort S8000 series device server can actively send
			UDP packets to remote hosts whose IP
			addresses are in the range between this parameter and
			udpDestinationAddress3End."
		::= { udpEntry 7 }     
		
	udpDestinationAddress3End OBJECT-TYPE
		SYNTAX IpAddress
		MAX-ACCESS read-write                
		STATUS current
		DESCRIPTION
			"The NPort S8000 series device server can actively send
			UDP packets to remote hosts whose IP
			addresses are in the range between
			udpDestinationAddress3Begin and this parameter."
		::= { udpEntry 8 }    
		
	udpDestinationPort3 OBJECT-TYPE
		SYNTAX INTEGER
		MAX-ACCESS read-write                
		STATUS current
		DESCRIPTION
			"The NPort S8000 series device server can actively send
			UDP packets to remote hosts that have this TCP port number."
		::= { udpEntry 9 } 
		
	udpDestinationAddress4Begin OBJECT-TYPE
		SYNTAX IpAddress
		MAX-ACCESS read-write                
		STATUS current
		DESCRIPTION
			"The NPort S8000 series device server can actively send
			UDP packets to remote hosts whose IP
			addresses are in the range between this parameter and
			udpDestinationAddress4End."
		::= { udpEntry 10 }     
		
	udpDestinationAddress4End OBJECT-TYPE
		SYNTAX IpAddress
		MAX-ACCESS read-write                
		STATUS current
		DESCRIPTION
			"The NPort S8000 series device server can actively send
			UDP packets to remote hosts whose IP
			addresses are in the range between
			udpDestinationAddress4Begin and this parameter."
		::= { udpEntry 11 }    
		
	udpDestinationPort4 OBJECT-TYPE
		SYNTAX INTEGER
		MAX-ACCESS read-write                
		STATUS current
		DESCRIPTION
			"The NPort S8000 series device server can actively send
			UDP packets to remote hosts that have this 
                        TCP port number."
		::= { udpEntry 12 } 
		
	udpLocalListenPort OBJECT-TYPE
		SYNTAX INTEGER
		MAX-ACCESS read-write                
		STATUS current
		DESCRIPTION
			"The UDP port that the NPort S8000 series device
			server listens to and that other devices must use
			to contact the NPort S8000 series device server."
		::= { udpEntry 13 } 

-- --------------------------------------------------------------------------------------
-- Serial settings -> Operation Modes settings -> Data Packing				1.3.1.3
-- --------------------------------------------------------------------------------------

	dataPacking OBJECT IDENTIFIER ::= { opModeSetting 3 }

	dataPackingPortTable OBJECT-TYPE
        SYNTAX SEQUENCE OF DataPackingPortEntry
        MAX-ACCESS not-accessible               
        STATUS current
        DESCRIPTION
            "The Data Packing table."
        ::= { dataPacking 1 }
    
    dataPackingPortEntry OBJECT-TYPE
        SYNTAX DataPackingPortEntry
        MAX-ACCESS not-accessible               
        STATUS current
        DESCRIPTION
            "The Data Packing entry."
        INDEX { portIndex }
        ::= { dataPackingPortTable 1 }
        
    DataPackingPortEntry ::=
        SEQUENCE {
            portPacketLength
                INTEGER,
            portDelimiter1Enable
                INTEGER,
            portDelimiter1
            	DisplayString,
            portDelimiter2Enable
                INTEGER,
            portDelimiter2
            	DisplayString,
            portDelimiterProcess
            	INTEGER,
            portForceTransmit
            	INTEGER
        }
        
	portPacketLength OBJECT-TYPE
        SYNTAX INTEGER 
        MAX-ACCESS read-write                
        STATUS current
        DESCRIPTION
            "If the value is 0, the Delimiter Process will be
            used, regardless of the length of the data
            packet. If the data length (in bytes) matches the
            configured value, the data will be forced out. The
            data length can be configured from 0 to 1024 bytes.
            Set to 0 if you do not need to limit the length."
        ::= { dataPackingPortEntry 1 }
        
    portDelimiter1Enable OBJECT-TYPE
		SYNTAX INTEGER {disable(0), enable(1)}
		MAX-ACCESS read-write                
		STATUS current
		DESCRIPTION
			"Enable the first delimiter character."
		::= { dataPackingPortEntry 2 }
	
	portDelimiter1 OBJECT-TYPE
		SYNTAX DisplayString (SIZE(0..2))
		MAX-ACCESS read-write                
		STATUS current
		DESCRIPTION
			"The first delimiter character, in hex decimal."
		::= { dataPackingPortEntry 3 }	
		
	portDelimiter2Enable OBJECT-TYPE
		SYNTAX INTEGER {disable(0), enable(1)}
		MAX-ACCESS read-write                
		STATUS current
		DESCRIPTION
			"Enable the second delimiter character."
		::= { dataPackingPortEntry 4 }
	
	portDelimiter2 OBJECT-TYPE
		SYNTAX DisplayString (SIZE(0..2))
		MAX-ACCESS read-write                
		STATUS current
		DESCRIPTION
			"The second delimiter character, in hex decimal."
		::= { dataPackingPortEntry 5 }	
	
	portDelimiterProcess OBJECT-TYPE
		SYNTAX INTEGER {
			doNothing(1), 
			delimiterAddOne(2),
			delimiterAddTwo(4),
			stripDelimiter(8)
			}
		MAX-ACCESS read-write                
		STATUS current
		DESCRIPTION
			"'delimiterAddOne' or 'delimiterAddTwo': The data
			will be transmitted when an additional byte (for
			'delimiterAddOne'), or an additional 2 bytes (for
			'delimiterAddTwo') of data is received after
			receiving the Delimiter.
			'stripDelimiter': When the delimiter is received,
			the Delimiter is deleted (i.e., stripped), and the
			remaining data is transmitted.
			'doNothing': The data will be transmitted when the
			delimiter is received."
		::= { dataPackingPortEntry 6 }
		
	portForceTransmit OBJECT-TYPE
		SYNTAX INTEGER
		MAX-ACCESS read-write                
		STATUS current
		DESCRIPTION
			"0: Disable the force transmit timeout.
			1 to 65535: Forces the NPort S8000 series device
			server's TCP/IP protocol software to try to pack
			serial data received during the specified time into
			the same data frame."
		::= { dataPackingPortEntry 7 }

	 opModeSettingActive OBJECT-TYPE
        SYNTAX INTEGER { active(1)}
        MAX-ACCESS read-write                
        STATUS current
        DESCRIPTION
        	"Submit opMode setting for all of serial ports."
        ::= { opModeSetting 4 }

-- -------------------------------------------------------------
-- Serial settings -> Communication Parameters settings		1.3.2
-- -------------------------------------------------------------

	comParamSetting OBJECT IDENTIFIER ::= { portSetting 2 }
	
    comParamPortTable OBJECT-TYPE
        SYNTAX SEQUENCE OF ComParamPortEntry
        MAX-ACCESS not-accessible               
        STATUS current
        DESCRIPTION
            "The Communication Parameters table."
        ::= { comParamSetting 1 }
    
    comParamPortEntry OBJECT-TYPE
        SYNTAX ComParamPortEntry
        MAX-ACCESS not-accessible
        STATUS current
        DESCRIPTION
            "The Communication Parameters entry."
        INDEX { portIndex }
        ::= { comParamPortTable 1 }
        
    ComParamPortEntry ::=
        SEQUENCE {
            portAlias
                DisplayString,
            portBaudRateManual
                INTEGER,
            portDataBits
                INTEGER,
            portStopBits
				INTEGER,
			portParity
				INTEGER,
			portFlowControl
				INTEGER,
			portFIFO
				INTEGER,
			portInterface
            	INTEGER,
            portBaudRate
                INTEGER
        }
    
    portAlias OBJECT-TYPE
		SYNTAX DisplayString (SIZE(0..16))
		MAX-ACCESS read-write                
		STATUS current
		DESCRIPTION
		"Port alias is included to allow easy identification of
		the serial devices that are connected to NPort S8000
		series device server's serial port."
		::= { comParamPortEntry 1 }
             
	portBaudRate OBJECT-TYPE
		SYNTAX INTEGER  { 
			b50(0), 
			b75(1), 
			b110(2),
			b134(3), 
			b150(4), 
			b300(5), 
			b600(6),
			b1200(7), 
			b1800(8),
			b2400(9), 
			b4800(10), 
			b7200(11), 
			b9600(12),
			b19200(13),
			b38400(14),
			b57600(15),
			b115200(16),
			b230400(17),
			b460800(18),
			b921600(19)
		}
		MAX-ACCESS read-write                
		STATUS current
		DESCRIPTION
			"The port's speed in bits per second. You can choose
			a standard baud rate by indexing."
		::= { comParamPortEntry 2 }   
        
    portDataBits OBJECT-TYPE
		SYNTAX INTEGER  { 
			bits-5(0), 
			bits-6(1), 
			bits-7(2),
			bits-8(3) 
		}
		MAX-ACCESS read-write
		STATUS current
		DESCRIPTION
			"The number of bits in a character for the port."
		::= { comParamPortEntry 3 }
		
	portStopBits OBJECT-TYPE
		SYNTAX INTEGER  {
			bits-1(0),
			bits-1dot5(1),
			bits-2(2)
		}
		MAX-ACCESS read-write
		STATUS current
		DESCRIPTION
			"The number of stop bits for the port."
		::= { comParamPortEntry 4 }
		
	portParity OBJECT-TYPE
		SYNTAX INTEGER  { 
			none(0), 
			odd(1), 
			even(2),
			mark(3), 
			space(4)
		}
		MAX-ACCESS read-write                
		STATUS current
		DESCRIPTION
			"The parity bit for the port."
		::= { comParamPortEntry 5 }
				
	portFlowControl OBJECT-TYPE
		SYNTAX INTEGER  { 
			none(0),
			rts-cts(1),
			xon-xoff(2)
		}
		MAX-ACCESS read-write                
		STATUS current
		DESCRIPTION
			"The flow-control method for the port."
		::= { comParamPortEntry 6 }
		
	portFIFO OBJECT-TYPE
		SYNTAX INTEGER  { 
			disable(0), 
			enable(1)
		}
		MAX-ACCESS read-write                
		STATUS current
		DESCRIPTION
			"Enable or disable the port's FIFO."
		::= { comParamPortEntry 7 }

    portInterface OBJECT-TYPE
		SYNTAX INTEGER  { 
			rs-232(0), 
			rs-422(1), 
			rs-485-2-wire(2),
			rs-485-4-wire(3) 
		}
		MAX-ACCESS read-write                
		STATUS current
		DESCRIPTION
			"The serial interface that the port works on."
		::= { comParamPortEntry 8 }

	portBaudRateManual OBJECT-TYPE
        SYNTAX INTEGER
        MAX-ACCESS read-write                
        STATUS current
        DESCRIPTION
            "The port's speed in bits per second. You can
            specify a baud rate manually."
        ::= { comParamPortEntry 9 }

	 comParamSettingActive OBJECT-TYPE
        SYNTAX INTEGER { active(1)}
        MAX-ACCESS read-write                
        STATUS current
        DESCRIPTION
        	"Submit communication parameters setting for all of serial ports."
        ::= { comParamSetting 2 }

-- -------------------------------------------------------------
-- Serial settings -> Serial Tos settings		1.3.3
-- -------------------------------------------------------------

	serialTosSetting OBJECT IDENTIFIER ::= { portSetting 3 }
	
    serialTosTable OBJECT-TYPE
        SYNTAX SEQUENCE OF SerialTosEntry
        MAX-ACCESS not-accessible               
        STATUS current
        DESCRIPTION
            "The Communication Parameters table."
        ::= { serialTosSetting 1 }
    
    serialTosEntry OBJECT-TYPE
        SYNTAX SerialTosEntry
        MAX-ACCESS not-accessible
        STATUS current
        DESCRIPTION
            "The Communication Parameters entry."
        INDEX { portIndex }
        ::= { serialTosTable 1 }
        
    SerialTosEntry ::=
        SEQUENCE {
			serialTosEnable
				INTEGER,
			serialTosValue
				INTEGER
        }
                
    serialTosEnable OBJECT-TYPE
		SYNTAX INTEGER  { 
			disable(0), 
			enable(1) 
		}
		MAX-ACCESS read-write
		STATUS current
		DESCRIPTION
			"The serial port TOS is enable or not."
		::= { serialTosEntry 1 }
		
	serialTosValue OBJECT-TYPE
		SYNTAX INTEGER  
		MAX-ACCESS read-write
		STATUS current
		DESCRIPTION
			"The serial port TOS value, the last 2 bits not be used."
		::= { serialTosEntry 2 }

	serialTosSettingActive OBJECT-TYPE
        SYNTAX INTEGER { active(1)}
        MAX-ACCESS read-write                
        STATUS current
        DESCRIPTION
        	"Submit serial Tos setting for all of serial ports."
        ::= { serialTosSetting 2 }
		

-- -----------------------------------------------------------------------------------------------------
-- Ethernet Settings											1.4
-- -----------------------------------------------------------------------------------------------------
    ethernetSetting OBJECT IDENTIFIER ::= { swMgmt 4 }

-- -----------------------------------------------------------------------------------------------------
-- Ethernet Settings -> Port Setting							1.4.1
-- -----------------------------------------------------------------------------------------------------

    portSettings OBJECT IDENTIFIER ::= { ethernetSetting 1 }
    
    portTable OBJECT-TYPE										-- 1.4.1.1
        SYNTAX SEQUENCE OF PortEntry
        MAX-ACCESS not-accessible               
        STATUS current
        DESCRIPTION
            "The port table."
        ::= { portSettings 1 }
    
    portEntry OBJECT-TYPE										-- 1.4.1.1.1
        SYNTAX PortEntry
        MAX-ACCESS not-accessible               
        STATUS current
        DESCRIPTION
            "The port entry."
        INDEX { portIndex-Eth }
        ::= { portTable 1 }
        
    PortEntry ::=
        SEQUENCE {
            portIndex-Eth
                INTEGER,
            portEnable
                INTEGER,
            portDesc
            	DisplayString,
            portName
                DisplayString,
            portSpeed
                INTEGER,
            portFDXFlowCtrl
                INTEGER,
            portMDI
                INTEGER
        }
    
    portIndex-Eth OBJECT-TYPE
        SYNTAX INTEGER 
        MAX-ACCESS read-only                
        STATUS current
        DESCRIPTION
            "The port index."
        ::= { portEntry 1 }

	portEnable OBJECT-TYPE
        SYNTAX INTEGER { disable(0), enable(1) }
        MAX-ACCESS read-write               
        STATUS current
        DESCRIPTION
            "This enable the port."
        ::= { portEntry 2 }
        
    portDesc OBJECT-TYPE
        SYNTAX DisplayString 
        MAX-ACCESS read-only
        STATUS current
        DESCRIPTION
            "The port description"
        ::= { portEntry 3 } 

    portName OBJECT-TYPE
        SYNTAX DisplayString (SIZE(0..63))
        MAX-ACCESS read-write               
        STATUS current
        DESCRIPTION
            "The port Name"
        ::= { portEntry 4 } 
    
    portSpeed OBJECT-TYPE
        SYNTAX INTEGER {
	        auto(0),
	        speed100M-Full(1),
	        speed100M-Half(2),
	        speed10M-Full(3),
	        speed10M-Half(4)
        }
        MAX-ACCESS read-write
        STATUS current
        DESCRIPTION
            "The port speed and duplex."
        ::= { portEntry 5 }

    portFDXFlowCtrl OBJECT-TYPE
        SYNTAX INTEGER { disable(0), enable(1)}
        MAX-ACCESS read-write               
        STATUS current
        DESCRIPTION
            "The port FDX Flow Control"
        ::= { portEntry 6 } 
    
    portMDI OBJECT-TYPE
        SYNTAX INTEGER
        {
        	na(0),
            auto(1),
            mdi(2),
            mdiX(3)
        }
        MAX-ACCESS read-write               
        STATUS current
        DESCRIPTION
            "The port MDI/MDIX."
        ::= { portEntry 7 }     

	portSettingActive OBJECT-TYPE
        SYNTAX INTEGER { active(1)}
        MAX-ACCESS read-write                
        STATUS current
        DESCRIPTION
        	"Submit all of ethernet port setting."
        ::= { portSettings 2 }

-- -----------------------------------------------------------------------------------------------------
-- Ethernet Settings -> Port Trunk								1.4.2
-- -----------------------------------------------------------------------------------------------------

    portTrunking OBJECT IDENTIFIER ::= { ethernetSetting 2 }
    
    -- trunk setting table
 
    trunkSettingTable OBJECT-TYPE
        SYNTAX SEQUENCE OF TrunkSettingEntry
        MAX-ACCESS not-accessible               
        STATUS current
        DESCRIPTION
            "Port Trunking Setting Table."
        ::= { portTrunking 1 }

    trunkSettingEntry OBJECT-TYPE
        SYNTAX TrunkSettingEntry
        MAX-ACCESS not-accessible               
        STATUS current
        DESCRIPTION
            "Port Trunking Setting Entry."
        INDEX { trunkSettingIndex }
        ::= { trunkSettingTable 1 }
        
    TrunkSettingEntry ::=
        SEQUENCE {     
            trunkSettingIndex
                INTEGER,
            trunkType
            	INTEGER,
            trunkMemberPorts
            	PortList
            }     
    
    trunkSettingIndex OBJECT-TYPE
        SYNTAX INTEGER 
        MAX-ACCESS read-only
        STATUS current
        DESCRIPTION
            "Trunking Group Index."
        ::= { trunkSettingEntry 1 }

    trunkType OBJECT-TYPE
        SYNTAX INTEGER {
        	static(1),
        	lacp(2)
        }
        MAX-ACCESS read-write
        STATUS current
        DESCRIPTION
            "Trunking Group Type."
        ::= { trunkSettingEntry 2 }

    trunkMemberPorts OBJECT-TYPE
        SYNTAX PortList
        MAX-ACCESS read-write
        STATUS current
        DESCRIPTION
            "Trunking Group Member Ports."
        ::= { trunkSettingEntry 3 }

 	portTrunkingActive OBJECT-TYPE
        SYNTAX INTEGER { active(1)}
        MAX-ACCESS read-write                
        STATUS current
        DESCRIPTION
        	"Submit port trunkning setting."
        ::= { portTrunking 2 }

-- -----------------------------------------------------------------------------------------------------
-- Ethernet Settings -> Communication Redundancy				1.4.3
-- -----------------------------------------------------------------------------------------------------
	commRedundancy OBJECT IDENTIFIER ::= { ethernetSetting 3 }

	protocolOfRedundancySetup OBJECT-TYPE
        SYNTAX INTEGER  { none(0), spanningTree(1), turboRing(2), turboRingV2(3), turboChain(4) }
        MAX-ACCESS read-write
        STATUS current
        DESCRIPTION
        "This set the redundancy protocol of this server. "
        ::= { commRedundancy 1 }                 
        
    spanningTree OBJECT IDENTIFIER ::= { commRedundancy 2 }
        
    spanningTreeBridgePriority OBJECT-TYPE
        SYNTAX INTEGER {priority-----0(0), priority--4096(4096), priority--8192(8192), priority-12288(12288),
                        priority-16384(16384), priority-20480(20480), priority-24576(24576),
                        priority-28672(28672), priority-32768(32768), priority-36864(36864),
                        priority-40960(40960), priority-45056(45056), priority-49152(49152),
                        priority-53248(53248), priority-57344(57344), priority-61440(61440)}
        MAX-ACCESS read-write               
        STATUS current
        DESCRIPTION
            "The bridge priority of spanning tree protocol."
        ::= { spanningTree 1 }
    
    spanningTreeHelloTime OBJECT-TYPE
        SYNTAX INTEGER  
        MAX-ACCESS read-write               
        STATUS current
        DESCRIPTION
            "The hello time of spanning tree protocol."
        ::= { spanningTree 2 }
    
    spanningTreeMaxAge OBJECT-TYPE
        SYNTAX INTEGER  
        MAX-ACCESS read-write               
        STATUS current
        DESCRIPTION
            "The max. age of spanning tree protocol."
        ::= { spanningTree 3 }
    
    spanningTreeForwardingDelay OBJECT-TYPE
        SYNTAX INTEGER  
        MAX-ACCESS read-write               
        STATUS current
        DESCRIPTION
            "Tje forwarding delay of spanning tree protocol."
        ::= { spanningTree 4 }
    
    spanningTreeTable OBJECT-TYPE
        SYNTAX SEQUENCE OF SpanningTreeEntry
        MAX-ACCESS not-accessible               
        STATUS current
        DESCRIPTION
            "The spanning tree table."
        ::= { spanningTree 5 }
    
    spanningTreeEntry OBJECT-TYPE
        SYNTAX SpanningTreeEntry
        MAX-ACCESS not-accessible               
        STATUS current
        DESCRIPTION
            "The spanning tree port entry."
        INDEX { spanningTreeIndex }
        ::= { spanningTreeTable 1 }
        
    SpanningTreeEntry ::=
        SEQUENCE {
            spanningTreeIndex
                INTEGER,
            enableSpanningTree
                INTEGER,
            spanningTreePortPriority
                INTEGER,
            spanningTreePortCost
                INTEGER
        }
    spanningTreeIndex OBJECT-TYPE
        SYNTAX INTEGER 
        MAX-ACCESS read-only                
        STATUS current
        DESCRIPTION
            "The index of spanning tree table."
        ::= { spanningTreeEntry 1 }      
        
    enableSpanningTree OBJECT-TYPE
        SYNTAX INTEGER { disable(0), enable(1) }
        MAX-ACCESS read-write               
        STATUS current
        DESCRIPTION
            "This enable of spanning tree protocol for this port."
        ::= { spanningTreeEntry 2 }
    
    spanningTreePortPriority OBJECT-TYPE
        SYNTAX INTEGER {priority---0(0), priority--16(16), priority--32(32), priority--48(48),
                        priority--64(64), priority--80(80), priority--96(96), priority-112(112),
                        priority-128(128), priority-144(144), priority-160(160), priority-176(176),
                        priority-192(192), priority-208(208), priority-224(224), priority-240(240)}
        MAX-ACCESS read-write               
        STATUS current
        DESCRIPTION
            "The port priority of spanning tree protocol."
        ::= { spanningTreeEntry 3 }
    
    spanningTreePortCost OBJECT-TYPE
        SYNTAX INTEGER 
        MAX-ACCESS read-write               
        STATUS current
        DESCRIPTION
            "The port cost of spanning tree protocol."
        ::= { spanningTreeEntry 4 }    
    
    turboRing OBJECT IDENTIFIER ::= { commRedundancy 3 }
 
    turboRingMasterSetup OBJECT-TYPE
        SYNTAX INTEGER  { no(0), yes(1) }
        MAX-ACCESS read-write               
        STATUS current
        DESCRIPTION
            "Set this to be Master."
        ::= { turboRing 1 }
                
    turboRingRdntPort1 OBJECT-TYPE
        SYNTAX  INTEGER
        MAX-ACCESS  read-write
        STATUS  current
        DESCRIPTION
             "The port number of 1st Redundant Port on the TURBO RING."
        ::= { turboRing 2 } 
        
    turboRingRdntPort2 OBJECT-TYPE
        SYNTAX  INTEGER
        MAX-ACCESS  read-write
        STATUS  current
        DESCRIPTION
             "The port number of 2nd Redundant Port on the TURBO RING."
        ::= { turboRing 3 } 
        
    turboRingEnableCoupling OBJECT-TYPE
        SYNTAX INTEGER  { disable(0), enable(1) }
        MAX-ACCESS read-write               
        STATUS current
        DESCRIPTION
            "This enable the ring coupling function."
        ::= { turboRing 4 }     
        
    turboRingCouplingPort OBJECT-TYPE
        SYNTAX INTEGER 
        MAX-ACCESS read-write               
        STATUS current
        DESCRIPTION
            "The coupling port of ring coupling function."
        ::= { turboRing 5 }
    
    turboRingControlPort OBJECT-TYPE
        SYNTAX INTEGER 
        MAX-ACCESS read-write               
        STATUS current
        DESCRIPTION
            "The control port of ring coupling function."
        ::= { turboRing 6 }         
        
                 
   turboRingV2 OBJECT IDENTIFIER ::= { commRedundancy 4}                                    
     
   turboRingV2Ring1 OBJECT IDENTIFIER ::= { turboRingV2 1 }    
     
   ringIndexRing1 OBJECT-TYPE
        SYNTAX INTEGER (1..2)
        MAX-ACCESS read-only                
        STATUS current
        DESCRIPTION
            "The turboRingV2 Ring Index."
        ::= { turboRingV2Ring1 1 }
                  
    ringEnableRing1 OBJECT-TYPE
        SYNTAX INTEGER  { disable(0), enable(1) }
        MAX-ACCESS read-write                
        STATUS current
        DESCRIPTION
            "The turboRingV2 Ring1 Enalbe Config."
        ::= { turboRingV2Ring1 2 }
        
    masterSetupRing1 OBJECT-TYPE
        SYNTAX INTEGER  { no(0), yes(1) }
        MAX-ACCESS read-write               
        STATUS current
        DESCRIPTION
            "Is this a Master or Slave."
        ::= { turboRingV2Ring1 3 }
               
    rdnt1stPortRing1 OBJECT-TYPE
        SYNTAX  INTEGER
        MAX-ACCESS  read-write
        STATUS  current
        DESCRIPTION
             "The port number of 1st Redundant Port on the turboRingV2."
        ::= { turboRingV2Ring1 4 } 
        
    rdnt2ndPortRing1 OBJECT-TYPE
        SYNTAX  INTEGER
        MAX-ACCESS  read-write
        STATUS current
        DESCRIPTION
             "The port number of 2nd Redundant Port on the turboRingV2."
        ::= { turboRingV2Ring1 5 }                          
 
    turboRingV2Ring2 OBJECT IDENTIFIER ::= { turboRingV2 2 }    
     
    ringIndexRing2 OBJECT-TYPE
        SYNTAX INTEGER (1..2)
        MAX-ACCESS read-only                
        STATUS current
        DESCRIPTION
            "The turboRingV2 Ring Index."
        ::= { turboRingV2Ring2 1 }
                  
    ringEnableRing2 OBJECT-TYPE
        SYNTAX INTEGER  { disable(0), enable(1) }
        MAX-ACCESS read-write                
        STATUS current
        DESCRIPTION
            "The turboRingV2 Ring2 Enalbe Config."
        ::= { turboRingV2Ring2 2 }
        
    masterSetupRing2 OBJECT-TYPE
        SYNTAX INTEGER  { no(0), yes(1) }
        MAX-ACCESS read-write               
        STATUS current
        DESCRIPTION
            "Is this a Master or Slave."
        ::= { turboRingV2Ring2 3 }
        
    rdnt1stPortRing2 OBJECT-TYPE
        SYNTAX  INTEGER
        MAX-ACCESS  read-write
        STATUS  current
        DESCRIPTION
             "The port number of 1st Redundant Port on the turboRingV2."
        ::= { turboRingV2Ring2 4 } 
        
    rdnt2ndPortRing2 OBJECT-TYPE
        SYNTAX  INTEGER
        MAX-ACCESS  read-write
        STATUS  current
        DESCRIPTION
             "The port number of 2nd Redundant Port on the turboRingV2."
        ::= { turboRingV2Ring2 5 }            
                    
    turboRingV2Coupling OBJECT IDENTIFIER ::= { turboRingV2 3 }        
    
    couplingEnable OBJECT-TYPE
        SYNTAX INTEGER  { disable(0), enable(1) }
        MAX-ACCESS read-write               
        STATUS current
        DESCRIPTION
            "Setting the ring coupling enable."
        ::= { turboRingV2Coupling 1 }     
        
    couplingMode OBJECT-TYPE
        SYNTAX INTEGER  { dualHoming(1), couplingBackup(2), couplingPrimary(3) }
        MAX-ACCESS read-write               
        STATUS current
        DESCRIPTION
            "Setting the ring coupling mode."
        ::= { turboRingV2Coupling 2 }     
        
    coupling1stPort OBJECT-TYPE
        SYNTAX INTEGER 
        MAX-ACCESS read-write               
        STATUS current
        DESCRIPTION
            "If in 'DUAL HOMING' mode,port name is 'Primary port',If in 'COUPLING' mode,port name is 'Coupling port'"
        ::= { turboRingV2Coupling 3 }
       
    coupling2ndPort OBJECT-TYPE
        SYNTAX INTEGER 
        MAX-ACCESS read-write               
        STATUS current
        DESCRIPTION
            "If in 'DUAL HOMING' mode,port name is 'Backup port',If in 'COUPLING' mode,port name is no used."
        ::= { turboRingV2Coupling 4 }
   
 	commRedundancyActive OBJECT-TYPE
        SYNTAX INTEGER { active(1)}
        MAX-ACCESS read-write                
        STATUS current
        DESCRIPTION
        	"Submit communication redundancy setting."
        ::= { commRedundancy 5 }

    turboChain OBJECT IDENTIFIER ::= { commRedundancy 6 } 
                  
    turboChainRole OBJECT-TYPE
        SYNTAX INTEGER  { head(1), member(2), tail(3) }
        MAX-ACCESS read-write                
        STATUS current
        DESCRIPTION
            "The device's role in Turbo Chain."
        ::= { turboChain 1 }
               
    turboChainPort1 OBJECT-TYPE
        SYNTAX  INTEGER
        MAX-ACCESS  read-write
        STATUS  current
        DESCRIPTION
             "If the device's role is Head, this variable assigns the Head Port.
              If the device's role is Member, this variable assigns the first Member Port.
              If the device's role is Tail, this variable assign the Tail Port."
        ::= { turboChain 2 } 

    turboChainPort2 OBJECT-TYPE
        SYNTAX  INTEGER
        MAX-ACCESS  read-write
        STATUS  current
        DESCRIPTION
             "If the device's role is Head, this variable assigns the Member Port.
              If the device's role is Member, this variable assigns the second Member Port.
              If the device's role is Tail, this variable assign the Member Port."
        ::= { turboChain 3 }                          

-- -----------------------------------------------------------------------------------------------------
-- Ethernet Settings -> Bandwidth Management					1.4.4
-- -----------------------------------------------------------------------------------------------------
    rateLimiting OBJECT IDENTIFIER ::= { ethernetSetting 4 }
    
    rateLimitingTable OBJECT-TYPE
        SYNTAX SEQUENCE OF RateLimitingEntry
        MAX-ACCESS not-accessible               
        STATUS current
        DESCRIPTION
            "The rate limiting table."
        ::= { rateLimiting 1 }
    
    rateLimitingEntry OBJECT-TYPE
        SYNTAX RateLimitingEntry
        MAX-ACCESS not-accessible               
        STATUS current
        DESCRIPTION
            "Rate limiting Entry."
        INDEX { portIndex-Eth }
        ::= { rateLimitingTable 1 }
    
    RateLimitingEntry ::=
        SEQUENCE {
            limitMode
                INTEGER,            
            lowPriLimitRate
                INTEGER,
            normalPriLimitRate
                INTEGER,            
            mediumPriLimitRate
                INTEGER,
            highPriLimitRate
                INTEGER            
            } 
    
    limitMode OBJECT-TYPE
        SYNTAX INTEGER {all(0),bmucast(1),bmcast(2),bcast(3)}
        MAX-ACCESS read-write               
        STATUS current
        DESCRIPTION
            "The limit mode."
        ::= { rateLimitingEntry 1 }  
        
    lowPriLimitRate OBJECT-TYPE
        SYNTAX INTEGER {not-limit(0),limit-128k(1),limit-256k(2),limit-512k(3),
                        limit-1M(4),limit-2M(5),limit-4M(6),limit-8M(7)}
        MAX-ACCESS read-write               
        STATUS current
        DESCRIPTION
            "The limiting rate of low priority queue."
        ::= { rateLimitingEntry 2 }  

    normalPriLimitRate OBJECT-TYPE
        SYNTAX INTEGER {not-limit(0),limit-128k(1),limit-256k(2),limit-512k(3),
                        limit-1M(4),limit-2M(5),limit-4M(6),limit-8M(7),
                        limit-16M(8)}
        MAX-ACCESS read-write               
        STATUS current
        DESCRIPTION
            "The limiting rate of normal priority queue.
            The values being equal to or double value of lowPriLimitRate are valid for set."
        ::= { rateLimitingEntry 3 }  

    mediumPriLimitRate OBJECT-TYPE
        SYNTAX INTEGER {not-limit(0),limit-128k(1),limit-256k(2),limit-512k(3),
                        limit-1M(4),limit-2M(5),limit-4M(6),limit-8M(7),
                        limit-16M(8),limit-32M(9)}
        MAX-ACCESS read-write               
        STATUS current
        DESCRIPTION
            "The limiting rate of medium priority queue.
            The values being equal to or double value of normalPriLimitRate are valid for set."
        ::= { rateLimitingEntry 4 }  

    highPriLimitRate OBJECT-TYPE
        SYNTAX INTEGER {not-limit(0),limit-128k(1),limit-256k(2),limit-512k(3),
                        limit-1M(4),limit-2M(5),limit-4M(6),limit-8M(7),
                        limit-16M(8),limit-32M(9),limit-64M(10)}
        MAX-ACCESS read-write
        STATUS current
        DESCRIPTION
            "The limiting rate of high priority queue.
            The values being equal to or double value of mediumPriLimitRate are valid for set."
        ::= { rateLimitingEntry 5 }  

 	rateLimitActive OBJECT-TYPE
        SYNTAX INTEGER { active(1)}
        MAX-ACCESS read-write                
        STATUS current
        DESCRIPTION
        	"Submit rate limit setting."
        ::= { rateLimiting 2 }

-- -----------------------------------------------------------------------------------------------------
-- Ethernet Settings -> Line Swap Fast Recovery					1.4.5
-- -----------------------------------------------------------------------------------------------------
    lineSwapFastRecovery OBJECT IDENTIFIER ::= { ethernetSetting 5 }

    lineSwapRecovery OBJECT-TYPE
        SYNTAX INTEGER  { disable(0), enable(1) }
        MAX-ACCESS read-write               
        STATUS current
        DESCRIPTION
            "This enable line-swap-fast-recovery function."
        ::= { lineSwapFastRecovery 1 }
     
 	lineSwapActive OBJECT-TYPE
        SYNTAX INTEGER { active(1)}
        MAX-ACCESS read-write                
        STATUS current
        DESCRIPTION
        	"Submit line swap fast recovery setting."
        ::= { lineSwapFastRecovery 2 }
    
-- -----------------------------------------------------------------------------------------------------
-- Ethernet Advanced Settings															1.5
-- -----------------------------------------------------------------------------------------------------
    ethernetAdvSetting OBJECT IDENTIFIER ::= { swMgmt 5 }

-- -----------------------------------------------------------------------------------------------------
-- Ethernet Advanced Settings -> Traffic Prioritization									1.5.1
-- -----------------------------------------------------------------------------------------------------
    trafficPrioritization OBJECT IDENTIFIER ::= { ethernetAdvSetting 1 }

-- -----------------------------------------------------------------------------------------------------
-- Ethernet Advanced Settings -> Traffic Prioritization -> QoS Classification			1.5.1.1
-- -----------------------------------------------------------------------------------------------------
    qosClassification OBJECT IDENTIFIER ::= { trafficPrioritization 1 }

    queuingMechanism OBJECT-TYPE
        SYNTAX INTEGER {sched-weight-fair(0),sched-strict(1)}
        MAX-ACCESS read-write               
        STATUS current
        DESCRIPTION
            "The queuing mechanism."
        ::= { qosClassification 1 }  
        
    qosPortTable OBJECT-TYPE
        SYNTAX SEQUENCE OF QosPortEntry
        MAX-ACCESS not-accessible               
        STATUS current
        DESCRIPTION
            "The QOS port table."
        ::= { qosClassification 2 }
    
    qosPortEntry OBJECT-TYPE
        SYNTAX QosPortEntry
        MAX-ACCESS not-accessible               
        STATUS current
        DESCRIPTION
            "The QOS Port Entry."
        INDEX { portIndex-Eth }
        ::= { qosPortTable 1 }
        
    QosPortEntry ::=
        SEQUENCE {
            inspectTos
                INTEGER,            
            inspectCos
                INTEGER,
            portPriority
                INTEGER
            } 
    
    inspectTos OBJECT-TYPE
        SYNTAX INTEGER {no (0),yes(1)}
        MAX-ACCESS read-write               
        STATUS current
        DESCRIPTION
            "This enable the inspection of TOS field."
        ::= { qosPortEntry 1 }  
        
    inspectCos OBJECT-TYPE
        SYNTAX INTEGER {no (0),yes(1)}
        MAX-ACCESS read-write               
        STATUS current
        DESCRIPTION
            "This enable the inspection of COS field."
        ::= { qosPortEntry 2 }  
        
    portPriority OBJECT-TYPE
       SYNTAX INTEGER {priority-0(0), priority-1(1), priority-2(2), priority-3(3),
        				priority-4(4), priority-5(5), priority-6(6), priority-7(7)
       	}
        MAX-ACCESS read-write               
        STATUS current
        DESCRIPTION
            "The deault priority of the port."
        ::= { qosPortEntry 3 }
        
 	qosClassificationActive OBJECT-TYPE
        SYNTAX INTEGER { active(1)}
        MAX-ACCESS read-write                
        STATUS current
        DESCRIPTION
        	"Submit Qos classification setting."
        ::= { qosClassification 3 }

-- -----------------------------------------------------------------------------------------------------
-- Ethernet Advanced Settings -> Traffic Prioritization -> Cos Mapping					1.5.1.2
-- -----------------------------------------------------------------------------------------------------
    cosMapping OBJECT IDENTIFIER ::= { trafficPrioritization 2 }
    
    cosMappingTable OBJECT-TYPE
        SYNTAX SEQUENCE OF CosMappingEntry
        MAX-ACCESS not-accessible               
        STATUS current
        DESCRIPTION
            "The COS mapping table."
        ::= { cosMapping 1 }
    
    cosMappingEntry OBJECT-TYPE
        SYNTAX CosMappingEntry
        MAX-ACCESS not-accessible               
        STATUS current
        DESCRIPTION
            "The COS mapping Entry."
        INDEX { cosTag}
        ::= { cosMappingTable 1 }
        
    CosMappingEntry ::=
        SEQUENCE {
            cosTag
                INTEGER,            
            cosMappedPriority
                INTEGER
            } 
    
    cosTag OBJECT-TYPE
        SYNTAX INTEGER (0..7) 
        MAX-ACCESS read-only
        STATUS current
        DESCRIPTION
            "The cos tag of TOS field."
        ::= { cosMappingEntry 1 }  
        
    cosMappedPriority OBJECT-TYPE
        SYNTAX INTEGER {low(0),normal(1),medium(2),high(3)}
        MAX-ACCESS read-write               
        STATUS current
        DESCRIPTION
            "The frame's priority corresponding to it's COS tag value."
        ::= { cosMappingEntry 2 }  

 	cosMappingActive OBJECT-TYPE
        SYNTAX INTEGER { active(1)}
        MAX-ACCESS read-write                
        STATUS current
        DESCRIPTION
        	"Submit Cos mapping setting."
        ::= { cosMapping 2 }
    
-- -----------------------------------------------------------------------------------------------------
-- Ethernet Advanced Settings -> Traffic Prioritization -> Tos/DiffServ Mapping			1.5.1.3
-- -----------------------------------------------------------------------------------------------------
    tosMapping OBJECT IDENTIFIER ::= { trafficPrioritization 3 }   
    
    tosMappingTable OBJECT-TYPE
        SYNTAX SEQUENCE OF TosMappingEntry
        MAX-ACCESS not-accessible               
        STATUS current
        DESCRIPTION
            "The TOS mapping table."
        ::= { tosMapping 1 }
    
    tosMappingEntry OBJECT-TYPE
        SYNTAX TosMappingEntry
        MAX-ACCESS not-accessible               
        STATUS current
        DESCRIPTION
            "TOS mapping Entry."
        INDEX { tosClass }
        ::= { tosMappingTable 1 }
        
    TosMappingEntry ::=
        SEQUENCE {
            tosClass
                INTEGER,            
            tosMappedPriority
                INTEGER
            } 
    
    tosClass OBJECT-TYPE
        SYNTAX INTEGER
        MAX-ACCESS read-only
        STATUS current
        DESCRIPTION
            "The TOS class of TOS field."
        ::= { tosMappingEntry 1 }  
        
    tosMappedPriority OBJECT-TYPE
        SYNTAX INTEGER {low(0),normal(1),medium(2),high(3)}
        MAX-ACCESS read-write               
        STATUS current
        DESCRIPTION
            "The frame's priority corresponding to it's TOS class value."
        ::= { tosMappingEntry 2 }  
    
 	tosMappingActive OBJECT-TYPE
        SYNTAX INTEGER { active(1)}
        MAX-ACCESS read-write                
        STATUS current
        DESCRIPTION
        	"Submit TOS mapping setting."
        ::= { tosMapping 2 }

-- -----------------------------------------------------------------------------------------------------
-- Ethernet Advanced Settings -> Virtual LAN											1.5.2
-- -----------------------------------------------------------------------------------------------------
    vlan OBJECT IDENTIFIER ::= { ethernetAdvSetting 2 }

    vlanType OBJECT-TYPE
        SYNTAX INTEGER {tagBased(0),portBased(1)}
        MAX-ACCESS read-write
        STATUS current
        DESCRIPTION
            "VLAN Type."
        ::= { vlan 1 }     

    managementVlanId OBJECT-TYPE
        SYNTAX INTEGER 
        MAX-ACCESS read-write
        STATUS current
        DESCRIPTION
            "The management VLAN id."
        ::= { vlan 2 }    
               
    vlanPortSettingTable OBJECT-TYPE
        SYNTAX SEQUENCE OF VlanPortSettingEntry
        MAX-ACCESS not-accessible               
        STATUS current
        DESCRIPTION
            "The vlan seting table of ports."
        ::= { vlan 3 }
    
    vlanPortSettingEntry OBJECT-TYPE
        SYNTAX VlanPortSettingEntry
        MAX-ACCESS not-accessible               
        STATUS current
        DESCRIPTION
            "Port Setting Entry of VLAN."
        INDEX { portIndex-Eth }
        ::= { vlanPortSettingTable 1 }
        
    VlanPortSettingEntry ::=
        SEQUENCE {
            portVlanType
                INTEGER,           
            portDefaultVid
                INTEGER,
            portFixedVid
                DisplayString,
            portForbiddenVid
                DisplayString
            } 
    
    portVlanType OBJECT-TYPE
        SYNTAX INTEGER {access(0),trunk(1)}
        MAX-ACCESS read-write
        STATUS current
        DESCRIPTION
            "The vlan type of port."
        ::= { vlanPortSettingEntry 1 }  
        
    portDefaultVid OBJECT-TYPE
        SYNTAX INTEGER (1..4094)
        MAX-ACCESS read-write               
        STATUS current
        DESCRIPTION
            "The PVID of port."
        ::= { vlanPortSettingEntry 2 }  
        
    portFixedVid OBJECT-TYPE
        SYNTAX DisplayString  (SIZE(0..320))
        MAX-ACCESS read-write               
        STATUS current
        DESCRIPTION
            "The fixed vids of (trunk) port."
        ::= { vlanPortSettingEntry 3 }  
        
    portForbiddenVid OBJECT-TYPE
        SYNTAX DisplayString (SIZE(0..320))
        MAX-ACCESS read-write               
        STATUS current
        DESCRIPTION
            "The forbidden vids of (trunk)port."
        ::= { vlanPortSettingEntry 4 }       
        
    portbaseVlanSettingTable OBJECT-TYPE
        SYNTAX SEQUENCE OF PortbaseVlanSettingEntry
        MAX-ACCESS not-accessible               
        STATUS current
        DESCRIPTION
            "Port base Vlan Setting Table."
        ::= { vlan 4 }

    portbaseVlanSettingEntry OBJECT-TYPE
        SYNTAX PortbaseVlanSettingEntry
        MAX-ACCESS not-accessible               
        STATUS current
        DESCRIPTION
            "Port base Vlan  Setting Entry."
        INDEX { portbaseVlanSettingIndex }
        ::= { portbaseVlanSettingTable 1 }
        
    PortbaseVlanSettingEntry ::=
        SEQUENCE {     
            portbaseVlanSettingIndex
                INTEGER,
            portbaseVlanMemberPorts
            	 PortList
            }     
    
    portbaseVlanSettingIndex OBJECT-TYPE
        SYNTAX INTEGER 
        MAX-ACCESS read-only
        STATUS current
        DESCRIPTION
            "port base Vlan Group Index."
        ::= { portbaseVlanSettingEntry 1 }

    portbaseVlanMemberPorts OBJECT-TYPE
        SYNTAX PortList
        MAX-ACCESS read-write
        STATUS current
        DESCRIPTION
            "port base Vlan  Group Member Ports."
        ::= { portbaseVlanSettingEntry 2 }

 	vlanActive OBJECT-TYPE
        SYNTAX INTEGER { active(1)}
        MAX-ACCESS read-write                
        STATUS current
        DESCRIPTION
        	"Submit VLAN setting."
        ::= { vlan 5 }

-- -----------------------------------------------------------------------------------------------------
-- Ethernet Advanced Settings -> Multicast Filtering									1.5.3
-- -----------------------------------------------------------------------------------------------------
	multicastFiltering OBJECT IDENTIFIER ::= { ethernetAdvSetting 3 }

-- -----------------------------------------------------------------------------------------------------
-- Ethernet Advanced Settings -> Multicast Filtering -> IGMP Snooping Setting			1.5.3.1
-- -----------------------------------------------------------------------------------------------------
    igmpSnooping OBJECT IDENTIFIER ::= { multicastFiltering 1 }
    
    enableGlobalIgmpSnooping OBJECT-TYPE
        SYNTAX INTEGER {disable(0),enable(1)}
        MAX-ACCESS read-write               
        STATUS current
        DESCRIPTION
            "This enable the IGMP snooping functon ."
        ::= { igmpSnooping 1 }  

    querierQueryInterval OBJECT-TYPE
        SYNTAX INTEGER (20..600)
        MAX-ACCESS read-write               
        STATUS current
        DESCRIPTION
            "This query interval of the querier function for this VLAN."
        ::= { igmpSnooping 2 }      
    
    igmpSnoopingSettingTable OBJECT-TYPE
        SYNTAX SEQUENCE OF IgmpSnoopingSettingEntry
        MAX-ACCESS not-accessible               
        STATUS current
        DESCRIPTION
            "The IGMP snooping setting table."
        ::= { igmpSnooping 3 }
    
    igmpSnoopingSettingEntry OBJECT-TYPE
        SYNTAX IgmpSnoopingSettingEntry
        MAX-ACCESS not-accessible               
        STATUS current
        DESCRIPTION
            "The IGMP snooping setting Entry."
        INDEX { vlanId }
        ::= { igmpSnoopingSettingTable 1 }
        
    IgmpSnoopingSettingEntry ::=
        SEQUENCE {
            enableIgmpSnooping
                INTEGER,           
            enableQuerier
                INTEGER,
            fixedMulticastQuerierPorts
                PortList
            } 
    
    enableIgmpSnooping OBJECT-TYPE
        SYNTAX INTEGER {disable(0),enable(1)}
        MAX-ACCESS read-write               
        STATUS current
        DESCRIPTION
            "This enable the IGMP snooping functon in this VLAN."
        ::= { igmpSnoopingSettingEntry 1 }  
        
    enableQuerier OBJECT-TYPE 
        SYNTAX INTEGER {disable(0),enable(1)}
        MAX-ACCESS read-write               
        STATUS current
        DESCRIPTION
            "This enable the querier function for this VLAN."
        ::= { igmpSnoopingSettingEntry 2 }  
    
    fixedMulticastQuerierPorts OBJECT-TYPE
        SYNTAX PortList
        MAX-ACCESS read-write               
        STATUS current
        DESCRIPTION
            "The ports that multicast-Querier exist."
        ::= { igmpSnoopingSettingEntry 3 }  
               
 	igmpSnoopingActive OBJECT-TYPE
        SYNTAX INTEGER { active(1)}
        MAX-ACCESS read-write                
        STATUS current
        DESCRIPTION
        	"Submit GIMP snoopong setting."
        ::= { igmpSnooping 4 }
        
-- -----------------------------------------------------------------------------------------------------
-- Ethernet Advanced Settings -> Multicast Filtering -> Static Multicast MAC			1.5.3.2
-- -----------------------------------------------------------------------------------------------------
    staticMulticast OBJECT IDENTIFIER ::= { multicastFiltering 2 }
    
    staticMulticastTable OBJECT-TYPE
        SYNTAX SEQUENCE OF StaticMulticastEntry
        MAX-ACCESS not-accessible               
        STATUS current
        DESCRIPTION
            "The static multicast table."
        ::= { staticMulticast 1 }
    
    staticMulticastEntry OBJECT-TYPE
        SYNTAX StaticMulticastEntry
        MAX-ACCESS not-accessible               
        STATUS current
        DESCRIPTION
            "Static multicast Entry."
        INDEX { staticMulticastIndex }
        ::= { staticMulticastTable 1 }
        
    StaticMulticastEntry ::=
        SEQUENCE {
        	staticMulticastIndex
        		INTEGER,
            staticMulticastAddress
                MacAddress,                
            staticMulticastPorts 
                PortList,
            staticMulticastStatus
                INTEGER
            }  
            
    staticMulticastIndex OBJECT-TYPE
        SYNTAX INTEGER
        MAX-ACCESS read-only              
        STATUS current
        DESCRIPTION
            "The static multicast index."
        ::= { staticMulticastEntry 1 }  
    
    staticMulticastAddress OBJECT-TYPE
        SYNTAX MacAddress
        MAX-ACCESS read-create              
        STATUS current
        DESCRIPTION
            "The static multicast address."
        ::= { staticMulticastEntry 2 }  
        
    staticMulticastPorts OBJECT-TYPE
        SYNTAX	PortList
        MAX-ACCESS read-create              
        STATUS current
        DESCRIPTION
            "The port map of the static multicast address."
        ::= { staticMulticastEntry 3 }      
    
    staticMulticastStatus OBJECT-TYPE
        SYNTAX INTEGER {
            active(1),
            createAndGo(4),
            createAndWait(5),
            destroy(6)
        }
        MAX-ACCESS read-create              
        STATUS current
        DESCRIPTION
            "The status is active to indicate normal.
            Use createAndGo to create new on multiple SET.
            Use createAndWait to create new on one SET all then actvie.
            Use destroy to delete this row."
        ::= { staticMulticastEntry 4 }
        

-- -----------------------------------------------------------------------------------------------------
-- Ethernet Advanced Settings -> Multicast Filtering -> GMRP							1.5.3.3
-- -----------------------------------------------------------------------------------------------------
    gmrp OBJECT IDENTIFIER ::= { multicastFiltering 3 }
    
    -- gmrp setting table    
    
    gmrpSettingTable OBJECT-TYPE
        SYNTAX SEQUENCE OF GmrpSettingEntry
        MAX-ACCESS not-accessible               
        STATUS current
        DESCRIPTION
            "The GMRP setting table."
        ::= { gmrp 1 }
    
    gmrpSettingEntry OBJECT-TYPE
        SYNTAX GmrpSettingEntry
        MAX-ACCESS not-accessible               
        STATUS current
        DESCRIPTION
            "The GMRP Setting Entry."
        INDEX { portIndex-Eth }
        ::= { gmrpSettingTable 1 }
        
    GmrpSettingEntry ::=
        SEQUENCE {   
            enableGMRP
                INTEGER
        } 
    
    enableGMRP OBJECT-TYPE
        SYNTAX INTEGER {
        	disable(0),
        	enable(1)
        }
        MAX-ACCESS read-write              
        STATUS current
        DESCRIPTION
            "Enable/Disable GMRP."
        ::= { gmrpSettingEntry 1 }       

 	gmrpActive OBJECT-TYPE
        SYNTAX INTEGER { active(1)}
        MAX-ACCESS read-write                
        STATUS current
        DESCRIPTION
        	"Submit GMRP setting."
        ::= { gmrp 2 }
    
-- -----------------------------------------------------------------------------------------------------
-- Ethernet Advanced Settings -> Set Device IP											1.5.4
-- -----------------------------------------------------------------------------------------------------
    setDeviceIp OBJECT IDENTIFIER ::= { ethernetAdvSetting 4 }
        
    setDevIpTable OBJECT-TYPE
        SYNTAX SEQUENCE OF SetDevIpEntry
        MAX-ACCESS not-accessible               
        STATUS current
        DESCRIPTION
            "The set devvice IP table."
        ::= { setDeviceIp 1 }
    
    setDevIpEntry OBJECT-TYPE
        SYNTAX SetDevIpEntry
        MAX-ACCESS not-accessible               
        STATUS current
        DESCRIPTION
            "The set devvice IP table entry."
        INDEX { setDevIpIndex }
        ::= { setDevIpTable 1 }
        
    SetDevIpEntry ::=
        SEQUENCE {
            setDevIpIndex
                INTEGER,
            setDevIpCurrentIpofDevice
                DisplayString,
            setDevIpPresentBy
                INTEGER,
            setDevIpDedicatedIp
                IpAddress
        }
    setDevIpIndex OBJECT-TYPE
        SYNTAX INTEGER 
        MAX-ACCESS read-only                
        STATUS current
        DESCRIPTION
            "The set devvice IP index."
        ::= { setDevIpEntry 1 }
    
    setDevIpCurrentIpofDevice OBJECT-TYPE
        SYNTAX DisplayString
        MAX-ACCESS read-only                
        STATUS current
        DESCRIPTION
            "The current IP address of connected to this port."
        ::= { setDevIpEntry 2 }
    
    setDevIpPresentBy OBJECT-TYPE
        SYNTAX INTEGER
            {
            no(0),
            dhcpClient(1),
            rarp(2),
            bootp(4)
            }
        MAX-ACCESS read-only                
        STATUS current
        DESCRIPTION
            "The protocol used that assigning IP to the device."
        ::= { setDevIpEntry 3 }
    
    setDevIpDedicatedIp OBJECT-TYPE
        SYNTAX IpAddress 
        MAX-ACCESS read-write               
        STATUS current
        DESCRIPTION
            "The IP address when assign to the device connected to this port."
        ::= { setDevIpEntry 4 } 

 	setDeviceIpActive OBJECT-TYPE
        SYNTAX INTEGER { active(1)}
        MAX-ACCESS read-write                
        STATUS current
        DESCRIPTION
        	"Submit automatic set device IP by DHCP/Bootp/RARP and DHCP relay agent setting."
        ::= { setDeviceIp 2 }
        
	dhcpServer1 OBJECT-TYPE
        SYNTAX DisplayString (SIZE(0..40))
        MAX-ACCESS read-write                
        STATUS current
        DESCRIPTION
        	"The IP address1 of the relay agent."
        ::= { setDeviceIp 3 }

	dhcpServer2 OBJECT-TYPE
        SYNTAX DisplayString (SIZE(0..40))
        MAX-ACCESS read-write                
        STATUS current
        DESCRIPTION
        	"The IP address2 of the relay agent."
        ::= { setDeviceIp 4 }
        
	dhcpServer3 OBJECT-TYPE
        SYNTAX DisplayString (SIZE(0..40))
        MAX-ACCESS read-write                
        STATUS current
        DESCRIPTION
        	"The IP address3 of the relay agent."
        ::= { setDeviceIp 5 }
        
	dhcpServer4 OBJECT-TYPE
        SYNTAX DisplayString (SIZE(0..40))
        MAX-ACCESS read-write                
        STATUS current
        DESCRIPTION
        	"The IP address4 of the relay agent."
        ::= { setDeviceIp 6 }
        
	DHCPOption82 OBJECT IDENTIFIER ::= { setDeviceIp 7 }

	enableOption82 OBJECT-TYPE
        SYNTAX INTEGER { disable(0), enable(1) }
        MAX-ACCESS read-write                
        STATUS current
        DESCRIPTION
        	"The Option 82 information contains 2 sub-options: Circuit ID and Remote ID, which define the relationship between end device IP and the DHCP Option 82 server."
        ::= { DHCPOption82 1 }
        
	option82Type OBJECT-TYPE
        SYNTAX INTEGER { IP(0), MAC(1), Circuit-ID(2), other(3) }
        MAX-ACCESS read-write                
        STATUS current
        DESCRIPTION
        	"The type of DHCP option 82."
        ::= { DHCPOption82 2 }
        
	option82Value OBJECT-TYPE
        SYNTAX DisplayString (SIZE(0..12))
        MAX-ACCESS read-write                
        STATUS current
        DESCRIPTION
        	"The value of DHCP option 82."
        ::= { DHCPOption82 3 }
        
	option82Display OBJECT-TYPE
        SYNTAX DisplayString
        MAX-ACCESS read-only             
        STATUS current
        DESCRIPTION
        	"The display of DHCP option 82."
        ::= { DHCPOption82 4 }
        
	dhcpFunctionTable OBJECT-TYPE
        SYNTAX SEQUENCE OF dhcpFunctionEntry
        MAX-ACCESS not-accessible               
        STATUS current
        DESCRIPTION
            "DHCP Function Table."
        ::= { DHCPOption82 5 }
        
	dhcpFunctionEntry OBJECT-TYPE
        SYNTAX dhcpFunctionEntry
        MAX-ACCESS not-accessible               
        STATUS current
        DESCRIPTION
            "The DHCP Function Table entry."
        INDEX { dhcpPortIndex }
        ::= { dhcpFunctionTable 1 }
        
	dhcpPortIndex OBJECT-TYPE
        SYNTAX INTEGER 
        MAX-ACCESS read-only                
        STATUS current
        DESCRIPTION
            "The DHCP Function Table index."
        ::= { dhcpFunctionEntry 1 }
        
	dhcpPortCirduitID OBJECT-TYPE
        SYNTAX DisplayString 
        MAX-ACCESS read-only                
        STATUS current
        DESCRIPTION
            "The DHCP Function Table Cirduit-ID."
        ::= { dhcpFunctionEntry 2 }
      
	dhcpPortO82enable OBJECT-TYPE
        SYNTAX INTEGER { disable(0), enable(1) }
        MAX-ACCESS read-write                
        STATUS current
        DESCRIPTION
            "The port enable of DHCP Function Table."
        ::= { dhcpFunctionEntry 3 }

-- -----------------------------------------------------------------------------------------------------
-- System Management																1.6
-- -----------------------------------------------------------------------------------------------------
    systemManagement OBJECT IDENTIFIER ::= { swMgmt 6 }

-- -----------------------------------------------------------------------------------------------------
-- System Management -> Misc. Network Settings										1.6.1
-- -----------------------------------------------------------------------------------------------------
    miscNetwork OBJECT IDENTIFIER ::= { systemManagement 1 }


-- -----------------------------------------------------------------------------------------------------
-- System Management -> Misc. Network Settings -> Accessible IP List				1.6.1.1
-- -----------------------------------------------------------------------------------------------------

    accessibleIP OBJECT IDENTIFIER ::= { miscNetwork 1 }
    
    enableAccessibleIP OBJECT-TYPE
        SYNTAX INTEGER  { disable(0), enable(1) }
        MAX-ACCESS read-write               
        STATUS current
        DESCRIPTION
            "Enable the accessible IP address list."
        ::= { accessibleIP 1 }
        
    accessibleIpTable OBJECT-TYPE
        SYNTAX SEQUENCE OF AccessibleIpEntry
        MAX-ACCESS not-accessible               
        STATUS current
        DESCRIPTION
            "accessibleIP."
        ::= { accessibleIP 2 }
    
    accessibleIpEntry OBJECT-TYPE
        SYNTAX AccessibleIpEntry
        MAX-ACCESS not-accessible               
        STATUS current
        DESCRIPTION
            "Accessible IP address entry."
        INDEX { accessibleIpIndex }
        ::= { accessibleIpTable 1 }
        
    AccessibleIpEntry ::=
        SEQUENCE {
        	accessibleIpIndex
        		 INTEGER,
            accessibleIpAddress
                IpAddress,
            accessibleIpNetMask
                IpAddress
        }                        
        
    accessibleIpIndex OBJECT-TYPE
        SYNTAX INTEGER
        MAX-ACCESS read-only
        STATUS current           
        DESCRIPTION
            "Accessible IP list index."
        ::= { accessibleIpEntry 1 }
        
    accessibleIpAddress OBJECT-TYPE
        SYNTAX IpAddress
        MAX-ACCESS read-write
        STATUS current           
        DESCRIPTION
            "Accessible IP address"
        ::= { accessibleIpEntry 2 } 
    
    accessibleIpNetMask OBJECT-TYPE
        SYNTAX IpAddress
        MAX-ACCESS read-write              
        STATUS current
        DESCRIPTION
            "Accessible IP netmask."
        ::= { accessibleIpEntry 3 }     

 	accessibleIPActive OBJECT-TYPE
        SYNTAX INTEGER { active(1)}
        MAX-ACCESS read-write
        STATUS current
        DESCRIPTION
        	"Submit accessible IP list setting."
        ::= { accessibleIP 3 }

-- -----------------------------------------------------------------------------------------------------
-- System Management -> Misc. Network Settings -> syslog server					1.6.1.2
-- -----------------------------------------------------------------------------------------------------

    syslogSetting OBJECT IDENTIFIER ::= { miscNetwork 2 }
    
    syslogServer1 OBJECT-TYPE
        SYNTAX DisplayString
        MAX-ACCESS read-write               
        STATUS current
        DESCRIPTION
            "The syslog server 1"
        ::= { syslogSetting 1 }
    
    syslogServer1port OBJECT-TYPE
        SYNTAX INTEGER
        MAX-ACCESS read-write               
        STATUS current
        DESCRIPTION
            "The syslog server 1 port"
        ::= { syslogSetting 2 }
        
    syslogServer2 OBJECT-TYPE
        SYNTAX DisplayString
        MAX-ACCESS read-write               
        STATUS current
        DESCRIPTION
            "The syslog server 2"
        ::= { syslogSetting 3 }
    
    syslogServer2port OBJECT-TYPE
        SYNTAX INTEGER
        MAX-ACCESS read-write               
        STATUS current
        DESCRIPTION
            "The syslog server 2 port"
        ::= { syslogSetting 4 }
        
    syslogServer3 OBJECT-TYPE
        SYNTAX DisplayString
        MAX-ACCESS read-write               
        STATUS current
        DESCRIPTION
            "The syslog server 3"
        ::= { syslogSetting 5 }
    
    syslogServer3port OBJECT-TYPE
        SYNTAX INTEGER
        MAX-ACCESS read-write               
        STATUS current
        DESCRIPTION
            "The syslog server 3 port"
        ::= { syslogSetting 6 }    

 	syslogSettingActive OBJECT-TYPE
        SYNTAX INTEGER { active(1)}
        MAX-ACCESS read-write
        STATUS current
        DESCRIPTION
        	"Submit syslog server setting."
        ::= { syslogSetting 7 }

-- -----------------------------------------------------------------------------------------------------
-- System Management -> Misc. Network Settings -> Local User Database				1.6.1.3
-- -----------------------------------------------------------------------------------------------------
--    localUserDB OBJECT IDENTIFIER ::= { miscNetwork 3 }


-- -----------------------------------------------------------------------------------------------------
-- System Management -> Port Access Control											1.6.2
-- -----------------------------------------------------------------------------------------------------
    portAccessControl OBJECT IDENTIFIER ::= { systemManagement 2 }
    
-- -----------------------------------------------------------------------------------------------------
-- System Management -> Port Access Control -> 	static port lock 					1.6.2.1
-- -----------------------------------------------------------------------------------------------------
    staticPortLock OBJECT IDENTIFIER ::= { portAccessControl 1 }
    
    staticPortLockAddress OBJECT-TYPE
        SYNTAX MacAddress
        MAX-ACCESS read-create              
        STATUS current
        DESCRIPTION
            "The static port lock address."
        ::= { staticPortLock 1 }  
        
    staticPortLockPort OBJECT-TYPE
        SYNTAX INTEGER 
        MAX-ACCESS read-create              
        STATUS current
        DESCRIPTION
            "The port of the static port lock address."
        ::= { staticPortLock 2 }  

    staticPortLockStatus OBJECT-TYPE
        SYNTAX INTEGER {
            active(1),
            createAndGo(4)
        }
        MAX-ACCESS read-create
        STATUS current
        DESCRIPTION
            "The status is active to indicate normal.
            Use createAndGo to create new on multiple SET."
        ::= { staticPortLock 3 }


-- -----------------------------------------------------------------------------------------------------
-- System Management -> Port Access Control -> 	dot1x			 					1.6.2.2
-- -----------------------------------------------------------------------------------------------------
   dot1x OBJECT IDENTIFIER ::= { portAccessControl 2 }
    
    -- ieee 802.1x global settings    
    
    dataBaseOption OBJECT-TYPE
        SYNTAX INTEGER {
            local(1),
            radius(2),
            radius-local(3)
        }
        MAX-ACCESS read-write               
        STATUS current
        DESCRIPTION
            "Set IEEE 802.1X database option."
        ::= { dot1x 1 }
        
    radiusServer OBJECT-TYPE
        SYNTAX DisplayString
        MAX-ACCESS read-write               
        STATUS current
        DESCRIPTION
            "Set Radius Server IP Address/Domain name."
        ::= { dot1x 2 }

    radiusPort OBJECT-TYPE
        SYNTAX INTEGER (1..65535)
        MAX-ACCESS read-write               
        STATUS current
        DESCRIPTION
            "Set Radius Port."
        ::= { dot1x 3 }

    radiusSharedKey OBJECT-TYPE
        SYNTAX DisplayString
        MAX-ACCESS read-write               
        STATUS current
        DESCRIPTION
            "Set Radius Shared Key."
        ::= { dot1x 4 }

    dot1xReauthEnable OBJECT-TYPE
        SYNTAX INTEGER {
        	disable(0),
        	enable(1)
        }
        MAX-ACCESS read-write               
        STATUS current
        DESCRIPTION
            "Enable/Disable IEEE 802.1X Re-authentication."
        ::= { dot1x 5 }

    dot1xReauthPeriod OBJECT-TYPE
        SYNTAX INTEGER (60..3600)
        MAX-ACCESS read-write               
        STATUS current
        DESCRIPTION
            "Set IEEE 802.1X Re-authentication Period."
        ::= { dot1x 6 }
    
    -- ieee 802.1X port setting table
    
    dot1xSettingTable OBJECT-TYPE
        SYNTAX SEQUENCE OF Dot1xSettingEntry
        MAX-ACCESS not-accessible               
        STATUS current
        DESCRIPTION
            "IEEE 802.1X Port Setting Table."
        ::= { dot1x 7 }
    
    dot1xSettingEntry OBJECT-TYPE
        SYNTAX Dot1xSettingEntry
        MAX-ACCESS not-accessible               
        STATUS current
        DESCRIPTION
            "IEEE 802.1X Port Setting Entry."
        INDEX { portIndex-Eth }
        ::= { dot1xSettingTable 1 }
        
    Dot1xSettingEntry ::=
        SEQUENCE {     
            enableDot1X
                INTEGER
            }     
    
    enableDot1X OBJECT-TYPE
        SYNTAX INTEGER {
        	disable(0),
        	enable(1)
        }
        MAX-ACCESS read-write
        STATUS current
        DESCRIPTION
            "Enable/Disable IEEE 802.1X."
        ::= { dot1xSettingEntry 1 }   
        
        
 	dot1xActive OBJECT-TYPE
        SYNTAX INTEGER { active(1)}
        MAX-ACCESS read-write
        STATUS current
        DESCRIPTION
        	"Submit 802.1X setting."
        ::= { dot1x 8 }

-- -----------------------------------------------------------------------------------------------------
-- System Management -> Auto Warning Settings												1.6.3
-- -----------------------------------------------------------------------------------------------------
	autoWarming OBJECT IDENTIFIER ::= { systemManagement 3 }
-- -----------------------------------------------------------------------------------------------------
-- System Management -> Auto Warning Settings -> E-mail Alert								1.6.3.1
-- -----------------------------------------------------------------------------------------------------
    emailAlert OBJECT IDENTIFIER ::= { autoWarming 1 }

    emailWarningMailServer OBJECT-TYPE
        SYNTAX DisplayString
        MAX-ACCESS read-write
        STATUS current
        DESCRIPTION
            "The email server's Ip Address/Domain name of email warning function."
        ::= { emailAlert 1 }
        
    emailWarningFromEmail OBJECT-TYPE
        SYNTAX DisplayString
        MAX-ACCESS read-write
        STATUS current
        DESCRIPTION
            "The e-mail address to be filled in the 'From' field of the auto-warning e-mail."
        ::= { emailAlert 2 }
        
    emailWarningFirstEmailAddr OBJECT-TYPE
        SYNTAX DisplayString
        MAX-ACCESS read-write
        STATUS current
        DESCRIPTION
            "The first email address of email warning function."
        ::= { emailAlert 3 }
        
    emailWarningSecondEmailAddr OBJECT-TYPE
        SYNTAX DisplayString
        MAX-ACCESS read-write
        STATUS current
        DESCRIPTION
            "The second email address of email warning function."
        ::= { emailAlert 4 }
        
    emailWarningThirdEmailAddr OBJECT-TYPE
        SYNTAX DisplayString
        MAX-ACCESS read-write
        STATUS current
        DESCRIPTION
            "The third email address of email warning function."
        ::= { emailAlert 5 }
        
    emailWarningFourthEmailAddr OBJECT-TYPE
        SYNTAX DisplayString
        MAX-ACCESS read-write
        STATUS current
        DESCRIPTION
            "The fourth email address of email warning function."
        ::= { emailAlert 6 }
 
 	emailAlertActive OBJECT-TYPE
        SYNTAX INTEGER { active(1)}
        MAX-ACCESS read-write
        STATUS current
        DESCRIPTION
        	"Submit EMail alert setting."
        ::= { emailAlert 7 }

-- -----------------------------------------------------------------------------------------------------
-- System Management -> Auto Warning Settings -> SNMP      									1.6.3.2
-- -----------------------------------------------------------------------------------------------------
    snmp OBJECT IDENTIFIER ::= { autoWarming 2 }

    snmpReadCommunity OBJECT-TYPE
        SYNTAX DisplayString (SIZE(0..30))
        MAX-ACCESS read-write
        STATUS current
        DESCRIPTION
            "The SNMP read community name"
        ::= { snmp 1 }

    trapServerAddr1 OBJECT-TYPE
        SYNTAX DisplayString (SIZE(0..30))
        MAX-ACCESS read-write               
        STATUS current
        DESCRIPTION
            "The IP address/Domain name of SNMP trap server"
        ::= { snmp 2 }

    snmpTrapCommunity1 OBJECT-TYPE
        SYNTAX DisplayString (SIZE(0..30))
        MAX-ACCESS read-write
        STATUS current
        DESCRIPTION
            "The SNMP trap community name"
        ::= { snmp 3 }

    trap2ServerAddr OBJECT-TYPE
        SYNTAX DisplayString (SIZE(0..30))
        MAX-ACCESS read-write               
        STATUS current
        DESCRIPTION
            "The IP address/Domain name of Second SNMP trap server"
        ::= { snmp 4 }

    snmpTrap2Community OBJECT-TYPE
        SYNTAX DisplayString (SIZE(0..30))
        MAX-ACCESS read-write
        STATUS current
        DESCRIPTION
            "The Second SNMP trap community name"
        ::= { snmp 5 }

 	snmpActive OBJECT-TYPE
        SYNTAX INTEGER { active(1)}
        MAX-ACCESS read-write
        STATUS current
        DESCRIPTION
        	"Submit SNMP setting."
        ::= { snmp 6 }
        
	SnmpInformEnable OBJECT-TYPE
        SYNTAX INTEGER { trap(0), inform(1) }
        MAX-ACCESS read-write
        STATUS current
        DESCRIPTION
        	"Enable snmp inform."
        ::= { snmp 7 }
       
	SnmpInformRetries OBJECT-TYPE
       SYNTAX INTEGER (1..99)
        MAX-ACCESS read-write
        STATUS current
        DESCRIPTION
        	"Retries of snmp inform."
        ::= { snmp 8 }
        
	SnmpInformTimeout OBJECT-TYPE
       SYNTAX INTEGER (1..300)
        MAX-ACCESS read-write
        STATUS current
        DESCRIPTION
        	"Timeout of snmp inform."
        ::= { snmp 9 }

-- -----------------------------------------------------------------------------------------------------
-- System Management -> Auto Warning Settings -> E-mail Event Setting						1.6.3.3
-- -----------------------------------------------------------------------------------------------------
    emailWarningEventType OBJECT IDENTIFIER ::= { autoWarming 3 }

    emailWarningEventServerColdStart OBJECT-TYPE
        SYNTAX INTEGER  { disable(0), enable(1) }
        MAX-ACCESS read-write
        STATUS current
        DESCRIPTION
            "The server cold start event of email warning function."
        ::= { emailWarningEventType 1 }
        
    emailWarningEventServerWarmStart OBJECT-TYPE
        SYNTAX INTEGER  { disable(0), enable(1) }
        MAX-ACCESS read-write
        STATUS current
        DESCRIPTION
            "The server warm start event of email warning function."
        ::= { emailWarningEventType 2 }

    emailWarningEventPowerOn2Off OBJECT-TYPE
        SYNTAX INTEGER  { disable(0), enable(1) }
        MAX-ACCESS read-write
        STATUS current
        DESCRIPTION
            "The power on event of email warning function."
        ::= { emailWarningEventType 3 }
        
    emailWarningEventPowerOff2On OBJECT-TYPE
        SYNTAX INTEGER  { disable(0), enable(1) }
        MAX-ACCESS read-write
        STATUS current
        DESCRIPTION
            "The power off event of email warning function."
        ::= { emailWarningEventType 4}
    
    emailWarningEventDiTable OBJECT-TYPE
        SYNTAX SEQUENCE OF EmailWarningEventDiEntry
        MAX-ACCESS not-accessible               
        STATUS current
        DESCRIPTION
            "The DI table of the email warning event."
        ::= { emailWarningEventType 5 }
    
    emailWarningEventDiEntry OBJECT-TYPE
        SYNTAX EmailWarningEventDiEntry
        MAX-ACCESS not-accessible               
        STATUS current
        DESCRIPTION
            "The DI table entry of the email warning event."
        INDEX { diIndex }
        ::= { emailWarningEventDiTable 1 }
        
    EmailWarningEventDiEntry ::=
        SEQUENCE {
            emailWarningEventDiInputOn2Off
                INTEGER,
            emailWarningEventDiInputOff2On
                INTEGER
        }

    emailWarningEventDiInputOn2Off OBJECT-TYPE
        SYNTAX INTEGER  { disable(0), enable(1) }
        MAX-ACCESS read-write
        STATUS current
        DESCRIPTION
            "The DI input off event of email warning function ."
        ::= { emailWarningEventDiEntry 1 }
        
    emailWarningEventDiInputOff2On OBJECT-TYPE
        SYNTAX INTEGER  { disable(0), enable(1) }
        MAX-ACCESS read-write
        STATUS current
        DESCRIPTION
            "The DI input on event of email warning function."
        ::= { emailWarningEventDiEntry 2 }  


        
    emailWarningEventConfigChange OBJECT-TYPE
        SYNTAX INTEGER  { disable(0), enable(1) }
        MAX-ACCESS read-write
        STATUS current
        DESCRIPTION
            "The configuration changed event of email warning function."
        ::= { emailWarningEventType 6 }
        
        
    emailWarningEventAuthFail OBJECT-TYPE
        SYNTAX INTEGER  { disable(0), enable(1) }
        MAX-ACCESS read-write
        STATUS current
        DESCRIPTION
            "The authentication fail event of email warning function."
        ::= { emailWarningEventType 7 }
        
    emailWarningEventTopologyChanged OBJECT-TYPE
        SYNTAX INTEGER  { disable(0), enable(1) }
        MAX-ACCESS read-write
        STATUS current
        DESCRIPTION
            "The communication redundancy topology changed event of email warning function."
        ::= { emailWarningEventType 8 }     
        
        
    emailWarningEventSerialPortTable OBJECT-TYPE
        SYNTAX SEQUENCE OF EmailWarningEventSerialPortEntry
        MAX-ACCESS not-accessible               
        STATUS current
        DESCRIPTION
            "The port table of the email warning event."
        ::= { emailWarningEventType 9 }
    
    emailWarningEventSerialPortEntry OBJECT-TYPE
        SYNTAX EmailWarningEventSerialPortEntry
        MAX-ACCESS not-accessible               
        STATUS current
        DESCRIPTION
            "The port table entry of the email warning event."
        INDEX { portIndex }        
        ::= { emailWarningEventSerialPortTable 1 }
        
    EmailWarningEventSerialPortEntry ::=
        SEQUENCE {
            emailWarningEventSerailDCDChange
                INTEGER,
            emailWarningEventSerailDSRChange
                INTEGER
        }  
        
    emailWarningEventSerailDCDChange OBJECT-TYPE
        SYNTAX INTEGER { disable(0), enable(1)}
        MAX-ACCESS read-write
        STATUS current
        DESCRIPTION
            "A change in the DCD (Data Carrier Detect) signal
            indicates that the modem connection status has
            changed. For example, if the DCD signal changes to
            low, it indicates that the connection line is down.
            When the DCD signal changes to low, the NPort S8000
            series device server will immediately send an e-mail
            message."
        ::= { emailWarningEventSerialPortEntry 1 }
  
    emailWarningEventSerailDSRChange OBJECT-TYPE
        SYNTAX INTEGER { disable(0), enable(1)}
        MAX-ACCESS read-write
        STATUS current
        DESCRIPTION
            "A change in the DSR (Data Set Ready) signal
            indicates that the data communication equipment is
            powered off. For example, if the DSR signal changes
            to low, it indicates that the data communication
            equipment is powered down. When the DSR signal
            changes to low, the NPort S8000 series device server
            will immediately send an e-mail message."
        ::= { emailWarningEventSerialPortEntry 2 }        
        
    
    emailWarningEventEthernetPortTable OBJECT-TYPE
        SYNTAX SEQUENCE OF EmailWarningEventEthernetPortEntry
        MAX-ACCESS not-accessible               
        STATUS current
        DESCRIPTION
            "The port table of the email warning event."
        ::= { emailWarningEventType 10 }
    
    emailWarningEventEthernetPortEntry OBJECT-TYPE
        SYNTAX EmailWarningEventEthernetPortEntry
        MAX-ACCESS not-accessible               
        STATUS current
        DESCRIPTION
            "The port table entry of the email warning event."
        INDEX { portIndex-Eth }        
        ::= { emailWarningEventEthernetPortTable 1 }
        
    EmailWarningEventEthernetPortEntry ::=
        SEQUENCE {
            emailWarningEventEthernetPortLinkOn
                INTEGER,
            emailWarningEventEthernetPortLinkOff
                INTEGER,
            emailWarningEventEthernetPortTrafficOverload
                INTEGER,
            emailWarningEventEthernetPortTrafficThreshold
                INTEGER,
            emailWarningEventEthernetPortTrafficDuration
                INTEGER             
        }
        
    emailWarningEventEthernetPortLinkOn OBJECT-TYPE
        SYNTAX INTEGER  { disable(0), enable(1) }
        MAX-ACCESS read-write
        STATUS current
        DESCRIPTION
            "The port link on event of email warning function."
        ::= { emailWarningEventEthernetPortEntry 1 }
        
    emailWarningEventEthernetPortLinkOff OBJECT-TYPE
        SYNTAX INTEGER  { disable(0), enable(1) }
        MAX-ACCESS read-write
        STATUS current
        DESCRIPTION
            "The port link off event of email warning function."
        ::= { emailWarningEventEthernetPortEntry 2 }
        
    emailWarningEventEthernetPortTrafficOverload OBJECT-TYPE
        SYNTAX INTEGER  { disable(0), enable(1) }
        MAX-ACCESS read-write
        STATUS current
        DESCRIPTION
            "The port's traffic overloading event of email warning function."
        ::= { emailWarningEventEthernetPortEntry 3 }
        
    emailWarningEventEthernetPortTrafficThreshold OBJECT-TYPE
        SYNTAX INTEGER 
        MAX-ACCESS read-write               
        STATUS current
        DESCRIPTION
            "The port's traffic threshold of the overloading event."
        ::= { emailWarningEventEthernetPortEntry 4 }   
        
    emailWarningEventEthernetPortTrafficDuration OBJECT-TYPE
        SYNTAX INTEGER 
        MAX-ACCESS read-write               
        STATUS current
        DESCRIPTION
            "The port's traffic duration of the overloading event."
        ::= { emailWarningEventEthernetPortEntry 5 }        

 	emailWarningEventTypeActive OBJECT-TYPE
        SYNTAX INTEGER { active(1)}
        MAX-ACCESS read-write
        STATUS current
        DESCRIPTION
        	"Submit Email event type setting."
        ::= { emailWarningEventType 11 }

-- -----------------------------------------------------------------------------------------------------
-- System Management -> Auto Warning Settings -> SNMP Trap									1.6.3.4
-- -----------------------------------------------------------------------------------------------------
    snmpWarningEventType OBJECT IDENTIFIER ::= { autoWarming 4 }

    snmpWarningEventServerColdStart OBJECT-TYPE
        SYNTAX INTEGER  { disable(0), enable(1) }
        MAX-ACCESS read-write
        STATUS current
        DESCRIPTION
            "The server cold start event of snmp warning function."
        ::= { snmpWarningEventType 1 }
        
    snmpWarningEventServerWarmStart OBJECT-TYPE
        SYNTAX INTEGER  { disable(0), enable(1) }
        MAX-ACCESS read-write
        STATUS current
        DESCRIPTION
            "The server warm start event of snmp warning function."
        ::= { snmpWarningEventType 2 }

    snmpWarningEventPowerOn2Off OBJECT-TYPE
        SYNTAX INTEGER  { disable(0), enable(1) }
        MAX-ACCESS read-write
        STATUS current
        DESCRIPTION
            "The power on event of snmp warning function."
        ::= { snmpWarningEventType 3 }
        
    snmpWarningEventPowerOff2On OBJECT-TYPE
        SYNTAX INTEGER  { disable(0), enable(1) }
        MAX-ACCESS read-write
        STATUS current
        DESCRIPTION
            "The power off event of snmp warning function."
        ::= { snmpWarningEventType 4}
    
    snmpWarningEventDiTable OBJECT-TYPE
        SYNTAX SEQUENCE OF SnmpWarningEventDiEntry
        MAX-ACCESS not-accessible               
        STATUS current
        DESCRIPTION
            "The DI table of the snmp warning event."
        ::= { snmpWarningEventType 5 }
    
    snmpWarningEventDiEntry OBJECT-TYPE
        SYNTAX SnmpWarningEventDiEntry
        MAX-ACCESS not-accessible               
        STATUS current
        DESCRIPTION
            "The DI table entry of the snmp warning event."
        INDEX { diIndex }
        ::= { snmpWarningEventDiTable 1 }
        
    SnmpWarningEventDiEntry ::=
        SEQUENCE {
            snmpWarningEventDiInputOn2Off
                INTEGER,
            snmpWarningEventDiInputOff2On
                INTEGER
        }

    snmpWarningEventDiInputOn2Off OBJECT-TYPE
        SYNTAX INTEGER  { disable(0), enable(1) }
        MAX-ACCESS read-write
        STATUS current
        DESCRIPTION
            "The DI input off event of snmp warning function ."
        ::= { snmpWarningEventDiEntry 1 }
        
    snmpWarningEventDiInputOff2On OBJECT-TYPE
        SYNTAX INTEGER  { disable(0), enable(1) }
        MAX-ACCESS read-write
        STATUS current
        DESCRIPTION
            "The DI input on event of snmp warning function."
        ::= { snmpWarningEventDiEntry 2 }  


        
    snmpWarningEventConfigChange OBJECT-TYPE
        SYNTAX INTEGER  { disable(0), enable(1) }
        MAX-ACCESS read-write
        STATUS current
        DESCRIPTION
            "The configuration changed event of snmp warning function."
        ::= { snmpWarningEventType 6 }
        
        
    snmpWarningEventAuthFail OBJECT-TYPE
        SYNTAX INTEGER  { disable(0), enable(1) }
        MAX-ACCESS read-write
        STATUS current
        DESCRIPTION
            "The authentication fail event of snmp warning function."
        ::= { snmpWarningEventType 7 }
        
    snmpWarningEventTopologyChanged OBJECT-TYPE
        SYNTAX INTEGER  { disable(0), enable(1) }
        MAX-ACCESS read-write
        STATUS current
        DESCRIPTION
            "The communication redundancy topology changed event of snmp warning function."
        ::= { snmpWarningEventType 8 }     
        
    snmpWarningEventSerailPortTable OBJECT-TYPE
        SYNTAX SEQUENCE OF SnmpWarningEventSerailPortEntry
        MAX-ACCESS not-accessible
        STATUS current
        DESCRIPTION
            "Port Event Settings Table."
        ::= { snmpWarningEventType 9 }
    
    snmpWarningEventSerailPortEntry OBJECT-TYPE
        SYNTAX SnmpWarningEventSerailPortEntry
        MAX-ACCESS not-accessible
        STATUS current
        DESCRIPTION
            "Port Event Settings entry."
        INDEX { portIndex }
        ::= { snmpWarningEventSerailPortTable 1 }    
     
    SnmpWarningEventSerailPortEntry ::=
        SEQUENCE {
            snmpWarningEventSerailDCDchange
                INTEGER,
            snmpWarningEventSerailDSRchange
                INTEGER
        }   
     
    snmpWarningEventSerailDCDchange OBJECT-TYPE
		SYNTAX INTEGER { disable(0), enable(1)}
		MAX-ACCESS read-write
		STATUS current
		DESCRIPTION
			"A change in the DCD (Data Carrier Detect) signal
            indicates that the modem connection status has
            changed. For example, if the DCD signal changes to
            low, it indicates that the connection line is down.
            When the DCD signal changes to low, the NPort S8000
            series device server will immediately send an SNMP
            trap."
		::= { snmpWarningEventSerailPortEntry 1 }   
		
    snmpWarningEventSerailDSRchange OBJECT-TYPE
		SYNTAX INTEGER { disable(0), enable(1)}
		MAX-ACCESS read-write
		STATUS current
		DESCRIPTION
			"A change in the DSR (Data Set Ready) signal
            indicates that the data communication equipment is
            powered off. For example, if the DSR signal changes
            to low, it indicates that the data communication
            equipment is powered down. When the DSR signal
            changes to low, the NPort S8000 series device server
            will immediately send an SNMP trap."
		::= { snmpWarningEventSerailPortEntry 2 }
        
     
    snmpWarningEventEthernetPortTable OBJECT-TYPE
        SYNTAX SEQUENCE OF SnmpWarningEventEthernetPortEntry
        MAX-ACCESS not-accessible               
        STATUS current
        DESCRIPTION
            "The port table of the snmp warning event."
        ::= { snmpWarningEventType 10 }
    
    snmpWarningEventEthernetPortEntry OBJECT-TYPE
        SYNTAX SnmpWarningEventEthernetPortEntry
        MAX-ACCESS not-accessible               
        STATUS current
        DESCRIPTION
            "The port table entry of the snmp warning event."
        INDEX { portIndex-Eth }        
        ::= { snmpWarningEventEthernetPortTable 1 }
        
    SnmpWarningEventEthernetPortEntry ::=
        SEQUENCE {
            snmpWarningEventEthernetPortLinkOn
                INTEGER,
            snmpWarningEventEthernetPortLinkOff
                INTEGER,
            snmpWarningEventEthernetPortTrafficOverload
                INTEGER,
            snmpWarningEventEthernetPortTrafficThreshold
                INTEGER,
            snmpWarningEventEthernetPortTrafficDuration
                INTEGER             
        }
        
    snmpWarningEventEthernetPortLinkOn OBJECT-TYPE
        SYNTAX INTEGER  { disable(0), enable(1) }
        MAX-ACCESS read-write
        STATUS current
        DESCRIPTION
            "The port link on event of snmp warning function."
        ::= { snmpWarningEventEthernetPortEntry 1 }
        
    snmpWarningEventEthernetPortLinkOff OBJECT-TYPE
        SYNTAX INTEGER  { disable(0), enable(1) }
        MAX-ACCESS read-write
        STATUS current
        DESCRIPTION
            "The port link off event of snmp warning function."
        ::= { snmpWarningEventEthernetPortEntry 2 }
        
    snmpWarningEventEthernetPortTrafficOverload OBJECT-TYPE
        SYNTAX INTEGER  { disable(0), enable(1) }
        MAX-ACCESS read-write
        STATUS current
        DESCRIPTION
            "The port's traffic overloading event of snmp warning function."
        ::= { snmpWarningEventEthernetPortEntry 3 }
        
    snmpWarningEventEthernetPortTrafficThreshold OBJECT-TYPE
        SYNTAX INTEGER 
        MAX-ACCESS read-write               
        STATUS current
        DESCRIPTION
            "The port's traffic threshold of the overloading event."
        ::= { snmpWarningEventEthernetPortEntry 4 }   
        
    snmpWarningEventEthernetPortTrafficDuration OBJECT-TYPE
        SYNTAX INTEGER 
        MAX-ACCESS read-write               
        STATUS current
        DESCRIPTION
            "The port's traffic duration of the overloading event."
        ::= { snmpWarningEventEthernetPortEntry 5 }        

 	snmpWarningEventTypeActive OBJECT-TYPE
        SYNTAX INTEGER { active(1)}
        MAX-ACCESS read-write
        STATUS current
        DESCRIPTION
        	"Submit SNMP event type setting."
        ::= { snmpWarningEventType 11 }

-- -----------------------------------------------------------------------------------------------------
-- System Management -> Auto Warning Settings -> Relay Alarm Setting						1.6.3.5
-- -----------------------------------------------------------------------------------------------------
    relayWarning OBJECT IDENTIFIER ::= { autoWarming 5 }   
    
    relayWarningTable OBJECT-TYPE
        SYNTAX SEQUENCE OF RelayWarningEntry
        MAX-ACCESS not-accessible               
        STATUS current
        DESCRIPTION
            "The relay warning table."
        ::= { relayWarning 1 }
    
    relayWarningEntry OBJECT-TYPE
        SYNTAX RelayWarningEntry
        MAX-ACCESS not-accessible               
        STATUS current
        DESCRIPTION
            "Relay Warning Entry."
        INDEX { relayAlarmIndex }
        ::= { relayWarningTable 1 }
        
    RelayWarningEntry ::=
        SEQUENCE {
            relayAlarmIndex
                INTEGER,   
            relayWarningRelayContact
                INTEGER,            
            overrideRelayWarningSetting
                INTEGER,
            relayWarningPower1Off
                INTEGER,   
            relayWarningPower1OffStatus
                INTEGER,
            relayWarningPower2Off
                INTEGER,
            relayWarningPower2OffStatus
                INTEGER,
            relayWarningTurboRingBreak
            	INTEGER,            
            relayWarningTurboRingBreakStatus
            	INTEGER                        	                
        }
        
    relayAlarmIndex OBJECT-TYPE
        SYNTAX INTEGER  
        MAX-ACCESS read-only
        STATUS current
        DESCRIPTION
            "The Relay alarm index."
        ::= { relayWarningEntry 1 }
        
    relayWarningRelayContact OBJECT-TYPE
        SYNTAX INTEGER  {closed(0) ,opened(1)}
        MAX-ACCESS read-only
        STATUS current
        DESCRIPTION
            "The first Relay contact status."
        ::= { relayWarningEntry 2 }

    
    overrideRelayWarningSetting OBJECT-TYPE
        SYNTAX INTEGER { no(0), yes(1) }
        MAX-ACCESS read-write
        STATUS current
        DESCRIPTION
            "Override the relay warning setting."
        ::= { relayWarningEntry 3 }
        
    relayWarningPower1Off OBJECT-TYPE
        SYNTAX INTEGER  { disable(0), enable(1) }
        MAX-ACCESS read-write
        STATUS current
        DESCRIPTION
            "The relay contact will be opened while the first power input off."
        ::= { relayWarningEntry 4 }    
        
    relayWarningPower1OffStatus OBJECT-TYPE
        SYNTAX INTEGER  { not-triggered(0), triggered(1) }
        MAX-ACCESS read-only
        STATUS current
        DESCRIPTION
            "The relay contact is opened as the first power input off.."
        ::= { relayWarningEntry 5 }    
        
    relayWarningPower2Off OBJECT-TYPE
        SYNTAX INTEGER  { disable(0), enable(1) }
        MAX-ACCESS read-write
        STATUS current
        DESCRIPTION
            "The relay contact will be opened while the second power input off."
        ::= { relayWarningEntry 6 }
        
    relayWarningPower2OffStatus OBJECT-TYPE
        SYNTAX INTEGER  { not-triggered(0), triggered(1) }
        MAX-ACCESS read-only
        STATUS current
        DESCRIPTION
            "The relay contact is opened as the second power input off."
        ::= { relayWarningEntry 7 }

     relayWarningTurboRingBreak OBJECT-TYPE
        SYNTAX INTEGER  { disable(0), enable(1) }
        MAX-ACCESS read-write
        STATUS current
        DESCRIPTION
            "The relay contact will be opened while turbo ring break."
        ::= { relayWarningEntry 8 }       
         
    relayWarningTurboRingBreakStatus OBJECT-TYPE
             SYNTAX INTEGER  { not-triggered(0), triggered(1) }
        MAX-ACCESS read-only
        STATUS current
        DESCRIPTION
            "The relay contact is opened while turbo ring is broken."
        ::= { relayWarningEntry 9 }                
        
    portRelayWarningTable OBJECT-TYPE
        SYNTAX SEQUENCE OF PortRelayWarningEntry
        MAX-ACCESS not-accessible               
        STATUS current
        DESCRIPTION
            "The relay warning port table."
        ::= { relayWarning 2 }
    
    portRelayWarningEntry OBJECT-TYPE
        SYNTAX PortRelayWarningEntry
        MAX-ACCESS not-accessible               
        STATUS current
        DESCRIPTION
            "Port Relay Warning Entry."
        INDEX { portIndex,relayAlarmIndex }
        ::= { portRelayWarningTable 1 }
        
    PortRelayWarningEntry ::=
        SEQUENCE {
            relayWarningLinkChanged
                INTEGER,            
            relayWarningLinkChangedStatus
                INTEGER,
            relayWarningTrafficOverload
                INTEGER,   
            relayWarningTrafficOverloadStatus
                INTEGER,
            relayWarningTrafficThreshold
                INTEGER,
            relayWarningTrafficDuration
                INTEGER             
        }
    
    relayWarningLinkChanged OBJECT-TYPE
        SYNTAX INTEGER  { ignore(0), on2off(1), off2on(2) }
        MAX-ACCESS read-write
        STATUS current
        DESCRIPTION
            "The relay contact will be opened while this port's link status is changed."
        ::= { portRelayWarningEntry 1 }
                                                  
    relayWarningLinkChangedStatus OBJECT-TYPE
        SYNTAX INTEGER  { not-triggered(0), triggered(1) }
        MAX-ACCESS read-only
        STATUS current
        DESCRIPTION
            "The relay contact is opened as this port's link status is changed."
        ::= { portRelayWarningEntry 2 }
                                                  
    relayWarningTrafficOverload OBJECT-TYPE
        SYNTAX INTEGER  { disable(0), enable(1) }
        MAX-ACCESS read-write
        STATUS current
        DESCRIPTION
            "The relay contact will be opened while this port's traffic is overload."
        ::= { portRelayWarningEntry 3 }  
        
    relayWarningTrafficOverloadStatus OBJECT-TYPE
        SYNTAX INTEGER  { not-triggered(0), triggered(1) }
        MAX-ACCESS read-only
        STATUS current
        DESCRIPTION
            "The relay contact is opened as this port's traffic is overload."
        ::= { portRelayWarningEntry 4 }
        
    relayWarningTrafficThreshold OBJECT-TYPE
        SYNTAX INTEGER 
        MAX-ACCESS read-write               
        STATUS current
        DESCRIPTION
            "The threshold of the port traffic will be over loading."
        ::= { portRelayWarningEntry 5 }         
        
    relayWarningTrafficDuration OBJECT-TYPE
        SYNTAX INTEGER 
        MAX-ACCESS read-write               
        STATUS current
        DESCRIPTION
            "The duration of the port traffic will be over loading."
        ::= { portRelayWarningEntry 6 }     
        
    diRelayWarningTable OBJECT-TYPE
        SYNTAX SEQUENCE OF DiRelayWarningEntry
        MAX-ACCESS not-accessible               
        STATUS current
        DESCRIPTION
            "The relay warning DI table."
        ::= { relayWarning 3 }
    
    diRelayWarningEntry OBJECT-TYPE
        SYNTAX DiRelayWarningEntry
        MAX-ACCESS not-accessible               
        STATUS current
        DESCRIPTION
            "DI Relay Warning Entry."
        INDEX { diIndex,relayAlarmIndex }
        ::= { diRelayWarningTable 1 }
        
    DiRelayWarningEntry ::=
        SEQUENCE {
            relayWarningDiInputChanged
                INTEGER,            
            relayWarningDiInputChangedStatus
                INTEGER
        }           
        
    relayWarningDiInputChanged OBJECT-TYPE
        SYNTAX INTEGER  { disable(0), off(1), on(2) }
        MAX-ACCESS read-write
        STATUS current
        DESCRIPTION
            "The relay contact will be opened while the DI input changed."
        ::= { diRelayWarningEntry 1 }       
        
    relayWarningDiInputChangedStatus OBJECT-TYPE
        SYNTAX INTEGER  { not-triggered(0), triggered(1) }
        MAX-ACCESS read-only
        STATUS current
        DESCRIPTION
            "The relay contact is opened as the first DI input changed.."
        ::= { diRelayWarningEntry 2 } 

 	relayWarningActive OBJECT-TYPE
        SYNTAX INTEGER { active(1)}
        MAX-ACCESS read-write
        STATUS current
        DESCRIPTION
        	"Submit relay warring setting."
        ::= { relayWarning 4 }

-- -----------------------------------------------------------------------------------------------------
-- System Management -> Auto Warning Settings -> System Log Setting						1.6.3.6
-- -----------------------------------------------------------------------------------------------------
	sysLogSettings OBJECT IDENTIFIER ::= { autoWarming 6 }
	
	sysLocalLog  OBJECT-TYPE
        SYNTAX INTEGER { disable(0), enable(1)}
        MAX-ACCESS read-write               
        STATUS current
        DESCRIPTION
            "Log the following events to the system log: System Cold
            Start, System Warm Start."
		::= { sysLogSettings 1 }
		
	networkLocalLog  OBJECT-TYPE
        SYNTAX INTEGER { disable(0), enable(1)}
        MAX-ACCESS read-write               
        STATUS current
        DESCRIPTION
            "Log the following events to the system log:
            DHCP/BOOTP/PPPoE Get IP/Renew, NTP, Mail Fail, NTP
            Connect Fail, DHCP Fail, IP Conflict, Ethernet Link
            Down."
		::= { sysLogSettings 2 }
		
	configLocalLog  OBJECT-TYPE
        SYNTAX INTEGER { disable(0), enable(1)}
        MAX-ACCESS read-write               
        STATUS current
        DESCRIPTION
            "Log the following events to the system log: Login Fail, IP
            Changed, Password Changed, Config Changed, Firmware
            Upgrade, SSL Key Import, Config Import, Config
            Export."
		::= { sysLogSettings 3 }
		
	opModeLocalLog  OBJECT-TYPE
        SYNTAX INTEGER { disable(0), enable(1)}
        MAX-ACCESS read-write               
        STATUS current
        DESCRIPTION
            "Log the following op-mode events to the system log:
            Connect, Disconnect, Authentication Fail, Restart."
		::= { sysLogSettings 4 }
	
	sysRemoteLog  OBJECT-TYPE
        SYNTAX INTEGER { disable(0), enable(1)}
        MAX-ACCESS read-write               
        STATUS current
        DESCRIPTION
            "Log the following events to the remote log server: System Cold
            Start, System Warm Start."
		::= { sysLogSettings 5 }
		
	networkRemoteLog  OBJECT-TYPE
        SYNTAX INTEGER { disable(0), enable(1)}
        MAX-ACCESS read-write               
        STATUS current
        DESCRIPTION
            "Log the following events to the remote log server:
            DHCP/BOOTP/PPPoE Get IP/Renew, NTP, Mail Fail, NTP
            Connect Fail, DHCP Fail, IP Conflict, Ethernet Link
            Down."
		::= { sysLogSettings 6 }
		
	configRemoteLog  OBJECT-TYPE
        SYNTAX INTEGER { disable(0), enable(1)}
        MAX-ACCESS read-write               
        STATUS current
        DESCRIPTION
            "Log the following events to the remote log server: Login Fail, IP
            Changed, Password Changed, Config Changed, Firmware
            Upgrade, SSL Key Import, Config Import, Config
            Export."
		::= { sysLogSettings 7 }
		
	opModeRemoteLog  OBJECT-TYPE
        SYNTAX INTEGER { disable(0), enable(1)}
        MAX-ACCESS read-write               
        STATUS current
        DESCRIPTION
            "Log the following op-mode events to the remote log server:
            Connect, Disconnect, Authentication Fail, Restart."
		::= { sysLogSettings 8 }	

 	sysLogSettingsActive OBJECT-TYPE
        SYNTAX INTEGER { active(1)}
        MAX-ACCESS read-write
        STATUS current
        DESCRIPTION
        	"Submit sysLog setting."
        ::= { sysLogSettings 9 }
	
-- -----------------------------------------------------------------------------------------------------
-- System Management -> Maintenance													1.6.4
-- -----------------------------------------------------------------------------------------------------
	maintenance OBJECT IDENTIFIER ::= { systemManagement 4 }

-- -----------------------------------------------------------------------------------------------------
-- System Management -> Maintenance -> Console setting								1.6.4.1
-- -----------------------------------------------------------------------------------------------------
	consoleSetting OBJECT IDENTIFIER ::= { maintenance 1 }

    webConsole OBJECT-TYPE
        SYNTAX INTEGER  { disable(0), enable(1) }
        MAX-ACCESS read-write
        STATUS current
        DESCRIPTION
            "Enable or disable Web console."
        ::= { consoleSetting 1 } 

    httpConsole OBJECT-TYPE
        SYNTAX INTEGER  { disable(0), enable(1) }
        MAX-ACCESS read-write
        STATUS current
        DESCRIPTION
            "Enable or disable HTTP console."
        ::= { consoleSetting 2 } 

    telnetConsole OBJECT-TYPE
        SYNTAX INTEGER  { disable(0), enable(1) }
        MAX-ACCESS read-write
        STATUS current
        DESCRIPTION
            "Enable or disable Telnet console."
        ::= { consoleSetting 3 } 

    resetButtonFunction OBJECT-TYPE
        SYNTAX INTEGER { disable-after-60-sec-uptime(0), always-enable(1)}
        MAX-ACCESS read-write               
        STATUS current
        DESCRIPTION
            "Enable or disable reset button protection. You can
            disable the hardware reset button after the NPort S8000
            series device server has been restarted for 60 seconds."
		::= { consoleSetting 4 }
        
    autoRefresh OBJECT-TYPE
        SYNTAX INTEGER
        MAX-ACCESS read-write
        STATUS current
        DESCRIPTION
            "Monitor refresh time."
        ::= { consoleSetting 5 } 

  	consoleSettingActive OBJECT-TYPE
        SYNTAX INTEGER { active(1)}
        MAX-ACCESS read-write
        STATUS current
        DESCRIPTION
        	"Submit console setting."
        ::= { consoleSetting 6 }


-- -----------------------------------------------------------------------------------------------------
-- System Management -> Maintenance -> Load Factory Default							1.6.4.2
-- -----------------------------------------------------------------------------------------------------
    loadFactoryDefault OBJECT IDENTIFIER ::= { maintenance 2 }
    
	loadFactoryDefaultSetting  OBJECT-TYPE
        SYNTAX INTEGER { 
        	resetToFactoryDefault (1)
        }
        MAX-ACCESS read-write               
        STATUS current
        DESCRIPTION
            "This function will reset all of the NPort S8000 series
            device server's settings to the factory default
            values. Be aware that previous settings will be
            lost. Selecting Reset to factory default will reset all
            settings including the IP configuration to factory
            defaults and restart immediately."
		::= { loadFactoryDefault 1 }   
-- -----------------------------------------------------------------------------------------------------
-- System Management -> Maintenance -> Change Password								1.6.4.3
-- -----------------------------------------------------------------------------------------------------

-- -----------------------------------------------------------------------------------------------------
-- System Management -> Maintenance -> Mirror										1.6.4.4
-- -----------------------------------------------------------------------------------------------------
    mirroring OBJECT IDENTIFIER ::= { maintenance 4 }
        
    targetPort OBJECT-TYPE
        SYNTAX INTEGER 
        MAX-ACCESS read-write               
        STATUS current
        DESCRIPTION
            "The mirrored port of mirroring function."
        ::= { mirroring 1 }

    monitorDirection OBJECT-TYPE
        SYNTAX INTEGER
            {
            inputDataStream(0),
            outputDataStream(1),
            biDirectional(2)
            }
        MAX-ACCESS read-write               
        STATUS current
        DESCRIPTION
            "The traffic direction of mirroring function."
        ::= { mirroring 2 }     
    
    mirroringPort OBJECT-TYPE
        SYNTAX INTEGER 
        MAX-ACCESS read-write               
        STATUS current
        DESCRIPTION
            "The mirroring port of mirroring function."
        ::= { mirroring 3 }

  	mirroringActive OBJECT-TYPE
        SYNTAX INTEGER { active(1)}
        MAX-ACCESS read-write
        STATUS current
        DESCRIPTION
        	"Submit mirroring setting."
        ::= { mirroring 4 }
        
-- -----------------------------------------------------------------------------------------------------
-- System Management -> TFTP Setting												1.6.5
-- -----------------------------------------------------------------------------------------------------
	sysFileUpdate OBJECT IDENTIFIER ::= { systemManagement 5 }

    tftpServer OBJECT-TYPE
        SYNTAX DisplayString
        MAX-ACCESS read-write               
        STATUS current
        DESCRIPTION
            "The TFTP Server name(IP Address)"
        ::= { sysFileUpdate 1 }

    confPathName OBJECT-TYPE
        SYNTAX DisplayString
        MAX-ACCESS read-write               
        STATUS current
        DESCRIPTION
            "The path name of configuration file in the TFTP Server"
        ::= { sysFileUpdate 2 }
        
    firmwarePathName OBJECT-TYPE
        SYNTAX DisplayString
        MAX-ACCESS read-write               
        STATUS current
        DESCRIPTION
            "The path name of firmware file in the TFTP Server"
        ::= { sysFileUpdate 3 }
        
    logPathName OBJECT-TYPE
        SYNTAX DisplayString
        MAX-ACCESS read-write               
        STATUS current
        DESCRIPTION
            "The path name of log file in the TFTP Server"
        ::= { sysFileUpdate 4 }

  	sysFileUpdateActive OBJECT-TYPE
        SYNTAX INTEGER { active(1)}
        MAX-ACCESS read-write
        STATUS current
        DESCRIPTION
        	"Submit sysFileUpdate setting."
        ::= { sysFileUpdate 5 }
        

-- -----------------------------------------------------------------------------------------------------
-- System Management -> Dip Switch Setting											1.6.6
-- -----------------------------------------------------------------------------------------------------
	dipSwitchSetting OBJECT IDENTIFIER ::= { systemManagement 6 }
    
    dipSwitchEnableTurboRing OBJECT-TYPE
        SYNTAX INTEGER  { disable(0), enable(1) }
        MAX-ACCESS read-write               
        STATUS current
        DESCRIPTION
            "Enable TurboRing Dip Switch functions"
        ::= { dipSwitchSetting 1 }

    dipSwitchTurboRingType OBJECT-TYPE
        SYNTAX INTEGER  { turbo-Ring(1), turbo-Ring-V2(2) }
        MAX-ACCESS read-write               
        STATUS current
        DESCRIPTION
            "Set DIP switch"
        ::= { dipSwitchSetting 2 } 

  	dipSwitchSettingActive OBJECT-TYPE
        SYNTAX INTEGER { active(1)}
        MAX-ACCESS read-write
        STATUS current
        DESCRIPTION
        	"Submit dip switch setting."
        ::= { dipSwitchSetting 3 }

-- -----------------------------------------------------------------------------------------------------
-- System Management -> LLDP											1.6.7
-- -----------------------------------------------------------------------------------------------------
	lldp OBJECT IDENTIFIER ::= { systemManagement 7 }
    
    lldpEnable OBJECT-TYPE
        SYNTAX INTEGER  { disable(0), enable(1) }
        MAX-ACCESS read-write               
        STATUS current
        DESCRIPTION
            "Enable LLDP function"
        ::= { lldp 1 }

    lldpMsgTxInterval OBJECT-TYPE
        SYNTAX INTEGER
        MAX-ACCESS read-write               
        STATUS current
        DESCRIPTION
            "LLDP message transmit interval(valid range 5~32768)"
        ::= { lldp 2 } 

-- -----------------------------------------------------------------------------------------------------
-- System Monitoring																		1.7
-- -----------------------------------------------------------------------------------------------------
    systemMonitoring OBJECT IDENTIFIER ::= { swMgmt 7 }

-- -----------------------------------------------------------------------------------------------------
-- System Monitoring -> Serial Status														1.7.1
-- -----------------------------------------------------------------------------------------------------
	serialStatus OBJECT IDENTIFIER ::= { systemMonitoring 1 }

-- -----------------------------------------------------------------------------------------------------
-- System Monitoring -> Serial Status -> Serial to Network Connections						1.7.1.1
-- -----------------------------------------------------------------------------------------------------
	s2eConnections  OBJECT IDENTIFIER ::= { serialStatus 1 }

	monitorRemoteIpTable OBJECT-TYPE
        SYNTAX SEQUENCE OF MonitorRemoteIpEntry
        MAX-ACCESS not-accessible
        STATUS current
        DESCRIPTION
            "Serial to Network Connections Remote IP table."
        ::= { s2eConnections 1 }
    
    monitorRemoteIpEntry OBJECT-TYPE
        SYNTAX MonitorRemoteIpEntry
        MAX-ACCESS not-accessible
        STATUS current
        DESCRIPTION
            "Serial to Network Connections Remote IP entry."
        INDEX { portIndex, remoteIpIndex }
        ::= { monitorRemoteIpTable 1 }
        
    MonitorRemoteIpEntry ::=
        SEQUENCE {
        	remoteIpIndex
        		INTEGER,
            monitorRemoteIp
                DisplayString,
            monitorCipher
            	DisplayString   
        }
    
    remoteIpIndex  OBJECT-TYPE
        SYNTAX INTEGER
        MAX-ACCESS read-only               
        STATUS current
        DESCRIPTION
            "Serial to Network Connections Remote IP index."
		::= { monitorRemoteIpEntry 1 }
   	    
	monitorRemoteIp  OBJECT-TYPE
        SYNTAX DisplayString
        MAX-ACCESS read-only               
        STATUS current
        DESCRIPTION
            "The remote IP currently connecting to this port."
		::= { monitorRemoteIpEntry 2 }
	
-- -----------------------------------------------------------------------------------------------------
-- System Monitoring -> Serial Status -> Serial Port Status									1.7.1.2
-- -----------------------------------------------------------------------------------------------------
	serialPortStatus  OBJECT IDENTIFIER ::= { serialStatus 2 }
	
	monitorSerialPortStatusTable OBJECT-TYPE
        SYNTAX SEQUENCE OF MonitorSerialPortStatusEntry
        MAX-ACCESS not-accessible
        STATUS current
        DESCRIPTION
            "Serial Port Status table."
        ::= { serialPortStatus 1 }
    
    monitorSerialPortStatusEntry OBJECT-TYPE
        SYNTAX MonitorSerialPortStatusEntry
        MAX-ACCESS not-accessible
        STATUS current
        DESCRIPTION
            "Serial Port Status entry."
        INDEX { portIndex }
        ::= { monitorSerialPortStatusTable 1 }
        
    MonitorSerialPortStatusEntry ::=
        SEQUENCE {
            monitorTxCount
				INTEGER,
			monitorRxCount
				INTEGER,
			monitorTxTotalCount
				INTEGER,
			monitorRxTotalCount
				INTEGER,
			monitorDSR
				INTEGER,
			monitorDTR
				INTEGER,
			monitorRTS
				INTEGER,
			monitorCTS
				INTEGER,
			monitorDCD
				INTEGER
        }

	monitorTxCount  OBJECT-TYPE
        SYNTAX INTEGER
        MAX-ACCESS read-only
        STATUS current
        DESCRIPTION
            "View the number of bytes transmitted from the port
            since the last time the port was initialized."
		::= { monitorSerialPortStatusEntry 1 }
		
	monitorRxCount  OBJECT-TYPE
        SYNTAX INTEGER
        MAX-ACCESS read-only
        STATUS current
        DESCRIPTION
            "View the number of bytes received by the port since
            the last time the port was initialized."
		::= { monitorSerialPortStatusEntry 2 }
		
	monitorTxTotalCount  OBJECT-TYPE
        SYNTAX INTEGER
        MAX-ACCESS read-only
        STATUS current
        DESCRIPTION
            "View the number of bytes transmitted from the port
            since the last time the system was initialized."
		::= { monitorSerialPortStatusEntry 3 }
		
	monitorRxTotalCount  OBJECT-TYPE
        SYNTAX INTEGER
        MAX-ACCESS read-only
        STATUS current
        DESCRIPTION
            "View the number of bytes received by the port since
            the last time the system was initialized."
		::= { monitorSerialPortStatusEntry 4 }
		
	monitorDSR  OBJECT-TYPE
        SYNTAX INTEGER { off(0), on(1)}
        MAX-ACCESS read-only
        STATUS current
        DESCRIPTION
            "View the current DSR status of this port."
		::= { monitorSerialPortStatusEntry 5 }
		
	monitorDTR  OBJECT-TYPE
        SYNTAX INTEGER { off(0), on(1)}
        MAX-ACCESS read-only
        STATUS current
        DESCRIPTION
            "View the current DTR status of this port."
		::= { monitorSerialPortStatusEntry 6 }
		
	monitorRTS  OBJECT-TYPE
        SYNTAX INTEGER { off(0), on(1)}
        MAX-ACCESS read-only
        STATUS current
        DESCRIPTION
            "View the current RTS status of this port."
		::= { monitorSerialPortStatusEntry 7 }
		
	monitorCTS  OBJECT-TYPE
        SYNTAX INTEGER { off(0), on(1)}
        MAX-ACCESS read-only
        STATUS current
        DESCRIPTION
            "View the current CTS status of this port."
		::= { monitorSerialPortStatusEntry 8 }
		
	monitorDCD  OBJECT-TYPE
        SYNTAX INTEGER { off(0), on(1)}
        MAX-ACCESS read-only
        STATUS current
        DESCRIPTION
            "View the current DCD status of this port."
		::= { monitorSerialPortStatusEntry 9 }
-- -----------------------------------------------------------------------------------------------------
-- System Monitoring -> Serial Status -> Serial Port Error Count							1.7.1.3
-- -----------------------------------------------------------------------------------------------------
	serialPortErrorCount  OBJECT IDENTIFIER ::= { serialStatus 3 }
	
	monitorSerialPortErrorCountTable OBJECT-TYPE
        SYNTAX SEQUENCE OF MonitorSerialPortErrorCountEntry
        MAX-ACCESS not-accessible
        STATUS current
        DESCRIPTION
            "Serial Port Error Count table."
        ::= { serialPortErrorCount 1 }
    
    monitorSerialPortErrorCountEntry OBJECT-TYPE
        SYNTAX MonitorSerialPortErrorCountEntry
        MAX-ACCESS not-accessible
        STATUS current
        DESCRIPTION
            "Serial Port Error Count entry."
        INDEX { portIndex }
        ::= { monitorSerialPortErrorCountTable 1 }
        
    MonitorSerialPortErrorCountEntry ::=
        SEQUENCE {
            monitorErrorCountFrame
				INTEGER,
			monitorErrorCountParity
				INTEGER,
			monitorErrorCountOverrun
				INTEGER,
			monitorErrorCountBreak
				INTEGER
        }

	monitorErrorCountFrame  OBJECT-TYPE
        SYNTAX INTEGER
        MAX-ACCESS read-only
        STATUS current
        DESCRIPTION
            "View the number of 'Frame' errors for this port."
		::= { monitorSerialPortErrorCountEntry 1 }
		
	monitorErrorCountParity  OBJECT-TYPE
        SYNTAX INTEGER
        MAX-ACCESS read-only
        STATUS current
        DESCRIPTION
            "View the number of 'Parity' errors for this port."
		::= { monitorSerialPortErrorCountEntry 2 }
		
	monitorErrorCountOverrun  OBJECT-TYPE
        SYNTAX INTEGER
        MAX-ACCESS read-only
        STATUS current
        DESCRIPTION
            "View the number of 'Overrun' errors for this port."
		::= { monitorSerialPortErrorCountEntry 3 }
		
	monitorErrorCountBreak  OBJECT-TYPE
        SYNTAX INTEGER
        MAX-ACCESS read-only
        STATUS current
        DESCRIPTION
            "View the number of 'Break' errors for this port."
		::= { monitorSerialPortErrorCountEntry 4 }


-- -----------------------------------------------------------------------------------------------------
-- System Monitoring -> Serial Status -> Serial Port Settings								1.7.1.4
-- -----------------------------------------------------------------------------------------------------
	serialPortSettings  OBJECT IDENTIFIER ::= { serialStatus 4 }
	
	monitorSerialPortSettingsTable OBJECT-TYPE
        SYNTAX SEQUENCE OF MonitorSerialPortSettingsEntry
        MAX-ACCESS not-accessible
        STATUS current
        DESCRIPTION
            "Serial Port Settings table."
        ::= { serialPortSettings 1 }
    
    monitorSerialPortSettingsEntry OBJECT-TYPE
        SYNTAX MonitorSerialPortSettingsEntry
        MAX-ACCESS not-accessible
        STATUS current
        DESCRIPTION
            "Serial Port Settings entry."
        INDEX { portIndex }
        ::= { monitorSerialPortSettingsTable 1 }
        
    MonitorSerialPortSettingsEntry ::=
        SEQUENCE {
            monitorBaudRate
				INTEGER,
			monitorDataBits
				INTEGER,
			monitorStopBits
				DisplayString,
			monitorParity
				INTEGER,
			monitorRTSCTSFlowControl
				INTEGER,
			monitorXONXOFFFlowControl
				INTEGER,
			monitorFIFO
				INTEGER,
			monitorInterface
				INTEGER
        }

	monitorBaudRate  OBJECT-TYPE
        SYNTAX INTEGER
        MAX-ACCESS read-only
        STATUS current
        DESCRIPTION
            "View the current baudrate of the port."
		::= { monitorSerialPortSettingsEntry 1 }
		
	monitorDataBits  OBJECT-TYPE
		SYNTAX INTEGER  { 
			bits-5(0), 
			bits-6(1), 
			bits-7(2),
			bits-8(3) 
		}
        MAX-ACCESS read-only
        STATUS current
        DESCRIPTION
            "View the number of bits per byte for the port."
		::= { monitorSerialPortSettingsEntry 2 }
		
	monitorStopBits  OBJECT-TYPE
        SYNTAX DisplayString
        MAX-ACCESS read-only
        STATUS current
        DESCRIPTION
            "View the number of stop bits for the port."
		::= { monitorSerialPortSettingsEntry 3 }
	
	monitorParity  OBJECT-TYPE
        SYNTAX INTEGER {
        	none(0),
			odd(8),
			even(24),
			mark(40),
			space(56)
        }
        MAX-ACCESS read-only
        STATUS current
        DESCRIPTION
            "View the parity bit for the port."
		::= { monitorSerialPortSettingsEntry 4 }
		
	monitorRTSCTSFlowControl  OBJECT-TYPE
        SYNTAX INTEGER { off(0), on(1) }
        MAX-ACCESS read-only
        STATUS current
        DESCRIPTION
            "View if the port is using RTS/CTS flow control."
		::= { monitorSerialPortSettingsEntry 5 }
		
	monitorXONXOFFFlowControl  OBJECT-TYPE
        SYNTAX INTEGER { off(0), on(1) }
        MAX-ACCESS read-only
        STATUS current
        DESCRIPTION
            "View if the port is using XON/XOFF flow control."
		::= { monitorSerialPortSettingsEntry 6 }
				
	monitorFIFO  OBJECT-TYPE
        SYNTAX INTEGER {
        	disable(0),
			enable(1)
        }
        MAX-ACCESS read-only
        STATUS current
        DESCRIPTION
            "View FIFO status of this port."
		::= { monitorSerialPortSettingsEntry 7 }
		
	monitorInterface  OBJECT-TYPE
        SYNTAX INTEGER {
        	rs-232(0),
			rs-422(1),
			rs-485-2-wire(2),
			rs-485-4-wire(3)
        }
        MAX-ACCESS read-only
        STATUS current
        DESCRIPTION
            "View the serial interface that the port is using."
		::= { monitorSerialPortSettingsEntry 8 }



-- -----------------------------------------------------------------------------------------------------
-- System Monitoring -> System Status														1.7.2
-- -----------------------------------------------------------------------------------------------------
	systemStatus OBJECT IDENTIFIER ::= { systemMonitoring 2 }

-- -----------------------------------------------------------------------------------------------------
-- System Monitoring -> System Status -> System Information									1.7.2.1
-- -----------------------------------------------------------------------------------------------------
	systemInfo OBJECT IDENTIFIER ::= { systemStatus 1 }

	power1InputStatus OBJECT-TYPE
        SYNTAX INTEGER { not-present(0), present(1) }
        MAX-ACCESS read-only                
        STATUS current
        DESCRIPTION
            "The status of the first power input."
        ::= { systemInfo 1 }
    
    power2InputStatus OBJECT-TYPE
        SYNTAX INTEGER { not-present(0), present(1) }
        MAX-ACCESS read-only                
        STATUS current
        DESCRIPTION
            "The status of the second power input."
        ::= { systemInfo 2 }

    monitorDiTable OBJECT-TYPE
        SYNTAX SEQUENCE OF MonitorDiEntry
        MAX-ACCESS not-accessible               
        STATUS current
        DESCRIPTION
            "The DI table of monitor function."
        ::= { systemInfo 3 }
    
    monitorDiEntry OBJECT-TYPE
        SYNTAX MonitorDiEntry
        MAX-ACCESS not-accessible               
        STATUS current
        DESCRIPTION
            "The DI table entry of monitor function."
        INDEX { diIndex }
        ::= { monitorDiTable 1 }
        
    MonitorDiEntry ::=
        SEQUENCE {
            diIndex
                INTEGER,
            diInputStatus
                INTEGER
        }
    
    diIndex OBJECT-TYPE
        SYNTAX INTEGER (1..2)
        MAX-ACCESS read-only                
        STATUS current
        DESCRIPTION
            "The DI index of monitor function"
        ::= { monitorDiEntry 1 }        
    
    diInputStatus OBJECT-TYPE
        SYNTAX INTEGER { off(0), on(1) }
        MAX-ACCESS read-only                
        STATUS current
        DESCRIPTION
            "The DI input status."
        ::= { monitorDiEntry 2 }
        
    dipSwitchTurboRingPole OBJECT-TYPE
        SYNTAX INTEGER  { off(0), on(1) }
        MAX-ACCESS read-only               
        STATUS current
        DESCRIPTION
            "The TurboRing Pole status of Dip switch."
        ::= { systemInfo 4 }
    
    dipSwitchRingCouplingPole OBJECT-TYPE
        SYNTAX INTEGER  { off(0), on(1) }
        MAX-ACCESS read-only               
        STATUS current
        DESCRIPTION
            "The Ring Coupling Pole status of Dip switch."
        ::= { systemInfo 5 }

    dipSwitchRingMasterPole OBJECT-TYPE
        SYNTAX INTEGER  { off(0), on(1) }
        MAX-ACCESS read-only               
        STATUS current
        DESCRIPTION
            "The Ring Master Pole status of Dip switch."
        ::= { systemInfo 6 }    



-- -----------------------------------------------------------------------------------------------------
-- System Monitoring -> System Status -> Network Connections									1.7.2.2
-- -----------------------------------------------------------------------------------------------------
    networkConnected OBJECT IDENTIFIER ::= { systemStatus 2 }   
    
    networkConnTable OBJECT-TYPE
        SYNTAX SEQUENCE OF NetworkConnEntry
        MAX-ACCESS not-accessible               
        STATUS current
        DESCRIPTION
            "The Port Access Control table."
        ::= { networkConnected 1 }
    
    networkConnEntry OBJECT-TYPE
        SYNTAX NetworkConnEntry
        MAX-ACCESS not-accessible               
        STATUS current
        DESCRIPTION
            "The Port Access Control table entry."
        INDEX { NULL }
        ::= { networkConnTable 1 }  
        
    NetworkConnEntry ::=
        SEQUENCE {
            protocol
                INTEGER,
            recv-q
                INTEGER,   
			send-q
                INTEGER,
			localIpAddress
                IpAddress,
			localPort
                INTEGER,
			remoteIpAddress
                IpAddress,
			remotePort
                INTEGER,
            state
                INTEGER
        }          
        
    protocol OBJECT-TYPE
        SYNTAX INTEGER {
        	udp(0),
        	tcp(1)
        }
        MAX-ACCESS read-only
        STATUS current
        DESCRIPTION
            "Connected potocol."
        ::= { networkConnEntry 1 }

    recv-q OBJECT-TYPE
        SYNTAX INTEGER 
        MAX-ACCESS read-only
        STATUS current
        DESCRIPTION
            "Receiver queue size."
        ::= { networkConnEntry 2 }
        
    send-q OBJECT-TYPE
        SYNTAX INTEGER
        MAX-ACCESS read-only
        STATUS current
        DESCRIPTION
            "Send queue size."
        ::= { networkConnEntry 3 }

    localIpAddress OBJECT-TYPE
        SYNTAX IpAddress
        MAX-ACCESS read-only
        STATUS current
        DESCRIPTION
            "Local IP Address."
        ::= { networkConnEntry 4 }

    localPort OBJECT-TYPE
        SYNTAX INTEGER
        MAX-ACCESS read-only
        STATUS current
        DESCRIPTION
            "Local port."
        ::= { networkConnEntry 5 }
        

    remoteIpAddress OBJECT-TYPE
        SYNTAX IpAddress
        MAX-ACCESS read-only
        STATUS current
        DESCRIPTION
            "Remote IP Address."
        ::= { networkConnEntry 6 }

    remotePort OBJECT-TYPE
        SYNTAX INTEGER
        MAX-ACCESS read-only
        STATUS current
        DESCRIPTION
            "Remote port."
        ::= { networkConnEntry 7 }

    state OBJECT-TYPE
        SYNTAX INTEGER {
        	closed(0),
			listen(1),
			synSend(2),
			synRecvd(3),
			estab(4),
			closeWait(5),
			finWait1(6),
			closing(7),
			lastAck(8),
			finWait2(9),
			timeWait(10)
        }
        MAX-ACCESS read-only
        STATUS current
        DESCRIPTION
            "Connected state."
        ::= { networkConnEntry 8 }

-- -----------------------------------------------------------------------------------------------------
-- System Monitoring -> System Status -> Event Log												1.7.2.3
-- -----------------------------------------------------------------------------------------------------
	eventLog OBJECT IDENTIFIER ::= { systemStatus 3 }

    eventLogTable OBJECT-TYPE
        SYNTAX SEQUENCE OF EventLogEntry
        MAX-ACCESS not-accessible               
        STATUS current
        DESCRIPTION
            "The Port Access Control table."
        ::= { eventLog 1 }
    
    eventLogEntry OBJECT-TYPE
        SYNTAX EventLogEntry
        MAX-ACCESS not-accessible               
        STATUS current
        DESCRIPTION
            "The Port Access Control table entry."
        INDEX { eventListIndex }
        ::= { eventLogTable 1 }
        
    EventLogEntry ::=
        SEQUENCE {
            eventListIndex
                INTEGER,
            eventListBootup
                INTEGER,   
			eventListData
                DisplayString,
			eventListTime
                DisplayString,
			eventListSysUpTime
                DisplayString,
			eventListEvent
                DisplayString
        }

	eventListIndex  OBJECT-TYPE
        SYNTAX INTEGER
        MAX-ACCESS read-only               
        STATUS current
        DESCRIPTION
            "index."
		::= { eventLogEntry 1 }

	eventListBootup  OBJECT-TYPE
        SYNTAX INTEGER
        MAX-ACCESS read-only               
        STATUS current
        DESCRIPTION
            "index."
		::= { eventLogEntry 2 }

	eventListData  OBJECT-TYPE
        SYNTAX DisplayString
        MAX-ACCESS read-only               
        STATUS current
        DESCRIPTION
            "index."
		::= { eventLogEntry 3 }

	eventListTime  OBJECT-TYPE
        SYNTAX DisplayString
        MAX-ACCESS read-only               
        STATUS current
        DESCRIPTION
            "index."
		::= { eventLogEntry 4 }

	eventListSysUpTime  OBJECT-TYPE
        SYNTAX DisplayString
        MAX-ACCESS read-only               
        STATUS current
        DESCRIPTION
            "index."
		::= { eventLogEntry 5 }

	eventListEvent  OBJECT-TYPE
        SYNTAX DisplayString
        MAX-ACCESS read-only               
        STATUS current
        DESCRIPTION
            "index."
		::= { eventLogEntry 6 }

	eventListClear  OBJECT-TYPE
        SYNTAX INTEGER
        MAX-ACCESS read-write               
        STATUS current
        DESCRIPTION
            "index."
		::= { eventLog 2 }

-- -----------------------------------------------------------------------------------------------------
-- System Monitoring -> System Status -> Serial data Log									1.7.2.5
-- -----------------------------------------------------------------------------------------------------






-- -----------------------------------------------------------------------------------------------------
-- System Monitoring -> Ethernet Status														1.7.3
-- -----------------------------------------------------------------------------------------------------
	ethernetStatus OBJECT IDENTIFIER ::= { systemMonitoring 3 }


-- -----------------------------------------------------------------------------------------------------
-- System Monitoring -> Ethernet Status -> MAC Address List								1.7.3.1
-- -----------------------------------------------------------------------------------------------------
	macAddressList OBJECT IDENTIFIER ::= { ethernetStatus 1 }

-- -----------------------------------------------------------------------------------------------------
-- System Monitoring -> Ethernet Status -> IGMP table										1.7.3.2
-- -----------------------------------------------------------------------------------------------------
	igmpstatus OBJECT IDENTIFIER ::= { ethernetStatus 2 }

    igmpSnoopingMulticastGroupTable OBJECT-TYPE
        SYNTAX SEQUENCE OF IgmpSnoopingMulticastGroupEntry
        MAX-ACCESS not-accessible               
        STATUS current
        DESCRIPTION
            "The multicast group table by IGMP snooping function."
        ::= { igmpstatus 1 }
    
    igmpSnoopingMulticastGroupEntry OBJECT-TYPE
        SYNTAX IgmpSnoopingMulticastGroupEntry
        MAX-ACCESS not-accessible               
        STATUS current
        DESCRIPTION
            "The multicast group entry by IGMP snooping function."
        -- INDEX { vlanId,multicastIpGroup }
        INDEX { vlanId, igmpSnoopingIpGroup }
        ::= { igmpSnoopingMulticastGroupTable 1 }
        
    IgmpSnoopingMulticastGroupEntry ::=
        SEQUENCE {  
            learnedMulticastQuerierPorts
                PortList,
            igmpSnoopingIpGroup
                IpAddress,           
            igmpSnoopingMacGroup
                MacAddress,
            igmpSnoopingJoinedPorts
                PortList
            }
            
    learnedMulticastQuerierPorts OBJECT-TYPE
        SYNTAX PortList
        MAX-ACCESS read-only
        STATUS current
        DESCRIPTION
            "The ports that multicast-Querier exist."
        ::= { igmpSnoopingMulticastGroupEntry 1 }       
    
    igmpSnoopingIpGroup OBJECT-TYPE
        SYNTAX IpAddress 
        MAX-ACCESS read-only                
        STATUS current
        DESCRIPTION
            "The multicast IP group by IGMP snooping function."
        ::= { igmpSnoopingMulticastGroupEntry 2 }  
        
    igmpSnoopingMacGroup OBJECT-TYPE
        SYNTAX MacAddress
        MAX-ACCESS read-only                
        STATUS current
        DESCRIPTION
            "The multicast MAC group by IGMP snooping function."
        ::= { igmpSnoopingMulticastGroupEntry 3 }  
        
    igmpSnoopingJoinedPorts OBJECT-TYPE
        SYNTAX PortList
        MAX-ACCESS read-only                
        STATUS current
        DESCRIPTION
            "The ports that joined this multicast group."
        ::= { igmpSnoopingMulticastGroupEntry 4 }  
    
-- -----------------------------------------------------------------------------------------------------
-- System Monitoring -> Ethernet Status -> GMRP Table										1.7.3.3
-- -----------------------------------------------------------------------------------------------------
	gmrpStatus OBJECT IDENTIFIER ::= { ethernetStatus 3 }

    gmrpTable OBJECT-TYPE
        SYNTAX SEQUENCE OF GmrpEntry
        MAX-ACCESS not-accessible               
        STATUS current
        DESCRIPTION
            "The GMRP status table."
        ::= { gmrpStatus 1 }
    
    gmrpEntry OBJECT-TYPE
        SYNTAX GmrpEntry
        MAX-ACCESS not-accessible               
        STATUS current
        DESCRIPTION
            "The GMRP Status Entry."
        INDEX { gmrpMulticastGroup }
        ::= { gmrpTable 1 }
        
    GmrpEntry ::=
        SEQUENCE {
            gmrpMulticastGroup
                MacAddress,           
            gmrpFixedPorts
                PortList,
            gmrpLearnedPorts
                PortList
            } 
    
    gmrpMulticastGroup OBJECT-TYPE
        SYNTAX MacAddress
        MAX-ACCESS read-only              
        STATUS current
        DESCRIPTION
            "GMRP multicast group."
        ::= { gmrpEntry 1 }  
        
    gmrpFixedPorts OBJECT-TYPE
        SYNTAX PortList
        MAX-ACCESS read-only              
        STATUS current
        DESCRIPTION
            "The ports that joined GMRP multicast group manually."
        ::= { gmrpEntry 2 }      
   
    gmrpLearnedPorts OBJECT-TYPE
        SYNTAX PortList
        MAX-ACCESS read-only
        STATUS current
        DESCRIPTION
            "The ports that joined GMRP multicast group by GMRP learning."
        ::= { gmrpEntry 3 }     
-- -----------------------------------------------------------------------------------------------------
-- System Monitoring -> Ethernet Status -> 802.1X Reauth									1.7.3.4
-- -----------------------------------------------------------------------------------------------------
	dot1XReauth OBJECT IDENTIFIER ::= { ethernetStatus 4 }

    dot1xReauthTable OBJECT-TYPE
        SYNTAX SEQUENCE OF Dot1xReauthEntry
        MAX-ACCESS not-accessible               
        STATUS current
        DESCRIPTION
            "IEEE 802.1X Re-authentication Table."
        ::= { dot1XReauth 1 }
    
    dot1xReauthEntry OBJECT-TYPE
        SYNTAX Dot1xReauthEntry
        MAX-ACCESS not-accessible               
        STATUS current
        DESCRIPTION
            "IEEE 802.1X Re-authentication Entry."
        INDEX { dot1xReauthPortIndex }
        ::= { dot1xReauthTable 1 }
        
    Dot1xReauthEntry ::=
        SEQUENCE { 
        	dot1xReauthPortIndex
        		INTEGER, 
            dot1xReauth
                INTEGER
            }     
    
    dot1xReauthPortIndex OBJECT-TYPE
        SYNTAX INTEGER
        MAX-ACCESS read-only
        STATUS current
        DESCRIPTION
            "IEEE 802.1X Enabled Port Index."
        ::= { dot1xReauthEntry 1 }

    dot1xReauth OBJECT-TYPE
        SYNTAX INTEGER {
        	no(0),
        	yes(1)
        }
        MAX-ACCESS read-write
        STATUS current
        DESCRIPTION
            "Reauth IEEE 802.1X."
        ::= { dot1xReauthEntry 2 }
        
  	dot1XReauthActive OBJECT-TYPE
        SYNTAX INTEGER { active(1)}
        MAX-ACCESS read-write
        STATUS current
        DESCRIPTION
        	"Submit dot1X Reauth setting."
        ::= { dot1XReauth 2 }
        
-- -----------------------------------------------------------------------------------------------------
-- System Monitoring -> Ethernet Status -> Port Access Control Table						1.7.3.5
-- -----------------------------------------------------------------------------------------------------
	portAccessControlList OBJECT IDENTIFIER ::= { ethernetStatus 5 }
	
    portAccessControlTable OBJECT-TYPE
        SYNTAX SEQUENCE OF PortAccessControlEntry
        MAX-ACCESS not-accessible               
        STATUS current
        DESCRIPTION
            "The Port Access Control table."
        ::= { portAccessControlList 1 }
    
    portAccessControlEntry OBJECT-TYPE
        SYNTAX PortAccessControlEntry
        MAX-ACCESS not-accessible               
        STATUS current
        DESCRIPTION
            "The Port Access Control table entry."
        INDEX { portAccessControlAddress }
        ::= { portAccessControlTable 1 }
        
    PortAccessControlEntry ::=
        SEQUENCE {
            portAccessControlAddress
                MacAddress,     
            portAccessControlPortNo
            	INTEGER,
            portAccessControlAccessStatus
                INTEGER,      
            portAccessControlStatus
                INTEGER
            } 
    
    portAccessControlAddress OBJECT-TYPE
        SYNTAX MacAddress
        MAX-ACCESS read-only                
        STATUS current
        DESCRIPTION
            "The MAC address which is static locked or IEEE 802.1X authorized."
        ::= { portAccessControlEntry 1 }  

    portAccessControlPortNo OBJECT-TYPE
        SYNTAX INTEGER
        MAX-ACCESS read-only                
        STATUS current
        DESCRIPTION
            "The port number that the Port Access Control address resides."
        ::= { portAccessControlEntry 2 }  

    portAccessControlAccessStatus OBJECT-TYPE
        SYNTAX INTEGER {  
        	staticLock(1), 	
        	authorized(2),
        	unAuthorized(3),
        	authorizing(4)
        } 
        MAX-ACCESS read-only                
        STATUS current
        DESCRIPTION
            "The access status of the Port Access Control address."
        ::= { portAccessControlEntry 3 }  

    portAccessControlStatus OBJECT-TYPE
        SYNTAX INTEGER {
            active(1),
            createAndGo(4),
            createAndWait(5),
            destroy(6)
        }
        MAX-ACCESS read-create              
        STATUS current
        DESCRIPTION
            "The status is active to indicate normal.
            Use createAndGo to create new on multiple SET.
            Use createAndWait to create new on one SET all then actvie.
            Use destroy to delete this row."
        ::= { portAccessControlEntry 4 }
-- -----------------------------------------------------------------------------------------------------
-- System Monitoring -> Ethernet Status -> Warning List										1.7.3.6
-- -----------------------------------------------------------------------------------------------------
	warningList OBJECT IDENTIFIER ::= { ethernetStatus 6 }

	warningListTable OBJECT-TYPE
        SYNTAX SEQUENCE OF WarningListEntry
        MAX-ACCESS not-accessible               
        STATUS current
        DESCRIPTION
            "The Port Access Control table."
        ::= { warningList 1 }
    
    warningListEntry OBJECT-TYPE
        SYNTAX WarningListEntry
        MAX-ACCESS not-accessible               
        STATUS current
        DESCRIPTION
            "The Port Access Control table entry."
        INDEX { warningListIndex }
        ::= { warningListTable 1 }
        
    WarningListEntry ::=
        SEQUENCE {
            warningListIndex
				INTEGER,
            warningListEvent
				DisplayString,
            warningListRelay
				INTEGER
            }
                     
	warningListIndex OBJECT-TYPE
        SYNTAX INTEGER
        MAX-ACCESS read-only                
        STATUS current
        DESCRIPTION
           ""
        ::= { warningListEntry 1 }
        
	warningListEvent OBJECT-TYPE
        SYNTAX DisplayString
        MAX-ACCESS read-only                
        STATUS current
        DESCRIPTION
           ""
        ::= { warningListEntry 2 }  
        
	warningListRelay OBJECT-TYPE
        SYNTAX INTEGER
        MAX-ACCESS read-only                
        STATUS current
        DESCRIPTION
           ""
        ::= { warningListEntry 3 }  


	

-- -----------------------------------------------------------------------------------------------------
-- System Monitoring -> Ethernet Status -> Ethernet Monitor									1.7.3.7
-- -----------------------------------------------------------------------------------------------------
	ethernetMonitor OBJECT IDENTIFIER ::= { ethernetStatus 7 }

    ethernetMonitorTable OBJECT-TYPE
        SYNTAX SEQUENCE OF EthernetMonitorEntry
        MAX-ACCESS not-accessible               
        STATUS current
        DESCRIPTION
            "The Port Access Control table."
        ::= { ethernetMonitor 1 }
    
    ethernetMonitorEntry OBJECT-TYPE
        SYNTAX EthernetMonitorEntry
        MAX-ACCESS not-accessible               
        STATUS current
        DESCRIPTION
            "The Port Access Control table entry."
        INDEX { portIndex-Eth }
        ::= { ethernetMonitorTable 1 }
        
    EthernetMonitorEntry ::=
        SEQUENCE {
            ethernetMonitorTxTotal
                INTEGER,
            ethernetMonitorTxUicast
                INTEGER,     
            ethernetMonitorTxMulticast
                INTEGER,     
            ethernetMonitorTxBroadcast
                INTEGER,     
            ethernetMonitorTxCollision
                INTEGER,     
            ethernetMonitorRxTotal
                INTEGER,     
            ethernetMonitorRxUicast
                INTEGER,     
            ethernetMonitorRxMulticast
                INTEGER,     
            ethernetMonitorRxBroadcast
                INTEGER,     
            ethernetMonitorRxPause
                INTEGER,     
            ethernetMonitorTxErr
                INTEGER,     
            ethernetMonitorTxErrLate
                INTEGER,     
            ethernetMonitorTxErrExcessive
                INTEGER,     
            ethernetMonitorRxErr
                INTEGER,     
            ethernetMonitorRxErrCRC
                INTEGER,     
            ethernetMonitorRxErrDiscard
                INTEGER,     
            ethernetMonitorRxErrUndersize
                INTEGER,     
            ethernetMonitorRxErrFragments
                INTEGER,     
            ethernetMonitorRxErrOversize
                INTEGER,     
            ethernetMonitorRxErrJabber
                INTEGER
            }

	ethernetMonitorTxTotal OBJECT-TYPE
        SYNTAX INTEGER
        MAX-ACCESS read-only                
        STATUS current
        DESCRIPTION
           ""
        ::= { ethernetMonitorEntry 1 }  


	ethernetMonitorTxUicast OBJECT-TYPE
        SYNTAX INTEGER
        MAX-ACCESS read-only                
        STATUS current
        DESCRIPTION
           ""
        ::= { ethernetMonitorEntry 2 }  
        
	ethernetMonitorTxMulticast OBJECT-TYPE
        SYNTAX INTEGER
        MAX-ACCESS read-only                
        STATUS current
        DESCRIPTION
           ""
        ::= { ethernetMonitorEntry 3 }  
        
	ethernetMonitorTxBroadcast OBJECT-TYPE
        SYNTAX INTEGER
        MAX-ACCESS read-only                
        STATUS current
        DESCRIPTION
           ""
        ::= { ethernetMonitorEntry 4 }  
        
	ethernetMonitorTxCollision OBJECT-TYPE
        SYNTAX INTEGER
        MAX-ACCESS read-only                
        STATUS current
        DESCRIPTION
           ""
        ::= { ethernetMonitorEntry 5 }  
        
	ethernetMonitorRxTotal OBJECT-TYPE
        SYNTAX INTEGER
        MAX-ACCESS read-only                
        STATUS current
        DESCRIPTION
           ""
        ::= { ethernetMonitorEntry 6 }  
        
	ethernetMonitorRxUicast OBJECT-TYPE
        SYNTAX INTEGER
        MAX-ACCESS read-only                
        STATUS current
        DESCRIPTION
           ""
        ::= { ethernetMonitorEntry 7 }  
        
	ethernetMonitorRxMulticast OBJECT-TYPE
        SYNTAX INTEGER
        MAX-ACCESS read-only                
        STATUS current
        DESCRIPTION
           ""
        ::= { ethernetMonitorEntry 8 }  
        
	ethernetMonitorRxBroadcast OBJECT-TYPE
        SYNTAX INTEGER
        MAX-ACCESS read-only                
        STATUS current
        DESCRIPTION
           ""
        ::= { ethernetMonitorEntry 9 }  
        
	ethernetMonitorRxPause OBJECT-TYPE
        SYNTAX INTEGER
        MAX-ACCESS read-only                
        STATUS current
        DESCRIPTION
           ""
        ::= { ethernetMonitorEntry 10 }  
        
	ethernetMonitorTxErr OBJECT-TYPE
        SYNTAX INTEGER
        MAX-ACCESS read-only                
        STATUS current
        DESCRIPTION
           ""
        ::= { ethernetMonitorEntry 11 }  
        
	ethernetMonitorTxErrLate OBJECT-TYPE
        SYNTAX INTEGER
        MAX-ACCESS read-only                
        STATUS current
        DESCRIPTION
           ""
        ::= { ethernetMonitorEntry 12 }  
        
	ethernetMonitorTxErrExcessive OBJECT-TYPE
        SYNTAX INTEGER
        MAX-ACCESS read-only                
        STATUS current
        DESCRIPTION
           ""
        ::= { ethernetMonitorEntry 13 }  
        
	ethernetMonitorRxErr OBJECT-TYPE
        SYNTAX INTEGER
        MAX-ACCESS read-only                
        STATUS current
        DESCRIPTION
           ""
        ::= { ethernetMonitorEntry 14 }  
        
	ethernetMonitorRxErrCRC OBJECT-TYPE
        SYNTAX INTEGER
        MAX-ACCESS read-only                
        STATUS current
        DESCRIPTION
           ""
        ::= { ethernetMonitorEntry 15 }  
        
	ethernetMonitorRxErrDiscard OBJECT-TYPE
        SYNTAX INTEGER
        MAX-ACCESS read-only                
        STATUS current
        DESCRIPTION
           ""
        ::= { ethernetMonitorEntry 16}  
        
	ethernetMonitorRxErrUndersize OBJECT-TYPE
        SYNTAX INTEGER
        MAX-ACCESS read-only                
        STATUS current
        DESCRIPTION
           ""
        ::= { ethernetMonitorEntry 17 }  
        
	ethernetMonitorRxErrFragments OBJECT-TYPE
        SYNTAX INTEGER
        MAX-ACCESS read-only                
        STATUS current
        DESCRIPTION
           ""
        ::= { ethernetMonitorEntry 18 }  
        
	ethernetMonitorRxErrOversize OBJECT-TYPE
        SYNTAX INTEGER
        MAX-ACCESS read-only                
        STATUS current
        DESCRIPTION
           ""
        ::= { ethernetMonitorEntry 19 }  
        
	ethernetMonitorRxErrJabber OBJECT-TYPE
        SYNTAX INTEGER
        MAX-ACCESS read-only                
        STATUS current
        DESCRIPTION
           ""
        ::= { ethernetMonitorEntry 20 }  
        

	ethernetMonitorReset OBJECT-TYPE
        SYNTAX INTEGER
        MAX-ACCESS read-write
        STATUS current
        DESCRIPTION
           ""
        ::= { ethernetMonitor 2 }  

    monitorPortTable OBJECT-TYPE
        SYNTAX SEQUENCE OF MonitorPortEntry
        MAX-ACCESS not-accessible               
        STATUS current
        DESCRIPTION
            "The  port table of monitor function."
        ::= { ethernetMonitor 3 }
    
    monitorPortEntry OBJECT-TYPE
        SYNTAX MonitorPortEntry
        MAX-ACCESS not-accessible               
        STATUS current
        DESCRIPTION
            "The port table entry of monitor function."
        INDEX { portIndex }        
        ::= { monitorPortTable 1 }
        
    MonitorPortEntry ::=
        SEQUENCE {
            monitorLinkStatus
                INTEGER,
            monitorSpeed
                INTEGER,
			monitorFDXFlowCtrl
                INTEGER,
            monitorAutoMDI
                INTEGER,
            monitorConnectedIP
                DisplayString,    
            monitorTraffic
                INTEGER
        }
        
    monitorLinkStatus OBJECT-TYPE
        SYNTAX INTEGER { disable(-1), off(0), on(1) }
        MAX-ACCESS read-only                
        STATUS current
        DESCRIPTION
            "The port link status."
        ::= { monitorPortEntry 1}
    
    monitorSpeed OBJECT-TYPE
        SYNTAX INTEGER
            {
            speed100M-Full(3),
            speed100M-Half(2),
            speed10M-Full(1),
            speed10M-Half(0),
            na(-1)
            }
        MAX-ACCESS read-only
        STATUS current
        DESCRIPTION
            "The port speed and duplex status."
        ::= { monitorPortEntry 2 }

    monitorFDXFlowCtrl OBJECT-TYPE
        SYNTAX INTEGER { off(0),on(1)}
        MAX-ACCESS read-only                
        STATUS current
        DESCRIPTION
            "The Full-Duplex flow control status"
        ::= { monitorPortEntry 3 }

    
    monitorAutoMDI OBJECT-TYPE
        SYNTAX INTEGER
            {
            mdiX(1),
            mdi(0),
            na(-1)
            }
        MAX-ACCESS read-only
        STATUS current
        DESCRIPTION
            "The port MDI/MDIX status."
        ::= { monitorPortEntry 4 }

    monitorConnectedIP OBJECT-TYPE
        SYNTAX DisplayString
        MAX-ACCESS read-only                
        STATUS current
        DESCRIPTION
            "The IP of connected device."
        ::= { monitorPortEntry 5 }
    
    monitorTraffic OBJECT-TYPE
        SYNTAX INTEGER
        MAX-ACCESS read-only                
        STATUS current
        DESCRIPTION
            "The trafic loading percentage of port."
        ::= { monitorPortEntry 6 }
        


            
-- -----------------------------------------------------------------------------------------------------
-- System Monitoring -> Ethernet Status -> Trunk Table										1.7.3.8
-- -----------------------------------------------------------------------------------------------------
	trunkTableList OBJECT IDENTIFIER ::= { ethernetStatus 8 }

    trunkTable OBJECT-TYPE
        SYNTAX SEQUENCE OF TrunkEntry
        MAX-ACCESS not-accessible               
        STATUS current
        DESCRIPTION
            "Port Trunking Table."
        ::= { trunkTableList 1 }

    trunkEntry OBJECT-TYPE
        SYNTAX TrunkEntry
        MAX-ACCESS not-accessible               
        STATUS current
        DESCRIPTION
            "Port Trunking Entry."
        INDEX { trunkIndex, trunkPort }
        ::= { trunkTable 1 }
        
    TrunkEntry ::=
        SEQUENCE {     
            trunkIndex
                INTEGER,
            trunkPort
            	INTEGER,
            trunkStatus
            	INTEGER
            }     
    
    trunkIndex OBJECT-TYPE
        SYNTAX INTEGER 
        MAX-ACCESS read-only
        STATUS current
        DESCRIPTION
            "Trunking Group Index."
        ::= { trunkEntry 1 }

    trunkPort OBJECT-TYPE
        SYNTAX INTEGER 
        MAX-ACCESS read-only
        STATUS current
        DESCRIPTION
            "Trunking Group Member Port."
        ::= { trunkEntry 2 }

    trunkStatus OBJECT-TYPE
        SYNTAX INTEGER {
        	success(1),
        	fail(2),
        	standby(3)
        }
        MAX-ACCESS read-only
        STATUS current
        DESCRIPTION
            "Trunking Port Status."
        ::= { trunkEntry 3 }
        
-- -----------------------------------------------------------------------------------------------------
-- System Monitoring -> Ethernet Status -> VLAN Table										1.7.3.9
-- -----------------------------------------------------------------------------------------------------
	vlanList OBJECT IDENTIFIER ::= { ethernetStatus 9 }

    vlanTable OBJECT-TYPE
        SYNTAX SEQUENCE OF VlanEntry
        MAX-ACCESS not-accessible               
        STATUS current
        DESCRIPTION
            "The VLAN table."
        ::= { vlanList 1 }
    
    vlanEntry OBJECT-TYPE
        SYNTAX VlanEntry
        MAX-ACCESS not-accessible               
        STATUS current
        DESCRIPTION
            "VLAN Entry."
        INDEX { vlanId }
        ::= { vlanTable 1 }
        
    VlanEntry ::=
        SEQUENCE {
            vlanId
                INTEGER,           
            joinedAccessPorts
                PortList,
            joinedTrunkPorts
                PortList
            } 
    
    vlanId OBJECT-TYPE
        SYNTAX INTEGER (1..4094)
        MAX-ACCESS read-only                
        STATUS current
        DESCRIPTION
            "The VLAN id."
        ::= { vlanEntry 1 }  

    joinedAccessPorts OBJECT-TYPE
        SYNTAX PortList
        MAX-ACCESS read-only                
        STATUS current
        DESCRIPTION
            "The access ports that joined this VID."
        ::= { vlanEntry 2 }  
        
    joinedTrunkPorts OBJECT-TYPE
        SYNTAX PortList
        MAX-ACCESS read-only                
        STATUS current
        DESCRIPTION
            "The trunk ports that joined this VID."
        ::= { vlanEntry 3 }     

-- -----------------------------------------------------------------------------------------------------
-- System Monitoring -> Ethernet Status -> Communication Redundancy Status						1.7.3.10
-- -----------------------------------------------------------------------------------------------------
	commRedStatus OBJECT IDENTIFIER ::= { ethernetStatus 10 }
	
	activeProtocolOfRedundancy OBJECT-TYPE
        SYNTAX INTEGER  { none(0), spanningTree(1), turboRing(2), turboRingV2(3), turboChain(4)}
        MAX-ACCESS read-only
        STATUS current
        DESCRIPTION
        "This shows the active redundancy protocol of this server now. The none(0) stauts will 
         be showed if only if the server's redundancy protocol is set to spanning tree and none of
         ports enable spanning tree."
        ::= { commRedStatus 1 }


	spanningTreeStatus OBJECT IDENTIFIER ::= { commRedStatus 2 } 
    
    spanningTreeRoot OBJECT-TYPE
        SYNTAX INTEGER  { no(0), yes(1) }
        MAX-ACCESS read-only                
        STATUS current
        DESCRIPTION
            "The root of spanning tree."
        ::= { spanningTreeStatus 1 }

    
    spanningTreeStatusTable OBJECT-TYPE
        SYNTAX SEQUENCE OF SpanningTreeStatusEntry
        MAX-ACCESS not-accessible               
        STATUS current
        DESCRIPTION
            "The spanning tree table."
        ::= { spanningTreeStatus 2 }
    
    spanningTreeStatusEntry OBJECT-TYPE
        SYNTAX SpanningTreeStatusEntry
        MAX-ACCESS not-accessible               
        STATUS current
        DESCRIPTION
            "The spanning tree port entry."
        INDEX { spanningTreeIndex }
        ::= { spanningTreeStatusTable 1 }
        
    SpanningTreeStatusEntry ::=
        SEQUENCE {
            spanningTreePortStatus
                INTEGER
        }
       
    spanningTreePortStatus OBJECT-TYPE
        SYNTAX INTEGER 
            {
            portDisabled(0),
            notSpanningTreePort(1),
            linkDown(2),
            blocked(3),
            learning(4),
            forwarding(5)
            }
        MAX-ACCESS read-only                
        STATUS current
        DESCRIPTION
            "The port status of spanning tree protocol."
        ::= { spanningTreeStatusEntry 1 }      
        
        
        
    turboRingStatus OBJECT IDENTIFIER ::= { commRedStatus 3 }     
        
    turboRingMaster OBJECT-TYPE
        SYNTAX INTEGER  { no(0), yes(1) }
        MAX-ACCESS read-only                
        STATUS current
        DESCRIPTION
            "Is this a Master or Slave."
        ::= { turboRingStatus 1 }
    
    turboRingPortTable OBJECT-TYPE
        SYNTAX SEQUENCE OF TurboRingPortEntry
        MAX-ACCESS not-accessible               
        STATUS current
        DESCRIPTION
            "Turbo Ring Port Table."
        ::= { turboRingStatus 2 }
    
    turboRingPortEntry OBJECT-TYPE
        SYNTAX TurboRingPortEntry
        MAX-ACCESS not-accessible               
        STATUS current
        DESCRIPTION
            "Turbo Ring Port Entry."
        INDEX { turboRingPortIndex  }
        ::= { turboRingPortTable 1 }
        
    TurboRingPortEntry ::=
        SEQUENCE {
            turboRingPortIndex
                INTEGER,
            turboRingPortStatus
                INTEGER,  
            turboRingPortDesignatedBridge
                OCTET STRING,
            turboRingPortDesignatedPort
                INTEGER
        }
        
    turboRingPortIndex OBJECT-TYPE
        SYNTAX INTEGER 
        MAX-ACCESS read-only                
        STATUS current
        DESCRIPTION
            "Turbo Ring Port Index."
        ::= { turboRingPortEntry 1 }
    
    turboRingPortStatus OBJECT-TYPE
        SYNTAX INTEGER 
            {
            portDisabled(0),     
            notTurboRingPort(1),
            linkDown(2),
            blocked(3),
            learning(4),
            forwarding(5)
            }
        MAX-ACCESS read-only
        STATUS current
        DESCRIPTION
            "Turbo Ring Port Status."
        ::= { turboRingPortEntry 2 } 
        
     turboRingPortDesignatedBridge OBJECT-TYPE
        SYNTAX  MacAddress
        MAX-ACCESS  read-only
        STATUS  mandatory
        DESCRIPTION
             "The MAC address of the bridge which this
              port considers to be the Designated Bridge for
              this port's segment."
        ::= { turboRingPortEntry 3 }

    turboRingPortDesignatedPort OBJECT-TYPE
        SYNTAX  INTEGER
        MAX-ACCESS  read-only
        STATUS  mandatory
        DESCRIPTION
              "The Port Number of the port on the Designated
               Bridge for this port's segment."  
     ::= { turboRingPortEntry 4 }
        
    turboRingDesignatedMaster OBJECT-TYPE
        SYNTAX  MacAddress
        MAX-ACCESS  read-only
        STATUS  mandatory
        DESCRIPTION
             "The MAC address of the bridge which is the Master of the TURBO RING."
        ::= { turboRingStatus 3 } 

    turboRingCouplingPortStatus OBJECT-TYPE
        SYNTAX INTEGER 
            {
            portDisabled(0),      
            notCouplingPort(1),
            linkDown(2),
            blocked(3),
            forwarding(5)
            }
        MAX-ACCESS read-only                
        STATUS current
        DESCRIPTION
            "The coupling port status of ring coupling function."
        ::= { turboRingStatus 4 }  
        
    turboRingControlPortStatus OBJECT-TYPE
        SYNTAX INTEGER 
            {
            portDisabled(0),      
            notControlPort(1),
            linkDown(2),
            blocked(3),
            forwarding(5),
            inactive(6),
            active(7)
            }
        MAX-ACCESS read-only                
        STATUS current
        DESCRIPTION
            "The control port status of ring coupling function."
        ::= { turboRingStatus 5 }       
           
    turboRingBrokenStatus OBJECT-TYPE
        SYNTAX INTEGER
            {
            na(0),
            normal(1),
            broken(2)
            }
        MAX-ACCESS read-only
        STATUS current
        DESCRIPTION
            "Turbo Ring broken display."
        ::= { turboRingStatus 6 }   

    turboRingV2Status OBJECT IDENTIFIER ::= { commRedStatus 4 } 
    
    turboRingV2Ring1Status OBJECT IDENTIFIER ::= { turboRingV2Status 1 }  
    
    masterStatusRing1 OBJECT-TYPE
        SYNTAX INTEGER  { no(0), yes(1) }
        MAX-ACCESS read-only                 
        STATUS current
        DESCRIPTION
            "Set this to be Master."
        ::= { turboRingV2Ring1Status 1 }    
        
    designatedMasterRing1 OBJECT-TYPE
        SYNTAX  MacAddress
        MAX-ACCESS  read-only
        STATUS  mandatory
        DESCRIPTION
             "The MAC address of the bridge which is the Master of the turboRingV2."
        ::= { turboRingV2Ring1Status 2 } 
    
    rdnt1stPortStatusRing1 OBJECT-TYPE
        SYNTAX INTEGER 
            {
            disabled(0),
            notRedundant(1),
            linkdown(2),      
            blocking(3),
            learning(4),
            forwarding(5) 
            }
        MAX-ACCESS  read-only
        STATUS  current
        DESCRIPTION
             "The status of 1st Redundant Port on the turboRingV2."
        ::= { turboRingV2Ring1Status 3 } 
                
    rdnt2ndPortStatusRing1 OBJECT-TYPE
        SYNTAX INTEGER 
            {
            disabled(0),
            notRedundant(1),
            linkdown(2),      
            blocking(3),
            learning(4),
            forwarding(5) 
            }
        MAX-ACCESS  read-only
        STATUS current
        DESCRIPTION
             "The status of 2nd Redundant Port on the turboRingV2."
        ::= { turboRingV2Ring1Status 4 }
       
    brokenStatusRing1 OBJECT-TYPE
        SYNTAX INTEGER
            {
            na(0),
            normal(1),
            broken(2)
        }
        MAX-ACCESS read-only
        STATUS current
        DESCRIPTION
            "turboRingV2 broken display."
        ::= { turboRingV2Ring1Status 5 }  
    
    turboRingV2Ring2Status OBJECT IDENTIFIER ::= { turboRingV2Status 2 }
    
    masterStatusRing2 OBJECT-TYPE
        SYNTAX INTEGER  { no(0), yes(1) }
        MAX-ACCESS read-only                 
        STATUS current
        DESCRIPTION
            "Set this to be Master."
        ::= { turboRingV2Ring2Status 1 }    
        
    designatedMasterRing2 OBJECT-TYPE
        SYNTAX  MacAddress
        MAX-ACCESS  read-only
        STATUS  mandatory
        DESCRIPTION
             "The MAC address of the bridge which is the Master of the turboRingV2."
        ::= { turboRingV2Ring2Status 2 } 
        
    rdnt1stPortStatusRing2 OBJECT-TYPE
        SYNTAX INTEGER 
            {
            disabled(0),
            notRedundant(1),
            linkdown(2),      
            blocking(3),
            learning(4),
            forwarding(5) 
            }
        MAX-ACCESS  read-only
        STATUS  current
        DESCRIPTION
             "The status of 1st Redundant Port on the turboRingV2."
        ::= { turboRingV2Ring2Status 3 }         
  
   rdnt2ndPortStatusRing2 OBJECT-TYPE
        SYNTAX INTEGER 
            {
            disabled(0),
            notRedundant(1),
            linkdown(2),      
            blocking(3),
            learning(4),
            forwarding(5) 
            }
        MAX-ACCESS  read-only
        STATUS  current
        DESCRIPTION
             "The status of 2nd Redundant Port on the turboRingV2."
        ::= { turboRingV2Ring2Status 4 }
                 
    brokenStatusRing2 OBJECT-TYPE
        SYNTAX INTEGER
            {
            na(0),
            normal(1),
            broken(2)
            }
        MAX-ACCESS read-only
        STATUS current
        DESCRIPTION
            "turboRingV2 broken display."
        ::= { turboRingV2Ring2Status 5 }                           
     
    turboRingV2CouplingStatus OBJECT IDENTIFIER ::= { turboRingV2Status 3 }

    coupling1stPortStatus OBJECT-TYPE
        SYNTAX INTEGER 
            {
            disabled(0),
            notRedundant(1),
            linkdown(2),      
            blocking(3),
            learning(4),
            forwarding(5) 
            }
        MAX-ACCESS read-only                
        STATUS current
        DESCRIPTION
            "The 1st coupling port status of coupling function."
        ::= { turboRingV2CouplingStatus 1 }  
              
    coupling2ndPortStatus OBJECT-TYPE
        SYNTAX INTEGER 
            {
            disabled(0),
            notRedundant(1),
            linkdown(2),      
            blocking(3),
            learning(4),
            forwarding(5) 
            }
        MAX-ACCESS read-only                
        STATUS current
        DESCRIPTION
            "The 2nd coupling port status of coupling function."
        ::= { turboRingV2CouplingStatus 2 }            

    turboChainStatus OBJECT IDENTIFIER ::= { commRedStatus 5 }     
        
    turboChainPort1Status OBJECT-TYPE
        SYNTAX INTEGER 
            {
            notTurboChainPort(0),
            linkDown(1),
            blocking(2),      
            blocked(3),
            forwarding(4),
            na(5) 
            }
        MAX-ACCESS read-only                
        STATUS current
        DESCRIPTION
            "Turbo Chain Port 1 Status"
        ::= { turboChainStatus 1 }

    turboChainPort2Status OBJECT-TYPE
        SYNTAX INTEGER 
            {
            notTurboChainPort(0),
            linkDown(1),
            blocking(2),      
            blocked(3),
            forwarding(4),
            na(5) 
            }
        MAX-ACCESS read-only                
        STATUS current
        DESCRIPTION
            "Turbo Chain Port 2 Status"
        ::= { turboChainStatus 2 }

    turboChainPort1PartnerBridge OBJECT-TYPE
        SYNTAX  MacAddress
        MAX-ACCESS  read-only
        STATUS  mandatory
        DESCRIPTION
             "The MAC address of the bridge which is attatched to this device's Turbo Chain Port 1."
        ::= { turboChainStatus 3 } 

    turboChainPort2PartnerBridge OBJECT-TYPE
        SYNTAX  MacAddress
        MAX-ACCESS  read-only
        STATUS  mandatory
        DESCRIPTION
             "The MAC address of the bridge which is attatched to this device's Turbo Chain Port 2."
        ::= { turboChainStatus 4 } 

-- -----------------------------------------------------------------------------------------------------
-- Restart														1.8
-- -----------------------------------------------------------------------------------------------------
    restart OBJECT IDENTIFIER ::= { swMgmt 8 }

-- -----------------------------------------------------------------------------------------------------
-- Restart -> restart system									1.8.1
-- -----------------------------------------------------------------------------------------------------
    restartSystem OBJECT-TYPE
        SYNTAX INTEGER   {
            restart(1)
            }

        MAX-ACCESS read-write               
        STATUS current
        DESCRIPTION
            "Restart the NPort S8000 series device server. Be sure
            to save all of your configuration changes before
            you restart the system. Otherwise, all of the changes will be
            lost."
        ::= { restart 1 }

-- -----------------------------------------------------------------------------------------------------
-- Restart -> restart port										1.8.2
-- -----------------------------------------------------------------------------------------------------
    restartPortNumber OBJECT-TYPE
        SYNTAX INTEGER    {
            port1(0),
            port2(1),
            port3(2),
            port4(3)
            }
        MAX-ACCESS read-write               
        STATUS current
        DESCRIPTION
            "Restart serial port. Restarting will cause port reseting."
        ::= { restart 2 }

		
END
