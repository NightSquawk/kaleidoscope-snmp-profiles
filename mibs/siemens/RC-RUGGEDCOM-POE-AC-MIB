RC-RUGGEDCOM-POE-AC-MIB DEFINITIONS ::= BEGIN

IMPORTS
    MODULE-IDENTITY				    FROM SNMPv2-SMI
    AGENT-CAPABILITIES              FROM SNMPv2-CONF
    ruggedcomAgentCapability        FROM RUGGEDCOM-MIB;

ruggedcomRcPoeACModule MODULE-IDENTITY
    LAST-UPDATED "201206011700Z"      -- Jun 01, 17:00 EST 2012;
    ORGANIZATION "RuggedCom - Industrial Strength Networks"
    CONTACT-INFO
       "Postal: RuggedCom Inc.
                300 Applewood Crescent
                Concord, Ontario, 
                L4K 5C7 Canada
        Tel:    1-905-856-5288
        E-Mail: support@ruggedcom.com"
    DESCRIPTION
        "The capabilities description for RUGGEDCOM-POE-MIB."
        
	REVISION    "201206011700Z"      -- Jun 01, 17:00 EST 2012;
    DESCRIPTION                
        "Fixed typos in group name."

	REVISION    "201102221700Z"      -- Feb 22, 17:00 EST 2011;
    DESCRIPTION                
        "Initial version of this MIB module."

    ::= { ruggedcomAgentCapability 14 }
    
-- ---------------------------------------------------------------------- --
--  POE MIB Agent Capabilities
-- ---------------------------------------------------------------------- --
ruggedcomRcPoeAC   	AGENT-CAPABILITIES
    PRODUCT-RELEASE "ROS-CF52"
    STATUS          current
    DESCRIPTION
        "RUGGEDCOM-POE-MIB Agent Capabilities."

    SUPPORTS RUGGEDCOM-POE-MIB
    
        INCLUDES    { rcPoeTableGroup }

-- ---------------------------------------------------------------------- --
    ::= { ruggedcomRcPoeACModule 1 }
    
    
    
ruggedcomRcPoe2AC   	AGENT-CAPABILITIES
    PRODUCT-RELEASE "ROS-CF52 based RuggedCom devices that support 
    				 RUGGEDCOM-POE-MIB."
    STATUS          current
    DESCRIPTION
        "RUGGEDCOM-POE-MIB Agent Capabilities."

    SUPPORTS RUGGEDCOM-POE-MIB
    
        INCLUDES    { rcBasePoeGroup,
        			  rcBasePoeStatusGroup,
        			  rcPoeTableGroup,
        			  rcPoeTablePriorityGroup,
        			  rcPoeNotifyGroup }

-- ---------------------------------------------------------------------- --
    ::= { ruggedcomRcPoeACModule 2 }
END
