RUGGEDCOM-IP-MIB DEFINITIONS ::= BEGIN

IMPORTS
    MODULE-IDENTITY, OBJECT-IDENTITY, 
    OBJECT-TYPE, IpAddress	        	FROM SNMPv2-SMI
    OBJECT-GROUP			       	    FROM SNMPv2-CONF    
    ruggedcomMgmt				        FROM RUGGEDCOM-MIB;
	
rcIp MODULE-IDENTITY
    LAST-UPDATED "201312111000Z"      -- Dec 10,  10:00 EST 2013
    ORGANIZATION "RuggedCom"
    CONTACT-INFO
       "Postal: RuggedCom Inc.
                300 Applewood Crescent
                Concord, Ontario, 
                L4K 5C7 Canada
        Tel:    1-905-856-5288
        E-Mail: support@ruggedcom.com"
    DESCRIPTION
        "RuggedCom MIB relevant to RuggedCom Discovery Protocol."

	REVISION    "201312111000Z"      -- Dec 10,  10:00 EST 2013
    DESCRIPTION                
        "Added object related to default management interface."

	REVISION    "200811111000Z"      -- Nov 11, 10:00 EST 2008
    DESCRIPTION                
        "Initial version of this MIB module."

    ::= { ruggedcomMgmt 3 }

-- ---------------------------------------------------------------------- --
-- branches rcIp 2 to 4 are reserved for future use
-- ---------------------------------------------------------------------- --
rcIpConformance OBJECT IDENTIFIER ::= { rcIp 5 }
rcIpGroups OBJECT IDENTIFIER ::= { rcIpConformance 1 }

-- ---------------------------------------------------------------------- --
--  RcdpInfo subtrees
-- ---------------------------------------------------------------------- --


rcIpConfig OBJECT-IDENTITY
    STATUS      current
    DESCRIPTION
        "The main subtree for Ip Interface configuration in RuggedCom
        devices."
    ::= { rcIp  1 }  


-- ---------------------------------------------------------------------- --
--  Device Management Interface objects
-- ---------------------------------------------------------------------- --

rcIpConfigMgmtIpAddress OBJECT-TYPE
    SYNTAX  	IpAddress
    MAX-ACCESS  read-write
    STATUS      current
    DESCRIPTION
         "The Management IP Address of the device."
    ::= { rcIpConfig 1}

rcIpConfigMgmtIpSubnet OBJECT-TYPE
    SYNTAX  	IpAddress
    MAX-ACCESS  read-write
    STATUS      current
    DESCRIPTION
        "The subnet mask associated with the management IP address 
 	    entry.  The value of the mask is an IP address with all the
 	    network bits set to 1 and all the hosts bits set to 0."
    ::= { rcIpConfig 2}

rcIpConfigDefaultGateway OBJECT-TYPE
    SYNTAX  	IpAddress
    MAX-ACCESS  read-write
    STATUS      current
    DESCRIPTION 
         "The default IP Gateway for the device."
    ::= { rcIpConfig 3}


-- ---------------------------------------------------------------------- --
--  Device Default Management Interface objects
-- ---------------------------------------------------------------------- --

rcIpConfigDfltMgmtIpAddress OBJECT-TYPE
    SYNTAX  	IpAddress
    MAX-ACCESS  read-write
    STATUS      current
    DESCRIPTION
         "The Management IP Address of the device."
    ::= { rcIpConfig 4}

rcIpConfigDfltMgmtIpSubnet OBJECT-TYPE
    SYNTAX  	IpAddress
    MAX-ACCESS  read-write
    STATUS      current
    DESCRIPTION
        "The subnet mask associated with the management IP address 
 	    entry.  The value of the mask is an IP address with all the
 	    network bits set to 1 and all the hosts bits set to 0."
    ::= { rcIpConfig 5}

-- ---------------------------------------------------------------------- --
--  Object Groups
-- ---------------------------------------------------------------------- --

rcIpObjectsGroup OBJECT-GROUP
    OBJECTS     {
					rcIpConfigMgmtIpAddress,
					rcIpConfigMgmtIpSubnet,
					rcIpConfigDefaultGateway 
                }
    STATUS      current
    DESCRIPTION 
        "A group of objects providing information about management Ip 
        interface of the device.
        This group is mandatory."
    ::= { rcIpGroups 1 }    

rcIpObjectsGroupDflt OBJECT-GROUP
    OBJECTS     {
					rcIpConfigDfltMgmtIpAddress,
					rcIpConfigDfltMgmtIpSubnet
                }
    STATUS      current
    DESCRIPTION 
        "A group of objects providing information about default management  
        IP interface of the device.
        This group is mandatory for devices that have default management 
        interface built in."
    ::= { rcIpGroups 2 }    
END
