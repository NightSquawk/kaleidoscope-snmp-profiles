--*********************************
-- MIB table for Papago ethernet meter
--
-- by Ing. Jiri Valek
-- www.papouch.com - Copyright (c) 2014
--
--*********************************

papago_1th_2di_1do_V01-MIB DEFINITIONS ::= BEGIN

IMPORTS  
--	MODULE-IDENTITY,
--	OBJECT-TYPE,
--	NOTIFICATION-TYPE,     
		enterprises,
		IpAddress,
		Counter,
		Gauge,
		TimeTicks
    	FROM RFC1155-SMI
    OBJECT-TYPE
		FROM RFC-1212    
	DisplayString
		FROM RFC1213-MIB
	TRAP-TYPE
		FROM RFC-1215
    ;
    		
papouchProjekt	   OBJECT IDENTIFIER ::= { enterprises 18248 }	
papago_1th_2di_1do OBJECT IDENTIFIER ::= { papouchProjekt 34 }	
version            OBJECT IDENTIFIER ::= { papago_1th_2di_1do 1 }            

deviceVar         OBJECT IDENTIFIER ::= { version 1 }
in_table          OBJECT IDENTIFIER ::= { version 2 } 
out_table         OBJECT IDENTIFIER ::= { version 3 }     
channel_table     OBJECT IDENTIFIER ::= { version 4 }

--
-- Type Definitions
--
PositiveInteger ::= INTEGER (0..65535)
---
--- TABULKA VSTUPU, cteni a zapis
---
 inputsTable OBJECT-TYPE
	SYNTAX  SEQUENCE OF InputsEntry
	ACCESS  not-accessible
	STATUS  current
	DESCRIPTION	""
 ::= { in_table 1 }
 
 inputsEntry OBJECT-TYPE
	SYNTAX  InputsEntry
	ACCESS  not-accessible
	STATUS  current
	DESCRIPTION	""
	INDEX   { index }
 ::= { inputsTable 1 }
 
 InputsEntry ::=
    SEQUENCE { 
        inState
            INTEGER,
        inCounter
            Counter,  
        inDecNum
            INTEGER,
        inUnit
            DisplayString
    }
--    
-- OID 1.3.6.1.4.1.18248.34.1.2.1.1.1.1 - x  
-- Stav vstupu
--  
inState  OBJECT-TYPE
	SYNTAX  	INTEGER
	ACCESS		read-only
	STATUS		current
	DESCRIPTION	"0 = OFF, 1 = ON"
::= { inputsEntry 1 }         

--
-- OID 1.3.6.1.4.1.18248.34.1.2.1.1.2.1 - x  
-- Hodnota citace
--
inCounter  OBJECT-TYPE
	SYNTAX  	Counter
	ACCESS		read-write
	STATUS		current
	DESCRIPTION	"Input counter (write=decrement)"
::= { inputsEntry 2 } 

--
-- OID 1.3.6.1.4.1.18248.34.1.2.1.1.3.1 - x  
-- Pocet desetinnych mist
--
inDecNum  OBJECT-TYPE
	SYNTAX  	INTEGER
	ACCESS		read-only
	STATUS		current
	DESCRIPTION	"Number of decimal places (0 - 3)"
::= { inputsEntry 3 }  

--
-- OID 1.3.6.1.4.1.18248.34.1.2.1.1.4.1 - x  
-- Jednotka
--
inUnit  OBJECT-TYPE
	SYNTAX  	DisplayString
	ACCESS		read-only
	STATUS		current
	DESCRIPTION	"String units"
::= { inputsEntry 4 }



---
--- TABULKA VYSTUPU, cteni a zapis
---
 outputsTable OBJECT-TYPE
	SYNTAX  SEQUENCE OF OutputsEntry
	ACCESS  not-accessible
	STATUS  current
	DESCRIPTION	""
 ::= { out_table 1 }
 
 outputsEntry OBJECT-TYPE
	SYNTAX  OutputsEntry
	ACCESS  not-accessible
	STATUS  current
	DESCRIPTION	""
	INDEX   { index }
 ::= { outputsTable 1 }
 
 OutputsEntry ::=
    SEQUENCE { 
        outState
            INTEGER,
    }
--    
-- OID 1.3.6.1.4.1.18248.34.1.3.1.1.1.1 - x  
-- Stav vystupu
--  
outState  OBJECT-TYPE
	SYNTAX  	INTEGER
	ACCESS		read-write
	STATUS		current
	DESCRIPTION	"0 = OFF, 1 = ON"
::= { outputsEntry 1 }         

 
 
---
--- TABULKA KANALU, cteni
---
 channelTable OBJECT-TYPE
	SYNTAX  SEQUENCE OF ChannelEntry
	ACCESS  not-accessible
	STATUS  current
	DESCRIPTION	""
 ::= { channel_table 1 }  
 
 channelEntry OBJECT-TYPE
	SYNTAX  ChannelEntry
	ACCESS  not-accessible
	STATUS  current
	DESCRIPTION	""
	INDEX   { index }
 ::= { channelTable 1 }
 
 ChannelEntry ::=
    SEQUENCE {
    	inChType
	        INTEGER, 
	    inChStatus
	        INTEGER,
	    inChValue
	        INTEGER,  
	    inChUnits
            INTEGER
            
    } 
--
-- OID 1.3.6.1.4.1.18248.34.1.4.1.1.1 - 3  
-- Typ veliciny
--  
inChType  OBJECT-TYPE
	SYNTAX  	INTEGER
	ACCESS		read-only
	STATUS		current
	DESCRIPTION	"0 = not used, 1 = temperature, 2 = humidity, 3 = dew point"
::= { channelEntry 1 }     

--
-- OID 1.3.6.1.4.1.18248.34.1.4.1.1.2.1 - 3  
-- Status kanalu
--  
inChStatus  OBJECT-TYPE
	SYNTAX  	INTEGER
	ACCESS		read-only
	STATUS		current
	DESCRIPTION	"0 = OK,1 = Not available,2 = over-flow,3 = under-flow,4=ERR"
::= { channelEntry 2 }                   

--
-- OID 1.3.6.1.4.1.18248.34.1.4.1.1.3.1 - 3  
-- Namerena hodnota
--
inChValue  OBJECT-TYPE
	SYNTAX  	INTEGER
	ACCESS		read-only
	STATUS		current
	DESCRIPTION	""
::= { channelEntry 3 }        

--
-- OID 1.3.6.1.4.1.18248.34.1.4.1.1.4.1 - 3  
-- Jednotka
--
inChUnits  OBJECT-TYPE
	SYNTAX  	INTEGER
	ACCESS		read-only
	STATUS		current
	DESCRIPTION	"Temperature and Dew point: 0 = Celsius, 1 = Fahrenfeit, 2 = Kelvin, Humidity: 0 = Percents"
::= { channelEntry 4 }
 
--
-- OID 1.3.6.1.4.1.18248.34.1.1.1.0  
-- Název zarizeni
--
deviceName OBJECT-TYPE
	SYNTAX		DisplayString
	ACCESS		read-only
	STATUS		mandatory
	DESCRIPTION	"Device Name"
::= { deviceVar 1 } 
--
-- OID 1.3.6.1.4.1.18248.34.1.1.2.0  
-- Chybove hlaseni v trapu
--
psAlarmString OBJECT-TYPE
	SYNTAX		DisplayString
	ACCESS		read-only
	STATUS		mandatory
	DESCRIPTION	""
::= { deviceVar 2 } 


watch_msg TRAP-TYPE
        ENTERPRISE deviceVar
        VARIABLES {deviceName,psAlarmString}
		DESCRIPTION ""
            ::= 1   


END
