--       SMC-MIB
-- MIB generated on Monday, September 29, 2014 at 10:40:53
-- 
--  Super Micro top-level MIB
-- _SNMP
-- 

	SMC-MIB DEFINITIONS ::= BEGIN
 
		IMPORTS
			OBJECT-GROUP			
				FROM SNMPv2-CONF			
			enterprises, IpAddress, Integer32, Unsigned32, OBJECT-TYPE, 
			MODULE-IDENTITY			
				FROM SNMPv2-SMI			
			PhysAddress			
				FROM SNMPv2-TC;
	
	
--  September 16, 2014 at 17:26 GMT
-- September 16, 2014 at 17:29 GMT
-- September 16, 2014 at 17:26 GMT
-- September 16, 2014 at 17:29 GMT
		-- 1.3.6.1.4.1.10876
		supermicro MODULE-IDENTITY 
			LAST-UPDATED "201409161726Z"		-- September 16, 2014 at 17:26 GMT
			ORGANIZATION 
				"Super Micro"
			CONTACT-INFO 
				"Email: support@supermicro.com"
			DESCRIPTION 
				"Top-level infrastructure of SMC MIB tree."
			REVISION "201409161729Z"		-- September 16, 2014 at 17:29 GMT
			DESCRIPTION 
				"The module for SuperMicro Computer Ltd."
			::= { enterprises 10876 }

		
	
	
--
-- Node definitions
--
	
--  Node definitions
-- 
		-- 1.3.6.1.4.1.10876.1
		cmm OBJECT IDENTIFIER ::= { supermicro 1 }

		
--   Network section
		-- 1.3.6.1.4.1.10876.1.1
		network OBJECT IDENTIFIER ::= { cmm 1 }

		
		-- 1.3.6.1.4.1.10876.1.1.1
		netGrpBasicSettings OBJECT-GROUP
			OBJECTS { netMACAddr, netIPAutoConf, netHostName, netIPAddr, netNetmask, 
				netGateway, netDNS1, netDNS2 }
			STATUS current
			DESCRIPTION 
				"The group for network basic settings."
			::= { network 1 }

		
		-- 1.3.6.1.4.1.10876.1.1.2
		netMACAddr OBJECT-TYPE
			SYNTAX PhysAddress
			MAX-ACCESS read-only
			STATUS current
			DESCRIPTION
				"CMM MAC address.
				"
			::= { network 2 }

		
		-- 1.3.6.1.4.1.10876.1.1.3
		netIPAutoConf OBJECT-TYPE
			SYNTAX INTEGER
				{
				none(0),
				dhcp(1),
				bootp(2)
				}
			MAX-ACCESS read-write
			STATUS current
			DESCRIPTION
				"CMM IP auto configuration options.
				Available options are None, DHCP, BOOTP.
				"
			::= { network 3 }

		
		-- 1.3.6.1.4.1.10876.1.1.4
		netHostName OBJECT-TYPE
			SYNTAX OCTET STRING (SIZE (0..63))
			MAX-ACCESS read-write
			STATUS current
			DESCRIPTION
				"CMM host name in DHCP mode. User customizable.
				"
			::= { network 4 }

		
		-- 1.3.6.1.4.1.10876.1.1.5
		netIPAddr OBJECT-TYPE
			SYNTAX IpAddress
			MAX-ACCESS read-write
			STATUS current
			DESCRIPTION
				"CMM IPv4 address."
			::= { network 5 }

		
		-- 1.3.6.1.4.1.10876.1.1.6
		netNetmask OBJECT-TYPE
			SYNTAX IpAddress
			MAX-ACCESS read-write
			STATUS current
			DESCRIPTION
				"CMM IPv4 subnet mask."
			::= { network 6 }

		
		-- 1.3.6.1.4.1.10876.1.1.7
		netGateway OBJECT-TYPE
			SYNTAX IpAddress
			MAX-ACCESS read-write
			STATUS current
			DESCRIPTION
				"CMM IPv4 gateway IP address."
			::= { network 7 }

		
		-- 1.3.6.1.4.1.10876.1.1.8
		netDNS1 OBJECT-TYPE
			SYNTAX IpAddress
			MAX-ACCESS read-write
			STATUS current
			DESCRIPTION
				"CMM primary DNS server IPv4 address."
			::= { network 8 }

		
		-- 1.3.6.1.4.1.10876.1.1.9
		netDNS2 OBJECT-TYPE
			SYNTAX IpAddress
			MAX-ACCESS read-write
			STATUS current
			DESCRIPTION
				"CMM secondary DNS server IPv4 address."
			::= { network 9 }

		
		-- 1.3.6.1.4.1.10876.1.1.10
		netGrpMiscSettings OBJECT-GROUP
			OBJECTS { netPortHTTPS, netPortHTTP, netPortSSH, 
netBandWidthLimit, netSSHAccess, 

				netSetupProtocol }
			STATUS current
			DESCRIPTION 
				"The group for network miscellaneous settings."
			::= { network 10 }

		
		-- 1.3.6.1.4.1.10876.1.1.11
		netPortHTTPS OBJECT-TYPE
			SYNTAX Integer32
			MAX-ACCESS read-write
			STATUS current
			DESCRIPTION
				"Port for Remote Console & HTTPS."
			::= { network 11 }

		
		-- 1.3.6.1.4.1.10876.1.1.12
		netPortHTTP OBJECT-TYPE
			SYNTAX Integer32
			MAX-ACCESS read-write
			STATUS current
			DESCRIPTION
				"Port for HTTP."
			::= { network 12 }

		
		-- 1.3.6.1.4.1.10876.1.1.13
		netPortSSH OBJECT-TYPE
			SYNTAX Integer32
			MAX-ACCESS read-write
			STATUS current
			DESCRIPTION
				"Port for SSH."
			::= { network 13 }

		
		-- 1.3.6.1.4.1.10876.1.1.14
		netBandWidthLimit OBJECT-TYPE
			SYNTAX Integer32 (1..10000)
			UNITS "kbit/s"
			MAX-ACCESS read-write
			STATUS current
			DESCRIPTION
				"Network Bandwidth limit setting. The MAX limitation is 10000 kbit/s"
			::= { network 14 }

		
		-- 1.3.6.1.4.1.10876.1.1.15
		netSSHAccess OBJECT-TYPE
			SYNTAX INTEGER
				{
				disabled(0),
				enabled(1)
				}
			MAX-ACCESS read-write
			STATUS current
			DESCRIPTION
				"SSH access enable/disable status."
			::= { network 15 }

		
		-- 1.3.6.1.4.1.10876.1.1.16
		netSetupProtocol OBJECT-TYPE
			SYNTAX INTEGER
				{
				disabled(0),
				enabled(1)
				}
			MAX-ACCESS read-write
			STATUS current
			DESCRIPTION
				"Setup protocol enable/diable status."
			::= { network 16 }

		
		-- 1.3.6.1.4.1.10876.1.1.17
		netGrpLANSettings OBJECT-GROUP
			OBJECTS { netLANSpeed, netLANDuplexMode }
			STATUS current
			DESCRIPTION 
				"The group for LAN interface settings."
			::= { network 17 }

		
		-- 1.3.6.1.4.1.10876.1.1.18
		netLANSpeed OBJECT-TYPE
			SYNTAX INTEGER
				{
				autoDetect(0),
				spd10M(1),
				spd100M(2)
				}
			MAX-ACCESS read-write
			STATUS current
			DESCRIPTION
				"LAN interface speed.
				Available options are AutoDetect, 10Mbps, 100Mbps."
			::= { network 18 }

		
		-- 1.3.6.1.4.1.10876.1.1.19
		netLANDuplexMode OBJECT-TYPE
			SYNTAX INTEGER
				{
				autoDetect(0),
				halfDuplex(1),
				fullDeplex(2)
				}
			MAX-ACCESS read-write
			STATUS current
			DESCRIPTION
				"LAN interface duplex mode.
				Available options are AutoDetect, Half Duplex, Full Duplex."
			::= { network 19 }

		
		-- 1.3.6.1.4.1.10876.1.1.20
		netGrpDDNSSettings OBJECT-GROUP
			OBJECTS { netDDNSStatus, netDDNSServer, netDDNSSystemMode, netDDNSHostName
, netDDNSUserName, 

				netDDNSPassword, netDDNSCheckTime, netDDNSCheckInterval }
			STATUS current
			DESCRIPTION 
				"The group for dynamic DNS settings."
			::= { network 20 }

		
		-- 1.3.6.1.4.1.10876.1.1.21
		netDDNSStatus OBJECT-TYPE
			SYNTAX INTEGER
				{
				disabled(0),
				enabled(1)
				}
			MAX-ACCESS read-write
			STATUS current
			DESCRIPTION
				"DDNS enable/disable status."
			::= { network 21 }

		
		-- 1.3.6.1.4.1.10876.1.1.22
		netDDNSServer OBJECT-TYPE
			SYNTAX OCTET STRING
			MAX-ACCESS read-only
			STATUS current
			DESCRIPTION
				"DDNS server."
			::= { network 22 }

		
		-- 1.3.6.1.4.1.10876.1.1.23
		netDDNSSystemMode OBJECT-TYPE
			SYNTAX INTEGER
				{
				dynamic(0),
				custom(1)
				}
			MAX-ACCESS read-write
			STATUS current
			DESCRIPTION
				"DDNS system mode.
				Available options are Dynamic, Custom."
			::= { network 23 }

		
		-- 1.3.6.1.4.1.10876.1.1.24
		netDDNSHostName OBJECT-TYPE
			SYNTAX OCTET STRING
			MAX-ACCESS read-write
			STATUS current
			DESCRIPTION
				"CMM host name in DDNS mode."
			::= { network 24 }

		
		-- 1.3.6.1.4.1.10876.1.1.25
		netDDNSUserName OBJECT-TYPE
			SYNTAX OCTET STRING
			MAX-ACCESS read-write
			STATUS current
			DESCRIPTION
				"CMM user name in DDNS mode."
			::= { network 25 }

		
		-- 1.3.6.1.4.1.10876.1.1.26
		netDDNSPassword OBJECT-TYPE
			SYNTAX OCTET STRING
			MAX-ACCESS read-write
			STATUS current
			DESCRIPTION
				"CMM password in DDNS mode."
			::= { network 26 }

		
		-- 1.3.6.1.4.1.10876.1.1.27
		netDDNSCheckTime OBJECT-TYPE
			SYNTAX OCTET STRING
			MAX-ACCESS read-write
			STATUS current
			DESCRIPTION
				"DDNS check time."
			::= { network 27 }

		
		-- 1.3.6.1.4.1.10876.1.1.28
		netDDNSCheckInterval OBJECT-TYPE
			SYNTAX INTEGER
				{
				time24h(0),
				time12h(1),
				time6h(2),
				time3h(3),
				time2h(4),
				time10min(5),
				time1min(6)
				}
			MAX-ACCESS read-write
			STATUS current
			DESCRIPTION
				"DDNS check interval.
				Available options are 24h, 12h, 6h, 3h, 2h, 10min, 1min."
			::= { network 28 }

		
--   Security section
		-- 1.3.6.1.4.1.10876.1.2
		security OBJECT IDENTIFIER ::= { cmm 2 }

		
		-- 1.3.6.1.4.1.10876.1.2.1
		secGrpEncryptionSettings OBJECT-GROUP
			OBJECTS { secForceWebHTTPS, secKVMEncryption }
			STATUS current
			DESCRIPTION 
				"The group for encryption settings."
			::= { security 1 }

		
		-- 1.3.6.1.4.1.10876.1.2.2
		secForceWebHTTPS OBJECT-TYPE
			SYNTAX INTEGER
				{
				disabled(0),
				enabled(1)
				}
			MAX-ACCESS read-write
			STATUS current
			DESCRIPTION
				"Force HTTPS for web access."
			::= { security 2 }

		
		-- 1.3.6.1.4.1.10876.1.2.3
		secKVMEncryption OBJECT-TYPE
			SYNTAX INTEGER
				{
				off(0),
				try(1),
				force(2)
				}
			MAX-ACCESS read-write
			STATUS current
			DESCRIPTION
				"KVM encryption setting.
				Available options are Off, Try, Force."
			::= { security 3 }

		
		-- 1.3.6.1.4.1.10876.1.2.4
		secGrpIPAccessControl OBJECT-GROUP
			OBJECTS { secIPFWStatus, secIPFWDefaultPolicy }
			STATUS current
			DESCRIPTION 
				"The group for IP access control settings."
			::= { security 4 }

		
		-- 1.3.6.1.4.1.10876.1.2.5
		secIPFWStatus OBJECT-TYPE
			SYNTAX INTEGER
				{
				disabled(0),
				enabled(1)
				}
			MAX-ACCESS read-write
			STATUS current
			DESCRIPTION
				"IP Access Control enable/disable status."
			::= { security 5 }

		
		-- 1.3.6.1.4.1.10876.1.2.6
		secIPFWDefaultPolicy OBJECT-TYPE
			SYNTAX INTEGER
				{
				accept(0),
				drop(1)
				}
			MAX-ACCESS read-write
			STATUS current
			DESCRIPTION
				"Default policy for IP access control."
			::= { security 6 }

		
		-- 1.3.6.1.4.1.10876.1.2.7
		secGrpLoginFailBlocking OBJECT-GROUP
			OBJECTS { secLoginRetryCount, secLoginBlockTime }
			STATUS current
			DESCRIPTION 
				"The group for login failure blocking settings."
			::= { security 7 }

		
		-- 1.3.6.1.4.1.10876.1.2.8
		secLoginRetryCount OBJECT-TYPE
			SYNTAX Integer32 (-1 | 0..1024)
			MAX-ACCESS read-write
			STATUS current
			DESCRIPTION
				"Max number of failed login attempts [0..1024].
				-1 for Infinite."
			::= { security 8 }

		
		-- 1.3.6.1.4.1.10876.1.2.9
		secLoginBlockTime OBJECT-TYPE
			SYNTAX Integer32 (-1 | 0..10080)
			UNITS "minute"
			MAX-ACCESS read-write
			STATUS current
			DESCRIPTION
				"Block time for the login failure retry limit reached [0..10080]min.
				-1 for infinite."
			::= { security 9 }

		
		-- 1.3.6.1.4.1.10876.1.2.10
		secIPMISettings OBJECT-GROUP
			OBJECTS { secSMCRAKP }
			STATUS current
			DESCRIPTION 
				"The group for IPMI security control settings"
			::= { security 10 }

		
		-- 1.3.6.1.4.1.10876.1.2.11
		secSMCRAKP OBJECT-TYPE
			SYNTAX INTEGER
				{
				disabled(0),
				enabled(1)
				}
			MAX-ACCESS read-write
			STATUS current
			DESCRIPTION
				"SMC RAKP feature enable/disable. It's disabled by default.
				IPMI LAN channel will be disabled while this inidication is enabled.
				"
			::= { security 11 }

		
--   User Management section
		-- 1.3.6.1.4.1.10876.1.3
		users OBJECT IDENTIFIER ::= { cmm 3 }

		
		-- 1.3.6.1.4.1.10876.1.3.1
		userMgmtTable OBJECT-TYPE
			SYNTAX SEQUENCE OF UserMgmtEntry
			MAX-ACCESS not-accessible
			STATUS current
			DESCRIPTION
				"This is the table for CMM user account management."
			::= { users 1 }

		
		-- 1.3.6.1.4.1.10876.1.3.1.1
		userMgmtEntry OBJECT-TYPE
			SYNTAX UserMgmtEntry
			MAX-ACCESS not-accessible
			STATUS current
			DESCRIPTION
				"The table entry for a CMM user."
			INDEX { userIndex }
			::= { userMgmtTable 1 }

		
		UserMgmtEntry ::=
			SEQUENCE { 
				userIndex
					Integer32,
				userPresence
					INTEGER,
				userName
					OCTET STRING,
				userFullName
					OCTET STRING,
				userPassword
					OCTET STRING,
				userEmail
					OCTET STRING,
				userMobile
					OCTET STRING,
				userPriv
					INTEGER
			 }

		-- 1.3.6.1.4.1.10876.1.3.1.1.1
		userIndex OBJECT-TYPE
			SYNTAX Integer32 (1..65535)
			MAX-ACCESS not-accessible
			STATUS current
			DESCRIPTION
				"The index for user management table."
			::= { userMgmtEntry 1 }

		
		-- 1.3.6.1.4.1.10876.1.3.1.1.2
		userPresence OBJECT-TYPE
			SYNTAX INTEGER
				{
				notPresent(0),
				present(1)
				}
			MAX-ACCESS read-only
			STATUS current
			DESCRIPTION
				"The indication for user presence."
			::= { userMgmtEntry 2 }

		
		-- 1.3.6.1.4.1.10876.1.3.1.1.3
		userName OBJECT-TYPE
			SYNTAX OCTET STRING (SIZE (0..15))
			MAX-ACCESS read-write
			STATUS current
			DESCRIPTION
				"The indication for user name."
			::= { userMgmtEntry 3 }

		
		-- 1.3.6.1.4.1.10876.1.3.1.1.4
		userFullName OBJECT-TYPE
			SYNTAX OCTET STRING (SIZE (0..15))
			MAX-ACCESS read-write
			STATUS current
			DESCRIPTION
				"The indication for user full name."
			::= { userMgmtEntry 4 }

		
		-- 1.3.6.1.4.1.10876.1.3.1.1.5
		userPassword OBJECT-TYPE
			SYNTAX OCTET STRING (SIZE (0..19))
			MAX-ACCESS read-write
			STATUS current
			DESCRIPTION
				"The indication for user password."
			::= { userMgmtEntry 5 }

		
		-- 1.3.6.1.4.1.10876.1.3.1.1.6
		userEmail OBJECT-TYPE
			SYNTAX OCTET STRING (SIZE (0..63))
			MAX-ACCESS read-write
			STATUS current
			DESCRIPTION
				"The indication for user email address."
			::= { userMgmtEntry 6 }

		
		-- 1.3.6.1.4.1.10876.1.3.1.1.7
		userMobile OBJECT-TYPE
			SYNTAX OCTET STRING (SIZE (0..63))
			MAX-ACCESS read-write
			STATUS current
			DESCRIPTION
				"The indication for user mobile number."
			::= { userMgmtEntry 7 }

		
		-- 1.3.6.1.4.1.10876.1.3.1.1.8
		userPriv OBJECT-TYPE
			SYNTAX INTEGER
				{
				noaccess(0),
				user(1),
				operator(2),
				administrator(3),
				oem(4)
				}
			MAX-ACCESS read-write
			STATUS current
			DESCRIPTION
				"The indication for user IPMI privilege."
			::= { userMgmtEntry 8 }

		
--   Blade Management section
		-- 1.3.6.1.4.1.10876.1.4
		blades OBJECT IDENTIFIER ::= { cmm 4 }

		
		-- 1.3.6.1.4.1.10876.1.4.1
		bladeTable OBJECT-TYPE
			SYNTAX SEQUENCE OF BladeEntry
			MAX-ACCESS not-accessible
			STATUS current
			DESCRIPTION
				"The table for blade summary from the CMM management perspective."
			::= { blades 1 }

		
		-- 1.3.6.1.4.1.10876.1.4.1.1
		bladeEntry OBJECT-TYPE
			SYNTAX BladeEntry
			MAX-ACCESS not-accessible
			STATUS current
			DESCRIPTION
				"The table entry for blade summary information."
			INDEX { bladeIndex }
			::= { bladeTable 1 }

		
		BladeEntry ::=
			SEQUENCE { 
				bladeIndex
					Integer32,
				bladeSlotID
					Integer32,
				bladePresence
					INTEGER,
				bladeName
					OCTET STRING,
				bladeModel
					OCTET STRING,
				bladePowerStatus
					INTEGER,
				bladePowerWatt
					Integer32,
				bladePowerControl
					INTEGER,
				bladeACLostPolicy
					INTEGER,
				bladeKVMStatus
					INTEGER,
				bladeUID
					INTEGER,
				bladeError
					INTEGER,
				bladeMgmtIPAddr
					IpAddress,
				bladeSN
					OCTET STRING,
				bladeBMCVersion
					OCTET STRING,
				bladeBIOSVersion
					OCTET STRING
			 }

		-- 1.3.6.1.4.1.10876.1.4.1.1.1
		bladeIndex OBJECT-TYPE
			SYNTAX Integer32 (1..65535)
			MAX-ACCESS not-accessible
			STATUS current
			DESCRIPTION
				"The index for blade table."
			::= { bladeEntry 1 }

		
		-- 1.3.6.1.4.1.10876.1.4.1.1.2
		bladeSlotID OBJECT-TYPE
			SYNTAX Integer32 (1..128)
			MAX-ACCESS read-only
			STATUS current
			DESCRIPTION
				"The indication for blade slot ID."
			::= { bladeEntry 2 }

		
		-- 1.3.6.1.4.1.10876.1.4.1.1.3
		bladePresence OBJECT-TYPE
			SYNTAX INTEGER
				{
				notPresent(0),
				present(1)
				}
			MAX-ACCESS read-only
			STATUS current
			DESCRIPTION
				"The indication for blade presence."
			::= { bladeEntry 3 }

		
		-- 1.3.6.1.4.1.10876.1.4.1.1.4
		bladeName OBJECT-TYPE
			SYNTAX OCTET STRING
			MAX-ACCESS read-only
			STATUS current
			DESCRIPTION
				"The indication for blade name."
			::= { bladeEntry 4 }

		
		-- 1.3.6.1.4.1.10876.1.4.1.1.5
		bladeModel OBJECT-TYPE
			SYNTAX OCTET STRING
			MAX-ACCESS read-only
			STATUS current
			DESCRIPTION
				"The indication for blade model."
			::= { bladeEntry 5 }

		
		-- 1.3.6.1.4.1.10876.1.4.1.1.6
		bladePowerStatus OBJECT-TYPE
			SYNTAX INTEGER
				{
				powerOff(0),
				powerOn(1),
				powerReset(2),
				powerGracefulShutdown(3)
				}
			MAX-ACCESS read-write
			STATUS current
			DESCRIPTION
				"The indication for blade power status and control."
			::= { bladeEntry 6 }

		
		-- 1.3.6.1.4.1.10876.1.4.1.1.7
		bladePowerWatt OBJECT-TYPE
			SYNTAX Integer32
			UNITS "W"
			MAX-ACCESS read-only
			STATUS current
			DESCRIPTION
				"The indication for blade current power consumption."
			::= { bladeEntry 7 }

		
		-- 1.3.6.1.4.1.10876.1.4.1.1.8
		bladePowerControl OBJECT-TYPE
			SYNTAX INTEGER
				{
				powerCtrl0per(0),
				powerCtrl50per(1),
				powerCtrlFull(2)
				}
			MAX-ACCESS read-write
			STATUS current
			DESCRIPTION
				"The indication for blade power control."
			::= { bladeEntry 8 }

		
		-- 1.3.6.1.4.1.10876.1.4.1.1.9
		bladeACLostPolicy OBJECT-TYPE
			SYNTAX INTEGER
				{
				powerOff(0),
				powerOn(1),
				lastState(2)
				}
			MAX-ACCESS read-write
			STATUS current
			DESCRIPTION
				"The indication for blade AC power lost policy."
			::= { bladeEntry 9 }

		
		-- 1.3.6.1.4.1.10876.1.4.1.1.10
		bladeKVMStatus OBJECT-TYPE
			SYNTAX INTEGER
				{
				deselected(0),
				selected(1)
				}
			MAX-ACCESS read-write
			STATUS current
			DESCRIPTION
				"The indication for blade KVM status."
			::= { bladeEntry 10 }

		
		-- 1.3.6.1.4.1.10876.1.4.1.1.11
		bladeUID OBJECT-TYPE
			SYNTAX INTEGER
				{
				off(0),
				on(1)
				}
			MAX-ACCESS read-write
			STATUS current
			DESCRIPTION
				"The indication for blade UID status and control."
			::= { bladeEntry 11 }

		
		-- 1.3.6.1.4.1.10876.1.4.1.1.12
		bladeError OBJECT-TYPE
			SYNTAX INTEGER
				{
				normal(0),
				error(1)
				}
			MAX-ACCESS read-only
			STATUS current
			DESCRIPTION
				"The indication for blade error status."
			::= { bladeEntry 12 }

		
		-- 1.3.6.1.4.1.10876.1.4.1.1.13
		bladeMgmtIPAddr OBJECT-TYPE
			SYNTAX IpAddress
			MAX-ACCESS read-only
			STATUS current
			DESCRIPTION
				"The indication for blade BMC IPv4 address."
			::= { bladeEntry 13 }

		
		-- 1.3.6.1.4.1.10876.1.4.1.1.14
		bladeSN OBJECT-TYPE
			SYNTAX OCTET STRING
			MAX-ACCESS read-only
			STATUS current
			DESCRIPTION
				"The indication for blade serial number."
			::= { bladeEntry 14 }

		
		-- 1.3.6.1.4.1.10876.1.4.1.1.15
		bladeBMCVersion OBJECT-TYPE
			SYNTAX OCTET STRING
			MAX-ACCESS read-only
			STATUS current
			DESCRIPTION
				"The indication for blade BMC version."
			::= { bladeEntry 15 }

		
		-- 1.3.6.1.4.1.10876.1.4.1.1.16
		bladeBIOSVersion OBJECT-TYPE
			SYNTAX OCTET STRING
			MAX-ACCESS read-only
			STATUS current
			DESCRIPTION
				"The indication for blade BIOS version."
			::= { bladeEntry 16 }

		
--   Switch Management section
		-- 1.3.6.1.4.1.10876.1.5
		switches OBJECT IDENTIFIER ::= { cmm 5 }

		
		-- 1.3.6.1.4.1.10876.1.5.1
		switchGBTable OBJECT-TYPE
			SYNTAX SEQUENCE OF SwitchGBEntry
			MAX-ACCESS not-accessible
			STATUS current
			DESCRIPTION
				"The table for gigabit switch summary from the CMM management perspective."
			::= { switches 1 }

		
		-- 1.3.6.1.4.1.10876.1.5.1.1
		switchGBEntry OBJECT-TYPE
			SYNTAX SwitchGBEntry
			MAX-ACCESS not-accessible
			STATUS current
			DESCRIPTION
				"The table entry for gigabit switch summary information management."
			INDEX { switchGBIndex }
			::= { switchGBTable 1 }

		
		SwitchGBEntry ::=
			SEQUENCE { 
				switchGBIndex
					Integer32,
				switchGBSlotID
					Integer32,
				switchGBPresence
					INTEGER,
				switchGBName
					OCTET STRING,
				switchGBModel
					OCTET STRING,
				switchGBPowerStatus
					INTEGER,
				switchGBTemperature
					Integer32,
				switchGBError
					INTEGER,
				switchGBInitialized
					INTEGER,
				switchGB2V5
					OCTET STRING,
				switchGB1V25
					OCTET STRING
			 }

		-- 1.3.6.1.4.1.10876.1.5.1.1.1
		switchGBIndex OBJECT-TYPE
			SYNTAX Integer32 (1..65535)
			MAX-ACCESS not-accessible
			STATUS current
			DESCRIPTION
				"The index for gigabit switch table."
			::= { switchGBEntry 1 }

		
		-- 1.3.6.1.4.1.10876.1.5.1.1.2
		switchGBSlotID OBJECT-TYPE
			SYNTAX Integer32
			MAX-ACCESS read-only
			STATUS current
			DESCRIPTION
				"The indication of switch slot."
			::= { switchGBEntry 2 }

		
		-- 1.3.6.1.4.1.10876.1.5.1.1.3
		switchGBPresence OBJECT-TYPE
			SYNTAX INTEGER
				{
				notPresent(0),
				present(1)
				}
			MAX-ACCESS read-only
			STATUS current
			DESCRIPTION
				"The indication for switch presence."
			::= { switchGBEntry 3 }

		
		-- 1.3.6.1.4.1.10876.1.5.1.1.4
		switchGBName OBJECT-TYPE
			SYNTAX OCTET STRING
			MAX-ACCESS read-only
			STATUS current
			DESCRIPTION
				"The indication for switch name."
			::= { switchGBEntry 4 }

		
		-- 1.3.6.1.4.1.10876.1.5.1.1.5
		switchGBModel OBJECT-TYPE
			SYNTAX OCTET STRING (SIZE (0..16))
			MAX-ACCESS read-only
			STATUS current
			DESCRIPTION
				"The indication for switch model."
			::= { switchGBEntry 5 }

		
		-- 1.3.6.1.4.1.10876.1.5.1.1.6
		switchGBPowerStatus OBJECT-TYPE
			SYNTAX INTEGER
				{
				powerOff(0),
				powerOn(1),
				restart(2),
				reset(3),
				resetFactoryDefaults(4)
				}
			MAX-ACCESS read-write
			STATUS current
			DESCRIPTION
				"The indication for switch power status."
			::= { switchGBEntry 6 }

		
		-- 1.3.6.1.4.1.10876.1.5.1.1.7
		switchGBTemperature OBJECT-TYPE
			SYNTAX Integer32
			UNITS "C"
			MAX-ACCESS read-only
			STATUS current
			DESCRIPTION
				"The indication for switch temperature."
			::= { switchGBEntry 7 }

		
		-- 1.3.6.1.4.1.10876.1.5.1.1.8
		switchGBError OBJECT-TYPE
			SYNTAX INTEGER
				{
				normal(0),
				error(1)
				}
			MAX-ACCESS read-only
			STATUS current
			DESCRIPTION
				"The indication for switch error status."
			::= { switchGBEntry 8 }

		
		-- 1.3.6.1.4.1.10876.1.5.1.1.9
		switchGBInitialized OBJECT-TYPE
			SYNTAX INTEGER
				{
				notready(0),
				ok(1)
				}
			MAX-ACCESS read-only
			STATUS current
			DESCRIPTION
				"The indication for switch initialization status."
			::= { switchGBEntry 9 }

		
		-- 1.3.6.1.4.1.10876.1.5.1.1.10
		switchGB2V5 OBJECT-TYPE
			SYNTAX OCTET STRING
			UNITS "V"
			MAX-ACCESS read-only
			STATUS current
			DESCRIPTION
				"The indication for switch 2.5V voltage."
			::= { switchGBEntry 10 }

		
		-- 1.3.6.1.4.1.10876.1.5.1.1.11
		switchGB1V25 OBJECT-TYPE
			SYNTAX OCTET STRING
			UNITS "V"
			MAX-ACCESS read-only
			STATUS current
			DESCRIPTION
				"The indication for switch 1.25V voltage."
			::= { switchGBEntry 11 }

		
		-- 1.3.6.1.4.1.10876.1.5.2
		switch10GBTable OBJECT-TYPE
			SYNTAX SEQUENCE OF Switch10GBEntry
			MAX-ACCESS not-accessible
			STATUS current
			DESCRIPTION
				"The table for 10 gigabit switch summary from the CMM management 
				perspective."
			::= { switches 2 }

		
		-- 1.3.6.1.4.1.10876.1.5.2.1
		switch10GBEntry OBJECT-TYPE
			SYNTAX Switch10GBEntry
			MAX-ACCESS not-accessible
			STATUS current
			DESCRIPTION
				"The table entry for 10 gigabit switch summary information management."
			INDEX { switch10GBIndex }
			::= { switch10GBTable 1 }

		
		Switch10GBEntry ::=
			SEQUENCE { 
				switch10GBIndex
					Integer32,
				switch10GBSlotID
					Integer32,
				switch10GBPresence
					INTEGER,
				switch10GBName
					OCTET STRING,
				switch10GBModel
					OCTET STRING,
				switch10GBPowerStatus
					INTEGER,
				switch10GBTemperature
					Integer32,
				switch10GBError
					INTEGER,
				switch10GBInitialized
					INTEGER,
				switch10GB3V3
					OCTET STRING,
				switch10GB1V25
					OCTET STRING
			 }

		-- 1.3.6.1.4.1.10876.1.5.2.1.1
		switch10GBIndex OBJECT-TYPE
			SYNTAX Integer32 (1..65535)
			MAX-ACCESS not-accessible
			STATUS current
			DESCRIPTION
				"The index for 10 gigabit switch table."
			::= { switch10GBEntry 1 }

		
		-- 1.3.6.1.4.1.10876.1.5.2.1.2
		switch10GBSlotID OBJECT-TYPE
			SYNTAX Integer32
			MAX-ACCESS read-only
			STATUS current
			DESCRIPTION
				"The indication of switch slot."
			::= { switch10GBEntry 2 }

		
		-- 1.3.6.1.4.1.10876.1.5.2.1.3
		switch10GBPresence OBJECT-TYPE
			SYNTAX INTEGER
				{
				notPresent(0),
				present(1)
				}
			MAX-ACCESS read-only
			STATUS current
			DESCRIPTION
				"The indication for switch presence."
			::= { switch10GBEntry 3 }

		
		-- 1.3.6.1.4.1.10876.1.5.2.1.4
		switch10GBName OBJECT-TYPE
			SYNTAX OCTET STRING
			MAX-ACCESS read-only
			STATUS current
			DESCRIPTION
				"The indication for switch name."
			::= { switch10GBEntry 4 }

		
		-- 1.3.6.1.4.1.10876.1.5.2.1.5
		switch10GBModel OBJECT-TYPE
			SYNTAX OCTET STRING (SIZE (0..16))
			MAX-ACCESS read-only
			STATUS current
			DESCRIPTION
				"The indication for switch model."
			::= { switch10GBEntry 5 }

		
		-- 1.3.6.1.4.1.10876.1.5.2.1.6
		switch10GBPowerStatus OBJECT-TYPE
			SYNTAX INTEGER
				{
				powerOff(0),
				powerOn(1),
				restart(2),
				reset(3),
				resetFactoryDefaults(4)
				}
			MAX-ACCESS read-write
			STATUS current
			DESCRIPTION
				"The indication for switch power status."
			::= { switch10GBEntry 6 }

		
		-- 1.3.6.1.4.1.10876.1.5.2.1.7
		switch10GBTemperature OBJECT-TYPE
			SYNTAX Integer32
			UNITS "C"
			MAX-ACCESS read-only
			STATUS current
			DESCRIPTION
				"The indication for switch temperature."
			::= { switch10GBEntry 7 }

		
		-- 1.3.6.1.4.1.10876.1.5.2.1.8
		switch10GBError OBJECT-TYPE
			SYNTAX INTEGER
				{
				normal(0),
				error(1)
				}
			MAX-ACCESS read-only
			STATUS current
			DESCRIPTION
				"The indication for switch error status."
			::= { switch10GBEntry 8 }

		
		-- 1.3.6.1.4.1.10876.1.5.2.1.9
		switch10GBInitialized OBJECT-TYPE
			SYNTAX INTEGER
				{
				notready(0),
				ok(1)
				}
			MAX-ACCESS read-only
			STATUS current
			DESCRIPTION
				"The indication for switch initialization status."
			::= { switch10GBEntry 9 }

		
		-- 1.3.6.1.4.1.10876.1.5.2.1.10
		switch10GB3V3 OBJECT-TYPE
			SYNTAX OCTET STRING
			UNITS "V"
			MAX-ACCESS read-only
			STATUS current
			DESCRIPTION
				"The indication for switch 3.3V voltage."
			::= { switch10GBEntry 10 }

		
		-- 1.3.6.1.4.1.10876.1.5.2.1.11
		switch10GB1V25 OBJECT-TYPE
			SYNTAX OCTET STRING
			UNITS "V"
			MAX-ACCESS read-only
			STATUS current
			DESCRIPTION
				"The indication for switch 1.25V voltage."
			::= { switch10GBEntry 11 }

		
		-- 1.3.6.1.4.1.10876.1.5.3
		passthru10GBTable OBJECT-TYPE
			SYNTAX SEQUENCE OF Passthru10GBEntry
			MAX-ACCESS not-accessible
			STATUS current
			DESCRIPTION
				"The table for 10 gigabit passthrough summary from the CMM management 
				perspective."
			::= { switches 3 }

		
		-- 1.3.6.1.4.1.10876.1.5.3.1
		passthru10GBEntry OBJECT-TYPE
			SYNTAX Passthru10GBEntry
			MAX-ACCESS not-accessible
			STATUS current
			DESCRIPTION
				"The table entry for 10 gigabit passthrough summary information management
				."
			INDEX { passthru10GBIndex }
			::= { passthru10GBTable 1 }

		
		Passthru10GBEntry ::=
			SEQUENCE { 
				passthru10GBIndex
					Integer32,
				passthru10GBSlotID
					Integer32,
				passthru10GBPresence
					INTEGER,
				passthru10GBName
					OCTET STRING,
				passthru10GBModel
					OCTET STRING,
				passthru10GBPowerStatus
					INTEGER,
				passthru10GBTemperature
					Integer32,
				passthru10GBError
					INTEGER,
				passthru10GBInitialized
					INTEGER,
				passthru10GB3V3
					OCTET STRING,
				passthru10GB1V25
					OCTET STRING
			 }

		-- 1.3.6.1.4.1.10876.1.5.3.1.1
		passthru10GBIndex OBJECT-TYPE
			SYNTAX Integer32 (1..65535)
			MAX-ACCESS not-accessible
			STATUS current
			DESCRIPTION
				"The index for 10 gigabit passthrough table."
			::= { passthru10GBEntry 1 }

		
		-- 1.3.6.1.4.1.10876.1.5.3.1.2
		passthru10GBSlotID OBJECT-TYPE
			SYNTAX Integer32
			MAX-ACCESS read-only
			STATUS current
			DESCRIPTION
				"The indication of passthrough slot."
			::= { passthru10GBEntry 2 }

		
		-- 1.3.6.1.4.1.10876.1.5.3.1.3
		passthru10GBPresence OBJECT-TYPE
			SYNTAX INTEGER
				{
				notPresent(0),
				present(1)
				}
			MAX-ACCESS read-only
			STATUS current
			DESCRIPTION
				"The indication for passthrough presence."
			::= { passthru10GBEntry 3 }

		
		-- 1.3.6.1.4.1.10876.1.5.3.1.4
		passthru10GBName OBJECT-TYPE
			SYNTAX OCTET STRING
			MAX-ACCESS read-only
			STATUS current
			DESCRIPTION
				"The indication for passthrough name."
			::= { passthru10GBEntry 4 }

		
		-- 1.3.6.1.4.1.10876.1.5.3.1.5
		passthru10GBModel OBJECT-TYPE
			SYNTAX OCTET STRING (SIZE (0..16))
			MAX-ACCESS read-only
			STATUS current
			DESCRIPTION
				"The indication for passthrough model."
			::= { passthru10GBEntry 5 }

		
		-- 1.3.6.1.4.1.10876.1.5.3.1.6
		passthru10GBPowerStatus OBJECT-TYPE
			SYNTAX INTEGER
				{
				powerOff(0),
				powerOn(1),
				restart(2),
				reset(3),
				resetFactoryDefaults(4)
				}
			MAX-ACCESS read-write
			STATUS current
			DESCRIPTION
				"The indication for passthrough power status."
			::= { passthru10GBEntry 6 }

		
		-- 1.3.6.1.4.1.10876.1.5.3.1.7
		passthru10GBTemperature OBJECT-TYPE
			SYNTAX Integer32
			UNITS "C"
			MAX-ACCESS read-only
			STATUS current
			DESCRIPTION
				"The indication for passthrough temperature."
			::= { passthru10GBEntry 7 }

		
		-- 1.3.6.1.4.1.10876.1.5.3.1.8
		passthru10GBError OBJECT-TYPE
			SYNTAX INTEGER
				{
				normal(0),
				error(1)
				}
			MAX-ACCESS read-only
			STATUS current
			DESCRIPTION
				"The indication for passthrough error status."
			::= { passthru10GBEntry 8 }

		
		-- 1.3.6.1.4.1.10876.1.5.3.1.9
		passthru10GBInitialized OBJECT-TYPE
			SYNTAX INTEGER
				{
				notready(0),
				ok(1)
				}
			MAX-ACCESS read-only
			STATUS current
			DESCRIPTION
				"The indication for passthrough initialization status."
			::= { passthru10GBEntry 9 }

		
		-- 1.3.6.1.4.1.10876.1.5.3.1.10
		passthru10GB3V3 OBJECT-TYPE
			SYNTAX OCTET STRING
			UNITS "V"
			MAX-ACCESS read-only
			STATUS current
			DESCRIPTION
				"The indication for passthrough 3.3V voltage."
			::= { passthru10GBEntry 10 }

		
		-- 1.3.6.1.4.1.10876.1.5.3.1.11
		passthru10GB1V25 OBJECT-TYPE
			SYNTAX OCTET STRING
			UNITS "V"
			MAX-ACCESS read-only
			STATUS current
			DESCRIPTION
				"The indication for passthrough 1.25V voltage."
			::= { passthru10GBEntry 11 }

		
		-- 1.3.6.1.4.1.10876.1.5.4
		switchIBTable OBJECT-TYPE
			SYNTAX SEQUENCE OF SwitchIBEntry
			MAX-ACCESS not-accessible
			STATUS current
			DESCRIPTION
				"The table for IB switch summary from the CMM management 
				perspective."
			::= { switches 4 }

		
		-- 1.3.6.1.4.1.10876.1.5.4.1
		switchIBEntry OBJECT-TYPE
			SYNTAX SwitchIBEntry
			MAX-ACCESS not-accessible
			STATUS current
			DESCRIPTION
				"The table entry for IB switch summary information management."
			INDEX { switchIBIndex }
			::= { switchIBTable 1 }

		
		SwitchIBEntry ::=
			SEQUENCE { 
				switchIBIndex
					Integer32,
				switchIBSlotID
					Integer32,
				switchIBPresence
					INTEGER,
				switchIBName
					OCTET STRING,
				switchIBModel
					OCTET STRING,
				switchIBPowerStatus
					INTEGER,
				switchIBTemperature
					Integer32,
				switchIBInitialized
					INTEGER,
				switchIB3V3Aux
					OCTET STRING,
				switchIB3V3
					OCTET STRING,
				switchIB1V8
					OCTET STRING,
				switchIB1V2
					OCTET STRING,
				switchIBVVdd
					OCTET STRING
			 }

		-- 1.3.6.1.4.1.10876.1.5.4.1.1
		switchIBIndex OBJECT-TYPE
			SYNTAX Integer32 (1..65535)
			MAX-ACCESS not-accessible
			STATUS current
			DESCRIPTION
				"The index for IB switch table."
			::= { switchIBEntry 1 }

		
		-- 1.3.6.1.4.1.10876.1.5.4.1.2
		switchIBSlotID OBJECT-TYPE
			SYNTAX Integer32
			MAX-ACCESS read-only
			STATUS current
			DESCRIPTION
				"The indication of switch slot."
			::= { switchIBEntry 2 }

		
		-- 1.3.6.1.4.1.10876.1.5.4.1.3
		switchIBPresence OBJECT-TYPE
			SYNTAX INTEGER
				{
				notPresent(0),
				present(1)
				}
			MAX-ACCESS read-only
			STATUS current
			DESCRIPTION
				"The indication for switch presence."
			::= { switchIBEntry 3 }

		
		-- 1.3.6.1.4.1.10876.1.5.4.1.4
		switchIBName OBJECT-TYPE
			SYNTAX OCTET STRING
			MAX-ACCESS read-only
			STATUS current
			DESCRIPTION
				"The indication for switch name."
			::= { switchIBEntry 4 }

		
		-- 1.3.6.1.4.1.10876.1.5.4.1.5
		switchIBModel OBJECT-TYPE
			SYNTAX OCTET STRING (SIZE (0..16))
			MAX-ACCESS read-only
			STATUS current
			DESCRIPTION
				"The indication for switch model."
			::= { switchIBEntry 5 }

		
		-- 1.3.6.1.4.1.10876.1.5.4.1.6
		switchIBPowerStatus OBJECT-TYPE
			SYNTAX INTEGER
				{
				powerOff(0),
				powerOn(1),
				reset(2)
				}
			MAX-ACCESS read-write
			STATUS current
			DESCRIPTION
				"The indication for switch power status."
			::= { switchIBEntry 6 }

		
		-- 1.3.6.1.4.1.10876.1.5.4.1.7
		switchIBTemperature OBJECT-TYPE
			SYNTAX Integer32
			UNITS "C"
			MAX-ACCESS read-only
			STATUS current
			DESCRIPTION
				"The indication for switch temperature."
			::= { switchIBEntry 7 }

		
		-- 1.3.6.1.4.1.10876.1.5.4.1.8
		switchIBInitialized OBJECT-TYPE
			SYNTAX INTEGER
				{
				notready(0),
				ok(1)
				}
			MAX-ACCESS read-only
			STATUS current
			DESCRIPTION
				"The indication for switch initialization status."
			::= { switchIBEntry 8 }

		
		-- 1.3.6.1.4.1.10876.1.5.4.1.9
		switchIB3V3Aux OBJECT-TYPE
			SYNTAX OCTET STRING
			UNITS "V"
			MAX-ACCESS read-only
			STATUS current
			DESCRIPTION
				"The indication for switch 3.3V AUX voltage."
			::= { switchIBEntry 9 }

		
		-- 1.3.6.1.4.1.10876.1.5.4.1.10
		switchIB3V3 OBJECT-TYPE
			SYNTAX OCTET STRING
			UNITS "V"
			MAX-ACCESS read-only
			STATUS current
			DESCRIPTION
				"The indication for switch 3.3V voltage."
			::= { switchIBEntry 10 }

		
		-- 1.3.6.1.4.1.10876.1.5.4.1.11
		switchIB1V8 OBJECT-TYPE
			SYNTAX OCTET STRING
			UNITS "V"
			MAX-ACCESS read-only
			STATUS current
			DESCRIPTION
				"The indication for switch 1.8V voltage."
			::= { switchIBEntry 11 }

		
		-- 1.3.6.1.4.1.10876.1.5.4.1.12
		switchIB1V2 OBJECT-TYPE
			SYNTAX OCTET STRING
			UNITS "V"
			MAX-ACCESS read-only
			STATUS current
			DESCRIPTION
				"The indication for switch 1.2V voltage."
			::= { switchIBEntry 12 }

		
		-- 1.3.6.1.4.1.10876.1.5.4.1.13
		switchIBVVdd OBJECT-TYPE
			SYNTAX OCTET STRING
			UNITS "V"
			MAX-ACCESS read-only
			STATUS current
			DESCRIPTION
				"The indication for switch VVDD voltage."
			::= { switchIBEntry 13 }

		
		-- 1.3.6.1.4.1.10876.1.5.5
		switchIBQDRTable OBJECT-TYPE
			SYNTAX SEQUENCE OF SwitchIBQDREntry
			MAX-ACCESS not-accessible
			STATUS current
			DESCRIPTION
				"The table for IB QDR switch summary from the CMM management 
				perspective."
			::= { switches 5 }

		
		-- 1.3.6.1.4.1.10876.1.5.5.1
		switchIBQDREntry OBJECT-TYPE
			SYNTAX SwitchIBQDREntry
			MAX-ACCESS not-accessible
			STATUS current
			DESCRIPTION
				"The table entry for IB QDR switch summary information management."
			INDEX { switchIBQDRIndex }
			::= { switchIBQDRTable 1 }

		
		SwitchIBQDREntry ::=
			SEQUENCE { 
				switchIBQDRIndex
					Integer32,
				switchIBQDRSlotID
					Integer32,
				switchIBQDRPresence
					INTEGER,
				switchIBQDRName
					OCTET STRING,
				switchIBQDRModel
					OCTET STRING,
				switchIBQDRPowerStatus
					INTEGER,
				switchIBQDRTemperature
					Integer32,
				switchIBQDRInitialized
					INTEGER,
				switchIBQDRError
					INTEGER,
				switchIBQDR3V3
					OCTET STRING,
				switchIBQDR1V25
					OCTET STRING
			 }

		-- 1.3.6.1.4.1.10876.1.5.5.1.1
		switchIBQDRIndex OBJECT-TYPE
			SYNTAX Integer32 (1..65535)
			MAX-ACCESS not-accessible
			STATUS current
			DESCRIPTION
				"The index for IB QDR switch table."
			::= { switchIBQDREntry 1 }

		
		-- 1.3.6.1.4.1.10876.1.5.5.1.2
		switchIBQDRSlotID OBJECT-TYPE
			SYNTAX Integer32
			MAX-ACCESS read-only
			STATUS current
			DESCRIPTION
				"The indication of switch slot."
			::= { switchIBQDREntry 2 }

		
		-- 1.3.6.1.4.1.10876.1.5.5.1.3
		switchIBQDRPresence OBJECT-TYPE
			SYNTAX INTEGER
				{
				notPresent(0),
				present(1)
				}
			MAX-ACCESS read-only
			STATUS current
			DESCRIPTION
				"The indication for switch presence."
			::= { switchIBQDREntry 3 }

		
		-- 1.3.6.1.4.1.10876.1.5.5.1.4
		switchIBQDRName OBJECT-TYPE
			SYNTAX OCTET STRING
			MAX-ACCESS read-only
			STATUS current
			DESCRIPTION
				"The indication for switch name."
			::= { switchIBQDREntry 4 }

		
		-- 1.3.6.1.4.1.10876.1.5.5.1.5
		switchIBQDRModel OBJECT-TYPE
			SYNTAX OCTET STRING (SIZE (0..16))
			MAX-ACCESS read-only
			STATUS current
			DESCRIPTION
				"The indication for switch model."
			::= { switchIBQDREntry 5 }

		
		-- 1.3.6.1.4.1.10876.1.5.5.1.6
		switchIBQDRPowerStatus OBJECT-TYPE
			SYNTAX INTEGER
				{
				powerOff(0),
				powerOn(1),
				reset(2)
				}
			MAX-ACCESS read-write
			STATUS current
			DESCRIPTION
				"The indication for switch power status."
			::= { switchIBQDREntry 6 }

		
		-- 1.3.6.1.4.1.10876.1.5.5.1.7
		switchIBQDRTemperature OBJECT-TYPE
			SYNTAX Integer32
			UNITS "C"
			MAX-ACCESS read-only
			STATUS current
			DESCRIPTION
				"The indication for switch temperature."
			::= { switchIBQDREntry 7 }

		
		-- 1.3.6.1.4.1.10876.1.5.5.1.8
		switchIBQDRInitialized OBJECT-TYPE
			SYNTAX INTEGER
				{
				notready(0),
				ok(1)
				}
			MAX-ACCESS read-only
			STATUS current
			DESCRIPTION
				"The indication for switch initialization status."
			::= { switchIBQDREntry 8 }

		
		-- 1.3.6.1.4.1.10876.1.5.5.1.9
		switchIBQDRError OBJECT-TYPE
			SYNTAX INTEGER
				{
				normal(0),
				error(1)
				}
			MAX-ACCESS read-only
			STATUS current
			DESCRIPTION
				"The indication for switch error status."
			::= { switchIBQDREntry 9 }

		
		-- 1.3.6.1.4.1.10876.1.5.5.1.10
		switchIBQDR3V3 OBJECT-TYPE
			SYNTAX OCTET STRING
			UNITS "V"
			MAX-ACCESS read-only
			STATUS current
			DESCRIPTION
				"The indication for switch 3.3V voltage."
			::= { switchIBQDREntry 10 }

		
		-- 1.3.6.1.4.1.10876.1.5.5.1.11
		switchIBQDR1V25 OBJECT-TYPE
			SYNTAX OCTET STRING
			UNITS "V"
			MAX-ACCESS read-only
			STATUS current
			DESCRIPTION
				"The indication for switch 1.25V voltage."
			::= { switchIBQDREntry 11 }

		
		-- 1.3.6.1.4.1.10876.1.5.6
		switchIBFDRTable OBJECT-TYPE
			SYNTAX SEQUENCE OF SwitchIBFDREntry
			MAX-ACCESS not-accessible
			STATUS current
			DESCRIPTION
				"The table for IB FDR switch summary from the CMM management 
				perspective."
			::= { switches 6 }

		
		-- 1.3.6.1.4.1.10876.1.5.6.1
		switchIBFDREntry OBJECT-TYPE
			SYNTAX SwitchIBFDREntry
			MAX-ACCESS not-accessible
			STATUS current
			DESCRIPTION
				"The table entry for IB FDR switch summary information management."
			INDEX { switchIBFDRIndex }
			::= { switchIBFDRTable 1 }

		
		SwitchIBFDREntry ::=
			SEQUENCE { 
				switchIBFDRIndex
					Integer32,
				switchIBFDRSlotID
					Integer32,
				switchIBFDRPresence
					INTEGER,
				switchIBFDRName
					OCTET STRING,
				switchIBFDRModel
					OCTET STRING,
				switchIBFDRPowerStatus
					INTEGER,
				switchIBFDRTemp1
					Integer32,
				switchIBFDRTemp2
					Integer32,
				switchIBFDRInitialized
					INTEGER,
				switchIBFDRError
					INTEGER,
				switchIBFDR3V3
					OCTET STRING,
				switchIBFDR1V2
					OCTET STRING,
				switchIBFDR0V9
					OCTET STRING
			 }

		-- 1.3.6.1.4.1.10876.1.5.6.1.1
		switchIBFDRIndex OBJECT-TYPE
			SYNTAX Integer32 (1..65535)
			MAX-ACCESS not-accessible
			STATUS current
			DESCRIPTION
				"The index for IB FDR switch table."
			::= { switchIBFDREntry 1 }

		
		-- 1.3.6.1.4.1.10876.1.5.6.1.2
		switchIBFDRSlotID OBJECT-TYPE
			SYNTAX Integer32
			MAX-ACCESS read-only
			STATUS current
			DESCRIPTION
				"The indication of switch slot."
			::= { switchIBFDREntry 2 }

		
		-- 1.3.6.1.4.1.10876.1.5.6.1.3
		switchIBFDRPresence OBJECT-TYPE
			SYNTAX INTEGER
				{
				notPresent(0),
				present(1)
				}
			MAX-ACCESS read-only
			STATUS current
			DESCRIPTION
				"The indication for switch presence."
			::= { switchIBFDREntry 3 }

		
		-- 1.3.6.1.4.1.10876.1.5.6.1.4
		switchIBFDRName OBJECT-TYPE
			SYNTAX OCTET STRING
			MAX-ACCESS read-only
			STATUS current
			DESCRIPTION
				"The indication for switch name."
			::= { switchIBFDREntry 4 }

		
		-- 1.3.6.1.4.1.10876.1.5.6.1.5
		switchIBFDRModel OBJECT-TYPE
			SYNTAX OCTET STRING (SIZE (0..16))
			MAX-ACCESS read-only
			STATUS current
			DESCRIPTION
				"The indication for switch model."
			::= { switchIBFDREntry 5 }

		
		-- 1.3.6.1.4.1.10876.1.5.6.1.6
		switchIBFDRPowerStatus OBJECT-TYPE
			SYNTAX INTEGER
				{
				powerOff(0),
				powerOn(1),
				reset(2)
				}
			MAX-ACCESS read-write
			STATUS current
			DESCRIPTION
				"The indication for switch power status."
			::= { switchIBFDREntry 6 }

		
		-- 1.3.6.1.4.1.10876.1.5.6.1.7
		switchIBFDRTemp1 OBJECT-TYPE
			SYNTAX Integer32
			UNITS "C"
			MAX-ACCESS read-only
			STATUS current
			DESCRIPTION
				"The indication for switch temperature 1."
			::= { switchIBFDREntry 7 }

		
		-- 1.3.6.1.4.1.10876.1.5.6.1.8
		switchIBFDRTemp2 OBJECT-TYPE
			SYNTAX Integer32
			UNITS "C"
			MAX-ACCESS read-only
			STATUS current
			DESCRIPTION
				"The indication for switch temperature 2."
			::= { switchIBFDREntry 8 }

		
		-- 1.3.6.1.4.1.10876.1.5.6.1.9
		switchIBFDRInitialized OBJECT-TYPE
			SYNTAX INTEGER
				{
				notready(0),
				ok(1)
				}
			MAX-ACCESS read-only
			STATUS current
			DESCRIPTION
				"The indication for switch initialization status."
			::= { switchIBFDREntry 9 }

		
		-- 1.3.6.1.4.1.10876.1.5.6.1.10
		switchIBFDRError OBJECT-TYPE
			SYNTAX INTEGER
				{
				normal(0),
				error(1)
				}
			MAX-ACCESS read-only
			STATUS current
			DESCRIPTION
				"The indication for switch error status."
			::= { switchIBFDREntry 10 }

		
		-- 1.3.6.1.4.1.10876.1.5.6.1.11
		switchIBFDR3V3 OBJECT-TYPE
			SYNTAX OCTET STRING
			UNITS "V"
			MAX-ACCESS read-only
			STATUS current
			DESCRIPTION
				"The indication for switch 3.3V voltage."
			::= { switchIBFDREntry 11 }

		
		-- 1.3.6.1.4.1.10876.1.5.6.1.12
		switchIBFDR1V2 OBJECT-TYPE
			SYNTAX OCTET STRING
			UNITS "V"
			MAX-ACCESS read-only
			STATUS current
			DESCRIPTION
				"The indication for switch 1.2V voltage."
			::= { switchIBFDREntry 12 }

		
		-- 1.3.6.1.4.1.10876.1.5.6.1.13
		switchIBFDR0V9 OBJECT-TYPE
			SYNTAX OCTET STRING
			UNITS "V"
			MAX-ACCESS read-only
			STATUS current
			DESCRIPTION
				"The indication for switch 0.9V voltage."
			::= { switchIBFDREntry 13 }

		
--   Power Management section
		-- 1.3.6.1.4.1.10876.1.6
		powerSupplies OBJECT IDENTIFIER ::= { cmm 6 }

		
		-- 1.3.6.1.4.1.10876.1.6.1
		psuTable OBJECT-TYPE
			SYNTAX SEQUENCE OF PsuEntry
			MAX-ACCESS not-accessible
			STATUS current
			DESCRIPTION
				"The table for power supply management from CMM perspective."
			::= { powerSupplies 1 }

		
		-- 1.3.6.1.4.1.10876.1.6.1.1
		psuEntry OBJECT-TYPE
			SYNTAX PsuEntry
			MAX-ACCESS not-accessible
			STATUS current
			DESCRIPTION
				"The table entry for power supply management."
			INDEX { psuIndex }
			::= { psuTable 1 }

		
		PsuEntry ::=
			SEQUENCE { 
				psuIndex
					Integer32,
				psuSlotID
					Integer32,
				psuPresence
					INTEGER,
				psuName
					OCTET STRING,
				psuModel
					OCTET STRING,
				psuPowerStatus
					INTEGER,
				psuTemperature
					OCTET STRING,
				psuFAN1Speed
					Integer32,
				psuFAN2Speed
					Integer32,
				psuFAN3Speed
					Integer32,
				psuFAN4Speed
					Integer32,
				psuACInVoltage
					Integer32,
				psuMaxWatt
					Integer32,
				psuACInCurrent
					OCTET STRING,
				psuDCOutCurrent
					OCTET STRING,
				psuCurrentPwrUsage
					OCTET STRING,
				psuFWVersion
					OCTET STRING,
				psuFRUVersion
					OCTET STRING
			 }

		-- 1.3.6.1.4.1.10876.1.6.1.1.1
		psuIndex OBJECT-TYPE
			SYNTAX Integer32 (1..65535)
			MAX-ACCESS not-accessible
			STATUS current
			DESCRIPTION
				"The index for power supply table."
			::= { psuEntry 1 }

		
		-- 1.3.6.1.4.1.10876.1.6.1.1.2
		psuSlotID OBJECT-TYPE
			SYNTAX Integer32
			MAX-ACCESS read-only
			STATUS current
			DESCRIPTION
				"The indication for power supply slot index."
			::= { psuEntry 2 }

		
		-- 1.3.6.1.4.1.10876.1.6.1.1.3
		psuPresence OBJECT-TYPE
			SYNTAX INTEGER
				{
				notPresent(0),
				present(1)
				}
			MAX-ACCESS read-only
			STATUS current
			DESCRIPTION
				"The indication for power supply presence."
			::= { psuEntry 3 }

		
		-- 1.3.6.1.4.1.10876.1.6.1.1.4
		psuName OBJECT-TYPE
			SYNTAX OCTET STRING
			MAX-ACCESS read-only
			STATUS current
			DESCRIPTION
				"The indication for power supply name."
			::= { psuEntry 4 }

		
		-- 1.3.6.1.4.1.10876.1.6.1.1.5
		psuModel OBJECT-TYPE
			SYNTAX OCTET STRING (SIZE (0..16))
			MAX-ACCESS read-only
			STATUS current
			DESCRIPTION
				"The indication for power supply model name."
			::= { psuEntry 5 }

		
		-- 1.3.6.1.4.1.10876.1.6.1.1.6
		psuPowerStatus OBJECT-TYPE
			SYNTAX INTEGER
				{
				powerOff(0),
				powerOn(1),
				powerFailure(2)
				}
			MAX-ACCESS read-write
			STATUS current
			DESCRIPTION
				"The indication for power supply power status."
			::= { psuEntry 6 }

		
		-- 1.3.6.1.4.1.10876.1.6.1.1.7
		psuTemperature OBJECT-TYPE
			SYNTAX OCTET STRING
			MAX-ACCESS read-only
			STATUS current
			DESCRIPTION
				"The indication for power supply temperature."
			::= { psuEntry 7 }

		
		-- 1.3.6.1.4.1.10876.1.6.1.1.8
		psuFAN1Speed OBJECT-TYPE
			SYNTAX Integer32
			UNITS "RPM"
			MAX-ACCESS read-only
			STATUS current
			DESCRIPTION
				"The indication for power supply FAN1 speed (RPM)."
			::= { psuEntry 8 }

		
		-- 1.3.6.1.4.1.10876.1.6.1.1.9
		psuFAN2Speed OBJECT-TYPE
			SYNTAX Integer32
			UNITS "RPM"
			MAX-ACCESS read-only
			STATUS current
			DESCRIPTION
				"The indication for power supply FAN2 speed (RPM)."
			::= { psuEntry 9 }

		
		-- 1.3.6.1.4.1.10876.1.6.1.1.10
		psuFAN3Speed OBJECT-TYPE
			SYNTAX Integer32
			UNITS "RPM"
			MAX-ACCESS read-only
			STATUS current
			DESCRIPTION
				"The indication for power supply FAN3(if exists) speed (RPM)."
			::= { psuEntry 10 }

		
		-- 1.3.6.1.4.1.10876.1.6.1.1.11
		psuFAN4Speed OBJECT-TYPE
			SYNTAX Integer32
			UNITS "RPM"
			MAX-ACCESS read-only
			STATUS current
			DESCRIPTION
				"The indication for power supply FAN4(if exists) speed (RPM)."
			::= { psuEntry 11 }

		
		-- 1.3.6.1.4.1.10876.1.6.1.1.12
		psuACInVoltage OBJECT-TYPE
			SYNTAX Integer32
			UNITS "V"
			MAX-ACCESS read-only
			STATUS current
			DESCRIPTION
				"The indication for power supply AC Input Voltage."
			::= { psuEntry 12 }

		
		-- 1.3.6.1.4.1.10876.1.6.1.1.13
		psuMaxWatt OBJECT-TYPE
			SYNTAX Integer32
			UNITS "W"
			MAX-ACCESS read-only
			STATUS current
			DESCRIPTION
				"The indication for power supply MAX Watts."
			::= { psuEntry 13 }

		
		-- 1.3.6.1.4.1.10876.1.6.1.1.14
		psuACInCurrent OBJECT-TYPE
			SYNTAX OCTET STRING
			UNITS "A"
			MAX-ACCESS read-only
			STATUS current
			DESCRIPTION
				"The indication for power supply AC Input Current."
			::= { psuEntry 14 }

		
		-- 1.3.6.1.4.1.10876.1.6.1.1.15
		psuDCOutCurrent OBJECT-TYPE
			SYNTAX OCTET STRING
			UNITS "A"
			MAX-ACCESS read-only
			STATUS current
			DESCRIPTION
				"The indication for power supply DC Out Current."
			::= { psuEntry 15 }

		
		-- 1.3.6.1.4.1.10876.1.6.1.1.16
		psuCurrentPwrUsage OBJECT-TYPE
			SYNTAX OCTET STRING
			UNITS "%"
			MAX-ACCESS read-only
			STATUS current
			DESCRIPTION
				"The indication for power supply Current Power Usage."
			::= { psuEntry 16 }

		
		-- 1.3.6.1.4.1.10876.1.6.1.1.17
		psuFWVersion OBJECT-TYPE
			SYNTAX OCTET STRING
			MAX-ACCESS read-only
			STATUS current
			DESCRIPTION
				"The indication for power supply F/W version."
			::= { psuEntry 17 }

		
		-- 1.3.6.1.4.1.10876.1.6.1.1.18
		psuFRUVersion OBJECT-TYPE
			SYNTAX OCTET STRING
			MAX-ACCESS read-only
			STATUS current
			DESCRIPTION
				"The indication for power supply FRU version."
			::= { psuEntry 18 }

		
		-- 1.3.6.1.4.1.10876.1.6.2
		pwrGrpConsumption OBJECT-GROUP
			OBJECTS { pwrTotalPower, pwrBladeReserved, pwrPeripheralReserved, 
pwrAvailablePower, pwrCurrentMaxTemp, 

				pwrCurrentMaxTempModule }
			STATUS current
			DESCRIPTION 
				"The group for power consumption."
			::= { powerSupplies 2 }

		
		-- 1.3.6.1.4.1.10876.1.6.3
		pwrTotalPower OBJECT-TYPE
			SYNTAX Integer32
			MAX-ACCESS read-only
			STATUS current
			DESCRIPTION
				"The indication for total power of all available power supplies."
			::= { powerSupplies 3 }

		
		-- 1.3.6.1.4.1.10876.1.6.4
		pwrBladeReserved OBJECT-TYPE
			SYNTAX Integer32
			MAX-ACCESS read-only
			STATUS current
			DESCRIPTION
				"The indication for blade reserved power."
			::= { powerSupplies 4 }

		
		-- 1.3.6.1.4.1.10876.1.6.5
		pwrPeripheralReserved OBJECT-TYPE
			SYNTAX Integer32
			MAX-ACCESS read-only
			STATUS current
			DESCRIPTION
				"The indication for peripheral reserved power."
			::= { powerSupplies 5 }

		
		-- 1.3.6.1.4.1.10876.1.6.6
		pwrAvailablePower OBJECT-TYPE
			SYNTAX Integer32
			MAX-ACCESS read-only
			STATUS current
			DESCRIPTION
				"The indication for available power."
			::= { powerSupplies 6 }

		
		-- 1.3.6.1.4.1.10876.1.6.7
		pwrCurrentMaxTemp OBJECT-TYPE
			SYNTAX OCTET STRING
			MAX-ACCESS read-only
			STATUS current
			DESCRIPTION
				"The indication for current MAX temperature within all available 
				modules."
			::= { powerSupplies 7 }

		
		-- 1.3.6.1.4.1.10876.1.6.8
		pwrCurrentMaxTempModule OBJECT-TYPE
			SYNTAX OCTET STRING
			MAX-ACCESS read-only
			STATUS current
			DESCRIPTION
				"The indication for the module with current MAX temperature."
			::= { powerSupplies 8 }

		
		-- 1.3.6.1.4.1.10876.1.6.9
		pwrGrpPSURedundancy OBJECT-GROUP
			OBJECTS { pwrRedundancy }
			STATUS current
			DESCRIPTION 
				"The group for power supply redundancy."
			::= { powerSupplies 9 }

		
		-- 1.3.6.1.4.1.10876.1.6.10
		pwrRedundancy OBJECT-TYPE
			SYNTAX INTEGER
				{
				pwrRedundancyDisabled(0),
				pwrRedundancyEnabled(1)
				}
			MAX-ACCESS read-write
			STATUS current
			DESCRIPTION
				"The indication for power redundancy policy. Enabled - 
				PSU Redundancy (7+1)."
			::= { powerSupplies 10 }

		
		-- 1.3.6.1.4.1.10876.1.6.11
		pwrGrpPSUFanCtrl OBJECT-GROUP
			OBJECTS { pwrPSUFanCtrl, pwrPSUFanSpdCtrl }
			STATUS current
			DESCRIPTION 
				"The group for power supply FAN control."
			::= { powerSupplies 11 }

		
		-- 1.3.6.1.4.1.10876.1.6.12
		pwrPSUFanCtrl OBJECT-TYPE
			SYNTAX INTEGER
				{
				userCtrl(0),
				autoCtrl(1)
				}
			MAX-ACCESS read-write
			STATUS current
			DESCRIPTION
				"The indication for power supply FAN control policy."
			::= { powerSupplies 12 }

		
		-- 1.3.6.1.4.1.10876.1.6.13
		pwrPSUFanSpdCtrl OBJECT-TYPE
			SYNTAX Integer32 (1..4)
			MAX-ACCESS read-write
			STATUS current
			DESCRIPTION
				"The indication for power supply FAN speed control when pwrPSUFanCtrl is 
				in userCtrl mode."
			::= { powerSupplies 13 }

		
--   CMM Management section
		-- 1.3.6.1.4.1.10876.1.7
		cmms OBJECT IDENTIFIER ::= { cmm 7 }

		
		-- 1.3.6.1.4.1.10876.1.7.1
		cmmTable OBJECT-TYPE
			SYNTAX SEQUENCE OF CmmEntry
			MAX-ACCESS not-accessible
			STATUS current
			DESCRIPTION
				"The table for CMM management."
			::= { cmms 1 }

		
		-- 1.3.6.1.4.1.10876.1.7.1.1
		cmmEntry OBJECT-TYPE
			SYNTAX CmmEntry
			MAX-ACCESS not-accessible
			STATUS current
			DESCRIPTION
				"The table entry for CMM management."
			INDEX { cmmIndex }
			::= { cmmTable 1 }

		
		CmmEntry ::=
			SEQUENCE { 
				cmmIndex
					Integer32,
				cmmSlot
					Integer32,
				cmmPresence
					INTEGER,
				cmmName
					OCTET STRING,
				cmmRole
					INTEGER,
				cmmIPAddr
					IpAddress,
				cmmStatus
					INTEGER,
				cmmFWVersion
					OCTET STRING,
				cmmFWTag
					OCTET STRING
			 }

		-- 1.3.6.1.4.1.10876.1.7.1.1.1
		cmmIndex OBJECT-TYPE
			SYNTAX Integer32 (1..65535)
			MAX-ACCESS not-accessible
			STATUS current
			DESCRIPTION
				"The index for CMM table."
			::= { cmmEntry 1 }

		
		-- 1.3.6.1.4.1.10876.1.7.1.1.2
		cmmSlot OBJECT-TYPE
			SYNTAX Integer32
			MAX-ACCESS read-only
			STATUS current
			DESCRIPTION
				"The indication for CMM slot index."
			::= { cmmEntry 2 }

		
		-- 1.3.6.1.4.1.10876.1.7.1.1.3
		cmmPresence OBJECT-TYPE
			SYNTAX INTEGER
				{
				notPresent(0),
				present(1)
				}
			MAX-ACCESS read-only
			STATUS current
			DESCRIPTION
				"The indication for CMM presence."
			::= { cmmEntry 3 }

		
		-- 1.3.6.1.4.1.10876.1.7.1.1.4
		cmmName OBJECT-TYPE
			SYNTAX OCTET STRING
			MAX-ACCESS read-write
			STATUS current
			DESCRIPTION
				"The indication for CMM name (user defined)."
			::= { cmmEntry 4 }

		
		-- 1.3.6.1.4.1.10876.1.7.1.1.5
		cmmRole OBJECT-TYPE
			SYNTAX INTEGER
				{
				master(0),
				slave(1)
				}
			MAX-ACCESS read-only
			STATUS current
			DESCRIPTION
				"The indication for CMM role (master/slave)."
			::= { cmmEntry 5 }

		
		-- 1.3.6.1.4.1.10876.1.7.1.1.6
		cmmIPAddr OBJECT-TYPE
			SYNTAX IpAddress
			MAX-ACCESS read-only
			STATUS current
			DESCRIPTION
				"The indication for CMM IP address."
			::= { cmmEntry 6 }

		
		-- 1.3.6.1.4.1.10876.1.7.1.1.7
		cmmStatus OBJECT-TYPE
			SYNTAX INTEGER
				{
				notAvailable(0),
				available(1)
				}
			MAX-ACCESS read-only
			STATUS current
			DESCRIPTION
				"The indication for CMM available status."
			::= { cmmEntry 7 }

		
		-- 1.3.6.1.4.1.10876.1.7.1.1.8
		cmmFWVersion OBJECT-TYPE
			SYNTAX OCTET STRING
			MAX-ACCESS read-only
			STATUS current
			DESCRIPTION
				"The indication for CMM firmware version."
			::= { cmmEntry 8 }

		
		-- 1.3.6.1.4.1.10876.1.7.1.1.9
		cmmFWTag OBJECT-TYPE
			SYNTAX OCTET STRING
			MAX-ACCESS read-only
			STATUS current
			DESCRIPTION
				"The indication for CMM firmware tag."
			::= { cmmEntry 9 }

		
		-- 1.3.6.1.4.1.10876.1.7.2
		cmmOperationMode OBJECT-TYPE
			SYNTAX INTEGER
				{
				enterprise(0),
				office(1)
				}
			MAX-ACCESS read-write
			STATUS current
			DESCRIPTION
				"The indication for CMM operation mode (enterprise/office)."
			::= { cmms 2 }

		
		-- 1.3.6.1.4.1.10876.1.7.3
		cmmDateTime OBJECT-TYPE
			SYNTAX OCTET STRING
			MAX-ACCESS read-write
			STATUS current
			DESCRIPTION
				"The indication for CMM date and time. The format must be 
				MM/dd/yyyy HH:mm:ss."
			::= { cmms 3 }

		
		-- 1.3.6.1.4.1.10876.1.7.4
		cmmNTPStatus OBJECT-TYPE
			SYNTAX INTEGER
				{
				userDefined(0),
				ntpSync(1)
				}
			MAX-ACCESS read-write
			STATUS current
			DESCRIPTION
				"The indication for CMM date and time synchronization mode (user specified
				/NTP server auto sync)."
			::= { cmms 4 }

		
		-- 1.3.6.1.4.1.10876.1.7.5
		cmmNTPServer1 OBJECT-TYPE
			SYNTAX IpAddress
			MAX-ACCESS read-write
			STATUS current
			DESCRIPTION
				"The indication for the primary NTP server for CMM."
			::= { cmms 5 }

		
		-- 1.3.6.1.4.1.10876.1.7.6
		cmmNTPServer2 OBJECT-TYPE
			SYNTAX IpAddress
			MAX-ACCESS read-write
			STATUS current
			DESCRIPTION
				"The indication for the secondary NTP server for CMM."
			::= { cmms 6 }

		
		-- 1.3.6.1.4.1.10876.1.7.7
		cmmUTCOffset OBJECT-TYPE
			SYNTAX Integer32 (-11..12)
			MAX-ACCESS read-write
			STATUS current
			DESCRIPTION
				"The indication for CMM UTC offset."
			::= { cmms 7 }

		
--   FRU section
		-- 1.3.6.1.4.1.10876.1.8
		fru OBJECT IDENTIFIER ::= { cmm 8 }

		
		-- 1.3.6.1.4.1.10876.1.8.1
		fruTable OBJECT-TYPE
			SYNTAX SEQUENCE OF FruEntry
			MAX-ACCESS not-accessible
			STATUS obsolete
			DESCRIPTION
				"The table for FRU of all devices managed by CMM."
			::= { fru 1 }

		
		-- 1.3.6.1.4.1.10876.1.8.1.1
		fruEntry OBJECT-TYPE
			SYNTAX FruEntry
			MAX-ACCESS not-accessible
			STATUS obsolete
			DESCRIPTION
				"The table entry for FRU of all devices managed by CMM."
			INDEX { fruTableIndex }
			::= { fruTable 1 }

		
		FruEntry ::=
			SEQUENCE { 
				fruTableIndex
					Integer32,
				fruDeviceType
					INTEGER,
				fruDeviceSlot
					Unsigned32,
				fruDevID
					Unsigned32,
				fruChassisType
					INTEGER,
				fruChassisTypeCode
					Unsigned32,
				fruChassisPN
					OCTET STRING,
				fruChassisSN
					OCTET STRING,
				fruBoardLang
					INTEGER,
				fruBoardLangCode
					Unsigned32,
				fruBoardMfgDatetime
					OCTET STRING,
				fruBoardMfgName
					OCTET STRING,
				fruBoardProdName
					OCTET STRING,
				fruBoardSN
					OCTET STRING,
				fruBoardPN
					OCTET STRING,
				fruProdLang
					INTEGER,
				fruProdLangCode
					Unsigned32,
				fruProdMfgName
					OCTET STRING,
				fruProdProdName
					OCTET STRING,
				fruProdPN
					OCTET STRING,
				fruProdVersion
					OCTET STRING,
				fruProdSN
					OCTET STRING,
				fruProdAssetTag
					OCTET STRING
			 }

		-- 1.3.6.1.4.1.10876.1.8.1.1.1
		fruTableIndex OBJECT-TYPE
			SYNTAX Integer32 (1..65535)
			MAX-ACCESS not-accessible
			STATUS obsolete
			DESCRIPTION
				"The index for the table for FRU of all devices managed by CMM."
			::= { fruEntry 1 }

		
		-- 1.3.6.1.4.1.10876.1.8.1.1.2
		fruDeviceType OBJECT-TYPE
			SYNTAX INTEGER
				{
				cmm(0),
				middlePlane(1),
				switch(2),
				powerSupply(3),
				blade(4)
				}
			MAX-ACCESS read-only
			STATUS obsolete
			DESCRIPTION
				"The indication for the FRU device type."
			::= { fruEntry 2 }

		
		-- 1.3.6.1.4.1.10876.1.8.1.1.3
		fruDeviceSlot OBJECT-TYPE
			SYNTAX Unsigned32
			MAX-ACCESS read-only
			STATUS obsolete
			DESCRIPTION
				"The indication for the FRU device slot."
			::= { fruEntry 3 }

		
		-- 1.3.6.1.4.1.10876.1.8.1.1.4
		fruDevID OBJECT-TYPE
			SYNTAX Unsigned32
			MAX-ACCESS read-only
			STATUS obsolete
			DESCRIPTION
				"The indication for the FRU block device ID."
			::= { fruEntry 4 }

		
		-- 1.3.6.1.4.1.10876.1.8.1.1.5
		fruChassisType OBJECT-TYPE
			SYNTAX INTEGER
				{
				reserved(0),
				other(1),
				unknown(2),
				desktop(3),
				lowProfileDesktop(4),
				pizzaBox(5),
				miniTower(6),
				tower(7),
				portable(8),
				laptop(9),
				notebook(10),
				handHeld(11),
				dockingStation(12),
				allInOne(13),
				subNotebook(14),
				spaceSaving(15),
				lunchBox(16),
				mainServerChassis(17),
				expansionChassis(18),
				subChassis(19),
				busExpansionChassis(20),
				peripheralChassis(21),
				raidChassis(22),
				rackMountChassis(23)
				}
			MAX-ACCESS read-only
			STATUS obsolete
			DESCRIPTION
				"The indication for the chassis type defined in FRU specification."
			::= { fruEntry 5 }

		
		-- 1.3.6.1.4.1.10876.1.8.1.1.6
		fruChassisTypeCode OBJECT-TYPE
			SYNTAX Unsigned32
			MAX-ACCESS read-only
			STATUS obsolete
			DESCRIPTION
				"The indication for the chassis type code."
			::= { fruEntry 6 }

		
		-- 1.3.6.1.4.1.10876.1.8.1.1.7
		fruChassisPN OBJECT-TYPE
			SYNTAX OCTET STRING
			MAX-ACCESS read-only
			STATUS obsolete
			DESCRIPTION
				"The indication for the chassis part number."
			::= { fruEntry 7 }

		
		-- 1.3.6.1.4.1.10876.1.8.1.1.8
		fruChassisSN OBJECT-TYPE
			SYNTAX OCTET STRING
			MAX-ACCESS read-only
			STATUS obsolete
			DESCRIPTION
				"The indication for the chassis serial number."
			::= { fruEntry 8 }

		
		-- 1.3.6.1.4.1.10876.1.8.1.1.9
		fruBoardLang OBJECT-TYPE
			SYNTAX INTEGER { english(0) }
			MAX-ACCESS read-only
			STATUS obsolete
			DESCRIPTION
				"The indication for the board language."
			::= { fruEntry 9 }

		
		-- 1.3.6.1.4.1.10876.1.8.1.1.10
		fruBoardLangCode OBJECT-TYPE
			SYNTAX Unsigned32
			MAX-ACCESS read-only
			STATUS obsolete
			DESCRIPTION
				"The indication for the board language code."
			::= { fruEntry 10 }

		
		-- 1.3.6.1.4.1.10876.1.8.1.1.11
		fruBoardMfgDatetime OBJECT-TYPE
			SYNTAX OCTET STRING
			MAX-ACCESS read-only
			STATUS obsolete
			DESCRIPTION
				"The indication for the board manufactory datetime."
			::= { fruEntry 11 }

		
		-- 1.3.6.1.4.1.10876.1.8.1.1.12
		fruBoardMfgName OBJECT-TYPE
			SYNTAX OCTET STRING
			MAX-ACCESS read-only
			STATUS obsolete
			DESCRIPTION
				"The indication for the board manufactory name."
			::= { fruEntry 12 }

		
		-- 1.3.6.1.4.1.10876.1.8.1.1.13
		fruBoardProdName OBJECT-TYPE
			SYNTAX OCTET STRING
			MAX-ACCESS read-only
			STATUS obsolete
			DESCRIPTION
				"The indication for the baord product name."
			::= { fruEntry 13 }

		
		-- 1.3.6.1.4.1.10876.1.8.1.1.14
		fruBoardSN OBJECT-TYPE
			SYNTAX OCTET STRING
			MAX-ACCESS read-only
			STATUS obsolete
			DESCRIPTION
				"The indication for the board serial number."
			::= { fruEntry 14 }

		
		-- 1.3.6.1.4.1.10876.1.8.1.1.15
		fruBoardPN OBJECT-TYPE
			SYNTAX OCTET STRING
			MAX-ACCESS read-only
			STATUS obsolete
			DESCRIPTION
				"The indication for the board part number."
			::= { fruEntry 15 }

		
		-- 1.3.6.1.4.1.10876.1.8.1.1.16
		fruProdLang OBJECT-TYPE
			SYNTAX INTEGER { english(0) }
			MAX-ACCESS read-only
			STATUS obsolete
			DESCRIPTION
				"The indication for the product language."
			::= { fruEntry 16 }

		
		-- 1.3.6.1.4.1.10876.1.8.1.1.17
		fruProdLangCode OBJECT-TYPE
			SYNTAX Unsigned32
			MAX-ACCESS read-only
			STATUS obsolete
			DESCRIPTION
				"The indication for the product language code."
			::= { fruEntry 17 }

		
		-- 1.3.6.1.4.1.10876.1.8.1.1.18
		fruProdMfgName OBJECT-TYPE
			SYNTAX OCTET STRING
			MAX-ACCESS read-only
			STATUS obsolete
			DESCRIPTION
				"The indication for the product manufactory name."
			::= { fruEntry 18 }

		
		-- 1.3.6.1.4.1.10876.1.8.1.1.19
		fruProdProdName OBJECT-TYPE
			SYNTAX OCTET STRING
			MAX-ACCESS read-only
			STATUS obsolete
			DESCRIPTION
				"The indication for the product name."
			::= { fruEntry 19 }

		
		-- 1.3.6.1.4.1.10876.1.8.1.1.20
		fruProdPN OBJECT-TYPE
			SYNTAX OCTET STRING
			MAX-ACCESS read-only
			STATUS obsolete
			DESCRIPTION
				"The indication for the product part/model number."
			::= { fruEntry 20 }

		
		-- 1.3.6.1.4.1.10876.1.8.1.1.21
		fruProdVersion OBJECT-TYPE
			SYNTAX OCTET STRING
			MAX-ACCESS read-only
			STATUS obsolete
			DESCRIPTION
				"The indication for the product version."
			::= { fruEntry 21 }

		
		-- 1.3.6.1.4.1.10876.1.8.1.1.22
		fruProdSN OBJECT-TYPE
			SYNTAX OCTET STRING
			MAX-ACCESS read-only
			STATUS obsolete
			DESCRIPTION
				"The indication for the product serial number."
			::= { fruEntry 22 }

		
		-- 1.3.6.1.4.1.10876.1.8.1.1.23
		fruProdAssetTag OBJECT-TYPE
			SYNTAX OCTET STRING
			MAX-ACCESS read-only
			STATUS obsolete
			DESCRIPTION
				"The indication for the product asset tag."
			::= { fruEntry 23 }

		
--   Virtual Media section
		-- 1.3.6.1.4.1.10876.1.9
		virtualMedias OBJECT IDENTIFIER ::= { cmm 9 }

		
		-- 1.3.6.1.4.1.10876.1.9.1
		floppyActiveImage1 OBJECT-TYPE
			SYNTAX OCTET STRING
			MAX-ACCESS read-only
			STATUS obsolete
			DESCRIPTION
				"Floppy Drive 1 active image information."
			::= { virtualMedias 1 }

		
		-- 1.3.6.1.4.1.10876.1.9.2
		floppyActiveImage2 OBJECT-TYPE
			SYNTAX OCTET STRING
			MAX-ACCESS read-only
			STATUS obsolete
			DESCRIPTION
				"Floppy Drive 2 active image information."
			::= { virtualMedias 2 }

		
		-- 1.3.6.1.4.1.10876.1.9.3
		cdromActiveImage1 OBJECT-TYPE
			SYNTAX OCTET STRING
			MAX-ACCESS read-only
			STATUS obsolete
			DESCRIPTION
				"CDROM Drive 1 active image information."
			::= { virtualMedias 3 }

		
		-- 1.3.6.1.4.1.10876.1.9.4
		cdromActiveImage2 OBJECT-TYPE
			SYNTAX OCTET STRING
			MAX-ACCESS read-only
			STATUS obsolete
			DESCRIPTION
				"CDROM Drive 2 active image information."
			::= { virtualMedias 4 }

		
		-- 1.3.6.1.4.1.10876.1.9.5
		drvRedirActiveImage1 OBJECT-TYPE
			SYNTAX OCTET STRING
			MAX-ACCESS read-only
			STATUS obsolete
			DESCRIPTION
				"Drive Redirection Drive 1 active image information."
			::= { virtualMedias 5 }

		
		-- 1.3.6.1.4.1.10876.1.9.6
		drvRedirActiveImage2 OBJECT-TYPE
			SYNTAX OCTET STRING
			MAX-ACCESS read-only
			STATUS obsolete
			DESCRIPTION
				"Drive Redirection Drive 2 active image information."
			::= { virtualMedias 6 }

		
		-- 1.3.6.1.4.1.10876.1.9.7
		drvRedirStatus OBJECT-TYPE
			SYNTAX INTEGER
				{
				disabled(0),
				enabled(1)
				}
			MAX-ACCESS read-write
			STATUS current
			DESCRIPTION
				"Drive Redirection enable/disable status."
			::= { virtualMedias 7 }

		
		-- 1.3.6.1.4.1.10876.1.9.8
		drvRedirAccessType OBJECT-TYPE
			SYNTAX INTEGER
				{
				readonly(0),
				readwrite(1)
				}
			MAX-ACCESS read-write
			STATUS current
			DESCRIPTION
				"Drive Redirection connections access options (readonly/readwrite)."
			::= { virtualMedias 8 }

		
		-- 1.3.6.1.4.1.10876.1.9.9
		usbEnableWithoutImage OBJECT-TYPE
			SYNTAX INTEGER
				{
				disabled(0),
				enabled(1)
				}
			MAX-ACCESS read-write
			STATUS current
			DESCRIPTION
				"Options to enable/disable USB Mass Storage if no image is loaded."
			::= { virtualMedias 9 }

		
--   KVM Setting section
		-- 1.3.6.1.4.1.10876.1.10
		kvmSettings OBJECT IDENTIFIER ::= { cmm 10 }

		
		-- 1.3.6.1.4.1.10876.1.10.1
		keyboardModel OBJECT-TYPE
			SYNTAX INTEGER
				{
				generic104KeyPC(0),
				generic109KeyPC(1),
				appleMacintosh(2)
				}
			MAX-ACCESS read-write
			STATUS current
			DESCRIPTION
				"Keyboard Model options."
			::= { kvmSettings 1 }

		
		-- 1.3.6.1.4.1.10876.1.10.2
		keyReleaseTimeoutStatus OBJECT-TYPE
			SYNTAX INTEGER
				{
				disabled(0),
				enabled(1)
				}
			MAX-ACCESS read-write
			STATUS current
			DESCRIPTION
				"Key release timeout enable/disable."
			::= { kvmSettings 2 }

		
		-- 1.3.6.1.4.1.10876.1.10.3
		keyReleaseTimeoutInterval OBJECT-TYPE
			SYNTAX INTEGER
				{
				time25(0),
				time50(1),
				time100(2),
				time200(3)
				}
			UNITS "msec"
			MAX-ACCESS read-write
			STATUS current
			DESCRIPTION
				"Key release timeout interval.
				Available options are 25, 50, 100, 200 msec."
			::= { kvmSettings 3 }

		
		-- 1.3.6.1.4.1.10876.1.10.4
		mouseType OBJECT-TYPE
			SYNTAX INTEGER
				{
				relative(0),
				absolute(1)
				}
			MAX-ACCESS read-write
			STATUS current
			DESCRIPTION
				"USB mouse type options.
				Option absolute for Windows (2000 or above) and Mac OS X.
				Option relative for the other OS."
			::= { kvmSettings 4 }

		
		-- 1.3.6.1.4.1.10876.1.10.5
		mouseSpeed OBJECT-TYPE
			SYNTAX INTEGER
				{
				auto(0),
				scale1v025(1),
				scale1v050(2),
				scale1v100(3),
				scale1v200(4),
				scale1v400(5)
				}
			MAX-ACCESS read-write
			STATUS current
			DESCRIPTION
				"Mouse speed, only available when mouseType is set to otherOS.
				Available options are Auto, or Fixed Scaling (1:0.25, 1:0.50, 1:1.00, 1:2.
				00, 1:4.00)."
			::= { kvmSettings 5 }

		
--   Event Log section
		-- 1.3.6.1.4.1.10876.1.11
		eventLogging OBJECT IDENTIFIER ::= { cmm 11 }

		
		-- 1.3.6.1.4.1.10876.1.11.1
		evtGrpLogTargetSettings OBJECT-GROUP
			OBJECTS { evtListLogStatus, evtListEntryPerPage, evtListClearLog, 
evtNFSLogStatus, evtNFSServer, 

				evtNFSShare, evtNFSLogFile, evtSMTPLogStatus, evtSMTPServer, 
evtSMTPRecvEmail, 

				evtSMTPSendEmail, evtSNMPLogStatus, evtSNMPDestIP, evtSNMPCommunity }
			STATUS current
			DESCRIPTION 
				"The group for event log target settings."
			::= { eventLogging 1 }

		
		-- 1.3.6.1.4.1.10876.1.11.2
		evtListLogStatus OBJECT-TYPE
			SYNTAX INTEGER
				{
				disabled(0),
				enabled(1)
				}
			MAX-ACCESS read-write
			STATUS current
			DESCRIPTION
				"Show the event log list enable/diable status."
			::= { eventLogging 2 }

		
		-- 1.3.6.1.4.1.10876.1.11.3
		evtListEntryPerPage OBJECT-TYPE
			SYNTAX Integer32
			MAX-ACCESS read-write
			STATUS current
			DESCRIPTION
				"Entries number per page. Default is 20."
			::= { eventLogging 3 }

		
		-- 1.3.6.1.4.1.10876.1.11.4
		evtListClearLog OBJECT-TYPE
			SYNTAX INTEGER { clear(0) }
			MAX-ACCESS read-write
			STATUS current
			DESCRIPTION
				"A write only action for clear CMM internal log."
			::= { eventLogging 4 }

		
		-- 1.3.6.1.4.1.10876.1.11.5
		evtNFSLogStatus OBJECT-TYPE
			SYNTAX INTEGER
				{
				disabled(0),
				enabled(1)
				}
			MAX-ACCESS read-write
			STATUS current
			DESCRIPTION
				"Event log for NFS logging enable/diable status."
			::= { eventLogging 5 }

		
		-- 1.3.6.1.4.1.10876.1.11.6
		evtNFSServer OBJECT-TYPE
			SYNTAX OCTET STRING
			MAX-ACCESS read-write
			STATUS current
			DESCRIPTION
				"The NFS server for logging."
			::= { eventLogging 6 }

		
		-- 1.3.6.1.4.1.10876.1.11.7
		evtNFSShare OBJECT-TYPE
			SYNTAX OCTET STRING
			MAX-ACCESS read-write
			STATUS current
			DESCRIPTION
				"The NFS share for logging."
			::= { eventLogging 7 }

		
		-- 1.3.6.1.4.1.10876.1.11.8
		evtNFSLogFile OBJECT-TYPE
			SYNTAX OCTET STRING
			MAX-ACCESS read-write
			STATUS current
			DESCRIPTION
				"The NFS log file for logging."
			::= { eventLogging 8 }

		
		-- 1.3.6.1.4.1.10876.1.11.9
		evtSMTPLogStatus OBJECT-TYPE
			SYNTAX INTEGER
				{
				disabled(0),
				enabled(1)
				}
			MAX-ACCESS read-write
			STATUS current
			DESCRIPTION
				"Event log for SMTP logging enable/diable status."
			::= { eventLogging 9 }

		
		-- 1.3.6.1.4.1.10876.1.11.10
		evtSMTPServer OBJECT-TYPE
			SYNTAX OCTET STRING
			MAX-ACCESS read-write
			STATUS current
			DESCRIPTION
				"The SMTP server for logging."
			::= { eventLogging 10 }

		
		-- 1.3.6.1.4.1.10876.1.11.11
		evtSMTPRecvEmail OBJECT-TYPE
			SYNTAX OCTET STRING
			MAX-ACCESS read-write
			STATUS current
			DESCRIPTION
				"The receiver email address for SMTP logging."
			::= { eventLogging 11 }

		
		-- 1.3.6.1.4.1.10876.1.11.12
		evtSMTPSendEmail OBJECT-TYPE
			SYNTAX OCTET STRING
			MAX-ACCESS read-write
			STATUS current
			DESCRIPTION
				"The sender email address for SMTP logging."
			::= { eventLogging 12 }

		
		-- 1.3.6.1.4.1.10876.1.11.13
		evtSNMPLogStatus OBJECT-TYPE
			SYNTAX INTEGER
				{
				disabled(0),
				enabled(1)
				}
			MAX-ACCESS read-write
			STATUS current
			DESCRIPTION
				"Event log for SNMP logging enable/diable status."
			::= { eventLogging 13 }

		
		-- 1.3.6.1.4.1.10876.1.11.14
		evtSNMPDestIP OBJECT-TYPE
			SYNTAX OCTET STRING
			MAX-ACCESS read-write
			STATUS current
			DESCRIPTION
				"The destination IP address for SNMP logging."
			::= { eventLogging 14 }

		
		-- 1.3.6.1.4.1.10876.1.11.15
		evtSNMPCommunity OBJECT-TYPE
			SYNTAX OCTET STRING
			MAX-ACCESS read-write
			STATUS current
			DESCRIPTION
				"The community name for SNMP logging."
			::= { eventLogging 15 }

		
	
	END

--
-- SMC-MIB.txt
--
