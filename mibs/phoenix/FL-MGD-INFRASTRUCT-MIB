--
-- The Phoenix Contact private SNMP MIB Module for Managed Infrastructure Devices
-- Revision: 2.3  
--

FL-MGD-INFRASTRUCT-MIB DEFINITIONS ::= BEGIN               
    
    IMPORTS
        
        MODULE-IDENTITY,
        OBJECT-TYPE,
        NOTIFICATION-TYPE,
        Integer32,
        Gauge32,
        IpAddress,
        enterprises,
        TimeTicks,
        Unsigned32
            FROM SNMPv2-SMI

        DisplayString,
        MacAddress,
        RowStatus,
        DateAndTime,
        TruthValue,
        TEXTUAL-CONVENTION
            FROM SNMPv2-TC
        
        PortList, 
        dot1qStaticMulticastEntry,
        dot1qVlanIndex
             FROM Q-BRIDGE-MIB  
  
        ifIndex,
        InterfaceIndex, 
        InterfaceIndexOrZero       
        	FROM IF-MIB

        rip2IfConfEntry
            FROM RIPv2-MIB

        ospfIfEntry, ospfVirtIfEntry,
        ospfAreaEntry, RouterID
            FROM OSPF-MIB

        vrrpOperVrId
                FROM VRRP-MIB;   
                
    
    phoenixContact
        OBJECT IDENTIFIER ::= { enterprises 4346 }

    pxcModules
        OBJECT IDENTIFIER ::= { phoenixContact 1 }
            

    flMgdInfrastructureMibModule MODULE-IDENTITY
        LAST-UPDATED    "202012091400Z" -- December 9th, 2020"
        ORGANIZATION    "Phoenix Contact GmbH & Co. KG"
        CONTACT-INFO
            " Contact:   Factory Line Service
              Postal:   Phoenix Contact GmbH & Co. KG
                        D-32823 Blomberg
                 Tel:   +49 (0)5235 341888
                 WEB:   http://www.PhoenixContact.com/
               eMail:   FactoryLine-Service@PhoenixContact.com"
        
        DESCRIPTION
            "Phoenix Contact private SNMP objects of the FL Managed Infrastructure Product Group."
			
		REVISION        "201901210800Z"
        DESCRIPTION 
            "Added Diag folder for crc surveillance, snapshot and syslog. Added CRC surveillance folder with crc monitoring table to diag folder."

        REVISION        "201803220800Z"
        DESCRIPTION 
            "Changes to previous revision 1.5: 
            - added objects to configure profinet boundary settings
            - added objects for sntp server description"
            
        REVISION        "201703240800Z"
        DESCRIPTION 
            "Add objects for mode LEDs off, DHCP port server service, and user-interface configuration.
             Changed the description of flWorkFWCtrlSecurityPortMode, flWorkFWCtrlConfStatus,
             flWorkFWCtrlPortPriorityLevel and flWorkFWCtrlSecurityPortLastMacAddr."

        REVISION        "201607120800Z"
        DESCRIPTION 
            "Add objects for DHCPServer, SFP RX and TX Power, and routing IP interface management.
             Fix some problems with object descriptions."

        REVISION        "201503190800Z"
        DESCRIPTION 
            "Fix all issues found by ASN1 parser."

    ::= { pxcModules 8}
   
-- type definitions
    EnabledDisabledStatus ::= TEXTUAL-CONVENTION
        STATUS current
        DESCRIPTION
                "This textual convention is used to some variables on the
                device that only permit two states.

                enableStatus  : The status of the variable is enabled or true.
                disableStatus : The status of the variable is disabled or false"

        SYNTAX INTEGER {
                disableStatus(0),
                enableStatus(1)
        }

   OpModeType ::= TEXTUAL-CONVENTION
        STATUS current
        DESCRIPTION
                "This textual convention is used to distinguish the WIFI operation mode of a device.
                 station: 0
                 access point (master): 1
                 single client bridge (scb): 2
                 multi client bridge (mcb): 3
                 fully transparent bridge (ftb): 4
                 repeater : 5
                 machine admin : 6"

        SYNTAX INTEGER {
                station(0),
                master(1),
                scb(2),
                mcb(3),
                ftb(4),
                repeater(5),
                machine-admin(6)
        }

    EtypeValue ::= TEXTUAL-CONVENTION
            DISPLAY-HINT "x"
            STATUS   current
            DESCRIPTION
               "Ethertype value of a packet.  The allowed value is 0x0600 to 0xFFFF."
            SYNTAX   Unsigned32 (1536..65535)   -- hex value 0x0600 to 0xFFFF




--
--
-- The Phoenix Contact private SNMP MIB objects level 1 (vendor):
--
--

    

    pxcGlobal
        OBJECT IDENTIFIER ::= { phoenixContact 2 }
 
    pxcFactoryLine
        OBJECT IDENTIFIER ::= { phoenixContact 11 }



    pxcBasic
        OBJECT IDENTIFIER ::= { pxcGlobal 1 }


    pxcBasicName
        OBJECT-TYPE
            SYNTAX      DisplayString
            MAX-ACCESS  read-only
            STATUS      current
            DESCRIPTION
                "The device will always return the
                 company name:
                 
                            Phoenix Contact GmbH & Co. KG"
        ::= { pxcBasic 1 }

    pxcBasicDescr
        OBJECT-TYPE
            SYNTAX      DisplayString
            MAX-ACCESS  read-only
            STATUS      current
            DESCRIPTION
                "The device will always return the
                 company description:
                 
                            Phoenix Contact GmbH & Co. KG, D-32823 Blomberg"
        ::= { pxcBasic 2 }

    pxcBasicURL
        OBJECT-TYPE
            SYNTAX      DisplayString
            MAX-ACCESS  read-only
            STATUS      current
            DESCRIPTION
                "The device will always return the URL of
                 company web page of Phoenix Contact:
                 
                            http://www.phoenixcontact.com/"
        ::= { pxcBasic 3 }





--
--
-- The Phoenix Contact private SNMP MIB objects level 2 (product line):
--
--

    flGlobal
        OBJECT IDENTIFIER ::= { pxcFactoryLine 1 }

    flWorkDevice         
        OBJECT IDENTIFIER ::= { pxcFactoryLine 11 }
 

    flBasic
        OBJECT IDENTIFIER ::= { flGlobal 1 }

    flComponents         
        OBJECT IDENTIFIER ::= { flGlobal 2 }



    --
    --
    -- flBasic Group
    --
    flBasicName
        OBJECT-TYPE
            SYNTAX      DisplayString
            MAX-ACCESS  read-only
            STATUS      current
            DESCRIPTION
                "The device will always return the
                 product group name:
                 
                            Factory Line"
        ::= { flBasic 1 }

    flBasicDescr
        OBJECT-TYPE
            SYNTAX      DisplayString
            MAX-ACCESS  read-only
            STATUS      current
            DESCRIPTION
                "The device will always return the
                 product group description:
                 
                            Ethernet Installation System"
        ::= { flBasic 2 }

    flBasicURL
        OBJECT-TYPE
            SYNTAX      DisplayString
            MAX-ACCESS  read-only
            STATUS      current
            DESCRIPTION
                "The device will always return the URL of product group
                 web page within the web space of Phoenix Contact:
                 
                            http://www.factoryline.de/"
        ::= { flBasic 3 }

    flBasicCompCapacity
        OBJECT-TYPE
            SYNTAX      Integer32 (1..1024)
            MAX-ACCESS  read-only
            STATUS      current
            DESCRIPTION
                "This objects indicates the number of available
                 components of the product group Factory Line, which
                 can be used together with this administrable component."
        ::= { flBasic 4 }



    --
    --
    -- flComponents Group
    --
    flComponentsTable
        OBJECT-TYPE
            SYNTAX      SEQUENCE OF FlComponentsEntry
            MAX-ACCESS  not-accessible
            STATUS      current
            DESCRIPTION
                "Table of descriptive information about the available
                 components of the product group Factory Line, which
                 can be used together with this administrable component."
        ::= { flComponents 1 }

    flComponentsEntry
        OBJECT-TYPE
            SYNTAX      FlComponentsEntry
            MAX-ACCESS  not-accessible
            STATUS      current
            DESCRIPTION
                "An entry in the table, containing information about a
                 single component (product) from Factory Line."
            INDEX       { flComponentsIndex }
        ::= { flComponentsTable 1 }

    FlComponentsEntry
        ::= SEQUENCE {
            flComponentsIndex
                Integer32,
            flComponentsName
                DisplayString,
            flComponentsDescr
                DisplayString,
            flComponentsURL
                DisplayString,
            flComponentsOrderNumber
                DisplayString
        }

    flComponentsIndex
        OBJECT-TYPE
            SYNTAX      Integer32 (1..1024)
            MAX-ACCESS  read-only
            STATUS      current
            DESCRIPTION
                "This object identifies the component within the
                 product group Factory Line for which this entry
                 contains information."
        ::= { flComponentsEntry 1 }

    flComponentsName
        OBJECT-TYPE
            SYNTAX      DisplayString
            MAX-ACCESS  read-only
            STATUS      current
            DESCRIPTION
                "This object contains the component name."
        ::= { flComponentsEntry 2 }

    flComponentsDescr
        OBJECT-TYPE
            SYNTAX      DisplayString
            MAX-ACCESS  read-only
            STATUS      current
            DESCRIPTION
                "This object contains the component description."
        ::= { flComponentsEntry 3 }

    flComponentsURL
        OBJECT-TYPE
            SYNTAX      DisplayString
            MAX-ACCESS  read-only
            STATUS      current
            DESCRIPTION
                "This object contains the URL of component's web page
                 within the web space of Phoenix Contact."
        ::= { flComponentsEntry 4 }

    flComponentsOrderNumber
        OBJECT-TYPE
            SYNTAX      DisplayString
            MAX-ACCESS  read-only
            STATUS      current
            DESCRIPTION
                "This object contains the component order number."
        ::= { flComponentsEntry 5 }



--
--
-- The Phoenix Contact private SNMP MIB objects level 3 (device of the product line):
--
--

    flWorkBasic
        OBJECT IDENTIFIER ::= { flWorkDevice 1 }

    flWorkComponents
        OBJECT IDENTIFIER ::= { flWorkDevice 2 }

    flWorkTraps
        OBJECT IDENTIFIER ::= { flWorkDevice 3 }
        
    flWorkNet
        OBJECT IDENTIFIER ::= { flWorkDevice 4 }

    flWorkTrapsDelemeter
        OBJECT IDENTIFIER ::= { flWorkTraps 0 }

    flWorkFirmware
        OBJECT IDENTIFIER ::= { flWorkDevice 11 }

    flWorkSecGateway
        OBJECT IDENTIFIER ::= { flWorkDevice 20 }
        
    flWorkTimeSynch
        OBJECT IDENTIFIER ::= { flWorkDevice 21 }

    flWorkWlan    
        OBJECT IDENTIFIER ::= { flWorkDevice 22 } 

    flWorkRouting
        OBJECT IDENTIFIER ::= { flWorkDevice 23 }     

    flWorkCip
        OBJECT IDENTIFIER ::= { flWorkDevice 25 }
		
	flWlan
        OBJECT IDENTIFIER ::= { flWorkDevice 27 }

    flWorkNetIfParameter
        OBJECT IDENTIFIER ::= { flWorkNet 1 }
    
    flWorkNetPort
        OBJECT IDENTIFIER ::= { flWorkNet 2 }   
        
    flWorkNetIfList
        OBJECT IDENTIFIER ::= { flWorkNet 3 }
         
    flWorkNetACD
        OBJECT IDENTIFIER ::= { flWorkNet 5 }	
        
    flWorkFWInfo
        OBJECT IDENTIFIER ::= { flWorkFirmware 1 }

    flWorkFWInfoEvent 
        OBJECT IDENTIFIER ::= { flWorkFWInfo 14 }
    
    flWorkFWCtrl
        OBJECT IDENTIFIER ::= { flWorkFirmware 2 }


    flWorkFWCtrlBasic
        OBJECT IDENTIFIER ::= { flWorkFWCtrl 1 }

    flWorkFWCtrlTrapDest
        OBJECT IDENTIFIER ::= { flWorkFWCtrl 2 }

    flWorkFWCtrlPasswd
        OBJECT IDENTIFIER ::= { flWorkFWCtrl 3 }

    flWorkFWCtrlUpdate
        OBJECT IDENTIFIER ::= { flWorkFWCtrl 4 }

    flWorkFWCtrlConf
        OBJECT IDENTIFIER ::= { flWorkFWCtrl 5 }

    flWorkFWCtrlSerial
        OBJECT IDENTIFIER ::= { flWorkFWCtrl 6 }
    
    flWorkFWCtrlAlarmContact
        OBJECT IDENTIFIER ::= { flWorkFWCtrl 7 }
        
    flWorkFWCtrlSecurity
        OBJECT IDENTIFIER ::= { flWorkFWCtrl 8 }

    flWorkFWCtrlProfinet
        OBJECT IDENTIFIER ::= { flWorkFWCtrl 9 }        
        
    flWorkTimeSynchSntp
        OBJECT IDENTIFIER ::= { flWorkTimeSynch 1 }
        
    flWorkTimeSynchRTC
        OBJECT IDENTIFIER ::= { flWorkTimeSynch 2 }

    flWorkRoutingIp
        OBJECT IDENTIFIER ::= { flWorkRouting 1 }

    flWorkRoutingArp
        OBJECT IDENTIFIER ::= { flWorkRouting 2 }

    flWorkRoutingVrrp
        OBJECT IDENTIFIER ::= { flWorkRouting 3 }

    flWorkRoutingRip
        OBJECT IDENTIFIER ::= { flWorkRouting 4 }

    flWorkRoutingOspf
        OBJECT IDENTIFIER ::= { flWorkRouting 5 }

    flWorkRoutingLoopback
        OBJECT IDENTIFIER ::= { flWorkRouting 6 }
              
    flWorkRoutingNAT
        OBJECT IDENTIFIER ::= { flWorkRouting 7 }

    flWorkFWConfig
        OBJECT IDENTIFIER ::= { flWorkFWCtrlConf 10 }
    
    flWorkFWCtrlConfigPluggable
        OBJECT IDENTIFIER ::= { flWorkFWCtrlConf 11 }        

    flWorkFWCtrlConfigMemInfo
        OBJECT IDENTIFIER ::= { flWorkFWCtrlConfigPluggable 5 }

    flWorkFWCtrlMRP
	  OBJECT IDENTIFIER ::= { flWorkFWCtrl 10 }
      
    flWorkFWCtrlTemp
        OBJECT IDENTIFIER ::= { flWorkFWCtrl 11 }

    flWorkFWCtrlTelnetGroup
	    OBJECT IDENTIFIER ::= { flWorkFWCtrl 12 } 
            
    flWorkFWCtrlImage                  
          OBJECT IDENTIFIER ::= { flWorkFWCtrl 13 } 

    flWorkFWCtrlUserConfigGroup                    
            OBJECT IDENTIFIER ::= { flWorkFWCtrl 14 }

     flWorkFWCtrlDigitalInput
	    OBJECT IDENTIFIER ::= { flWorkFWCtrl 15 }
        
    -- flWorkFWCtrlFan
	--     OBJECT IDENTIFIER ::= { flWorkFWCtrl 16 }

    flWorkFWCtrlEnergy
      OBJECT IDENTIFIER ::= { flWorkFWCtrl 17 }

   flWorkFWCtrlDigitalOutput
      OBJECT IDENTIFIER ::= { flWorkFWCtrl 18 }

    flWorkFWCtrlDLR    
	    OBJECT IDENTIFIER ::= { flWorkFWCtrl 19 }  

	flWorkFWCtrlFileTransfer
		OBJECT IDENTIFIER ::= { flWorkFWCtrl 22 }  
          
    flWorkFWCtrlMRPConfig 
        OBJECT IDENTIFIER ::= { flWorkFWCtrlMRP 1 }
   
    flWorkFWCtrlMRPInfo 
        OBJECT IDENTIFIER ::= { flWorkFWCtrlMRP 2 }

    flWorkCipInfo
	OBJECT IDENTIFIER ::= { flWorkCip 1 }   

    flWorkFWCtrlDiag
        OBJECT IDENTIFIER ::= { flWorkFWCtrl 23 }   

    flWorkFWCtrlDiagSurveillance
        OBJECT IDENTIFIER ::= { flWorkFWCtrlDiag 1 }   

    flWorkFWCtrlDiagSnapshot
        OBJECT IDENTIFIER ::= { flWorkFWCtrlDiag 2 }   

    flWorkFWCtrlDiagSyslog
        OBJECT IDENTIFIER ::= { flWorkFWCtrlDiag 3 }
	
	
    --
    --
    -- flWorkBasic Group
    --
    flWorkBasicName
        OBJECT-TYPE
            SYNTAX      DisplayString
            MAX-ACCESS  read-write
            STATUS      current
            DESCRIPTION
                "The device will always return his name.

                 At the delivery time to the customer an default value
                 is already present. After an firmware update it may be
                 possible that the contents of this object will be
                 overwriting.

                 As far as he is concerned the customer can write his
                 own device name later."            
        ::= { flWorkBasic 1 }

    flWorkBasicDescr
        OBJECT-TYPE
            SYNTAX      DisplayString
            MAX-ACCESS  read-write
            STATUS      current
            DESCRIPTION
                "The device will always return his description.

                 At the delivery time to the customer an default value
                 is already present. After an firmware update it may be
                 possible that the contents of this object will be
                 overwriting.

                 As far as he is concerned the customer can write his
                 own description later."
        ::= { flWorkBasic 2 }

    flWorkBasicURL
        OBJECT-TYPE
            SYNTAX      DisplayString
            MAX-ACCESS  read-only
            STATUS      current
            DESCRIPTION
                "The device will always return the web page URL
                 of itself:

                            http://ip_addr/

                 In further kinds it may be that instead of the
                 ip_addr the full qualified domain name will be
                 showing."
        ::= { flWorkBasic 3 }

    flWorkBasicSerialNumber
        OBJECT-TYPE
            SYNTAX      OCTET STRING (SIZE(12))
            MAX-ACCESS  read-only
            STATUS      current
            DESCRIPTION
                "The device will always return the serial
                 number of itself. That are eight or twelve
                 digits presented as string value."
        ::= { flWorkBasic 4 }

   flWorkBasicHWRevision
       OBJECT-TYPE
           SYNTAX      OCTET STRING
           MAX-ACCESS  read-only
           STATUS      current
           DESCRIPTION
               "The device will always return the hardware
                revision code of itself."
       ::= { flWorkBasic 5 }

    flWorkBasicPowerStat
        OBJECT-TYPE
            SYNTAX      INTEGER {
                            unknown(1),
                            sourceOne(3),
                            sourceTwo(4),
                            sourceBoth(5)
                        }
            MAX-ACCESS  read-only
            STATUS      current
            DESCRIPTION
                "This object presents power status of itself."
        ::= { flWorkBasic 6 }

   flWorkBasicSystemBusRevision
       OBJECT-TYPE
           SYNTAX      OCTET STRING
           MAX-ACCESS  read-only
           STATUS      current
           DESCRIPTION
               "The device will always return revision code 
                of the system bus."
       ::= { flWorkBasic 7 }
       
    flWorkBasicCompMaxCapacity
        OBJECT-TYPE
            SYNTAX      Integer32 (1..1024)
            MAX-ACCESS  read-only
            STATUS      current
            DESCRIPTION
                "The device will always return the maximum of
                 interfaces which theoretical may be connected."
        ::= { flWorkBasic 11 }

    flWorkBasicCompCapacity
        OBJECT-TYPE
            SYNTAX      Integer32 (1..1024)
            MAX-ACCESS  read-only
            STATUS      current
            DESCRIPTION
                "The device will alway return the number of
                 really connected interfaces. This value is
                 never greater than flWorkBasicCompMaxCapacity."
        ::= { flWorkBasic 12 }

     flWorkBasicLogicRevision
        OBJECT-TYPE
            SYNTAX      OCTET STRING  (SIZE(12))
            MAX-ACCESS  read-only
            STATUS      current
            DESCRIPTION
                "This will deliver the actual revision of several logic
                 devices inside the system."
        ::= { flWorkBasic 13 }


    flWorkBasicPlatformID
        OBJECT-TYPE
            SYNTAX      OCTET STRING  (SIZE(12))
            MAX-ACCESS  read-only
            STATUS      current
            DESCRIPTION
                "This will return the actual revision of the platform ID."
        ::= { flWorkBasic 14 }


    flWorkBasicFwGeneration
        OBJECT-TYPE
            SYNTAX      OCTET STRING  (SIZE(12))
            MAX-ACCESS  read-only
            STATUS      current
            DESCRIPTION
                "This will return the actual revision of the firmware generation."
        ::= { flWorkBasic 15 }


    flWorkBasicCfGeneration
        OBJECT-TYPE
            SYNTAX      OCTET STRING  (SIZE(12))
            MAX-ACCESS  read-only
            STATUS      current
            DESCRIPTION
                "This will return the actual revision of the configuration generation."
        ::= { flWorkBasic 16 }

	--**********************************************************************
	-- flWorkBasicPortTable
	--**********************************************************************
 
	flWorkBasicPortTable OBJECT-TYPE
		SYNTAX    	SEQUENCE OF FlWorkBasicPortEntry
		MAX-ACCESS 	not-accessible
		STATUS     	current
		DESCRIPTION
			"Table which shows information about the user interfaces."
		::= { flWorkBasic 17 }
	   
	flWorkBasicPortEntry OBJECT-TYPE
		SYNTAX		FlWorkBasicPortEntry
		MAX-ACCESS 	not-accessible 
		STATUS     	current
		DESCRIPTION 
			"Each entry in this table represents an information instance about a single user interface."
		INDEX		{ flWorkBasicPortIdx }
		::= { flWorkBasicPortTable 1 }
	   
	FlWorkBasicPortEntry ::=
		SEQUENCE {
			flWorkBasicPortIdx  
				INTEGER,
			flWorkBasicPortService
				OCTET STRING,
			flWorkBasicPortProtocol
				OCTET STRING,
			flWorkBasicPortTransport
				OCTET STRING,
			flWorkBasicPort
				INTEGER
          }
		  
	flWorkBasicPortIdx OBJECT-TYPE
		SYNTAX     	INTEGER (1..255)
		MAX-ACCESS 	read-only
		STATUS     	current
		DESCRIPTION
			"Each index is the number of an information instance about a single user interface."
		::= { flWorkBasicPortEntry 1 }

	flWorkBasicPortService OBJECT-TYPE
		SYNTAX     	OCTET STRING
		MAX-ACCESS 	read-only
		STATUS     	current
		DESCRIPTION
			"User interface service"
		::= { flWorkBasicPortEntry 2 }
		
	flWorkBasicPortProtocol OBJECT-TYPE
		SYNTAX     	OCTET STRING
		MAX-ACCESS 	read-only
		STATUS     	current
		DESCRIPTION
			"Used protocol"
		::= { flWorkBasicPortEntry 3 }
		
	flWorkBasicPortTransport OBJECT-TYPE
		SYNTAX     	OCTET STRING
		MAX-ACCESS 	read-only
		STATUS     	current
		DESCRIPTION
			"Used transport protocol"
		::= { flWorkBasicPortEntry 4 }
	  
	flWorkBasicPort OBJECT-TYPE
		SYNTAX		INTEGER
		MAX-ACCESS	read-only
		STATUS    	current
		DESCRIPTION
			"Used port"
		::= { flWorkBasicPortEntry 5 }
				 
	--**********************************************************************


    --
    --
    -- flWorkComponents Group
    --
    flWorkComponentsTable
        OBJECT-TYPE
            SYNTAX      SEQUENCE OF FlWorkComponentsEntry
            MAX-ACCESS  not-accessible
            STATUS      current
            DESCRIPTION
                "Table of information about the available
                 interface modules of the current device union."
        ::= { flWorkComponents 1 }

    flWorkComponentsEntry
        OBJECT-TYPE
            SYNTAX      FlWorkComponentsEntry
            MAX-ACCESS  not-accessible
            STATUS      current
            DESCRIPTION
                "An entry in the table, containing information about
                 a single interface module of current device union."
            INDEX       { flWorkComponentsIndex }
        ::= { flWorkComponentsTable 1 }

    FlWorkComponentsEntry
        ::= SEQUENCE {
            flWorkComponentsIndex
                Integer32,
            flWorkComponentsOID
                OBJECT IDENTIFIER,
            flWorkComponentsURL
                DisplayString,
            flWorkComponentsDevSign
                INTEGER
        }

    flWorkComponentsIndex
        OBJECT-TYPE
            SYNTAX      Integer32 (1..1024)
            MAX-ACCESS  read-only
            STATUS      current
            DESCRIPTION
                "This object identifies the interface module within
                 the device union for which this entry contains
                 information."
        ::= { flWorkComponentsEntry 1 }

    flWorkComponentsOID
        OBJECT-TYPE
            SYNTAX      OBJECT IDENTIFIER
            MAX-ACCESS  read-only
            STATUS      current
            DESCRIPTION
                "This OID points to the correspondent component
                 entry in flComponents group."
        ::= { flWorkComponentsEntry 2 }

    flWorkComponentsURL
        OBJECT-TYPE
            SYNTAX      DisplayString
            MAX-ACCESS  read-only
            STATUS      current
            DESCRIPTION
                "The device will always return the web page URL
                 of itself within the devices web space which
                 contains information about the component:
                 
                            http://ip_addr/
                 
                 In further kinds it may be that instead of the
                 ip_addr the full qualified domain name will be
                 showing."
        ::= { flWorkComponentsEntry 3 }

    flWorkComponentsDevSign
        OBJECT-TYPE
            SYNTAX      INTEGER (0..255)
            MAX-ACCESS  read-only
            STATUS      current
            DESCRIPTION
                "Reports the device sign of the interface module
                 like defined by the vendor."
        ::= { flWorkComponentsEntry 4}


    --
    --
    -- flWorkFWInfo Group
    --
    flWorkFWInfoVersion
        OBJECT-TYPE
            SYNTAX      OCTET STRING
            MAX-ACCESS  read-only
            STATUS      current
            DESCRIPTION
                "This object represents the version string
                 of the firmware release."
        ::= { flWorkFWInfo 1 }

    flWorkFWInfoState
        OBJECT-TYPE
            SYNTAX      OCTET STRING
            MAX-ACCESS  read-only
            STATUS      current
            DESCRIPTION
                "This object represent the current status
                 string of the firmware release."
        ::= { flWorkFWInfo 2 }

    flWorkFWInfoDate
        OBJECT-TYPE
            SYNTAX      OCTET STRING
            MAX-ACCESS  read-only
            STATUS      current
            DESCRIPTION
                "This object represent the compiling date
                 string of the firmware release."
        ::= { flWorkFWInfo 3 }

    flWorkFWInfoTime
        OBJECT-TYPE
            SYNTAX      OCTET STRING
            MAX-ACCESS  read-only
            STATUS      current
            DESCRIPTION
                "This object represent the compiling time
                 string of the firmware release."
        ::= { flWorkFWInfo 4 }

    flWorkFWInfoCopyright
        OBJECT-TYPE
            SYNTAX      DisplayString
            MAX-ACCESS  read-only
            STATUS      current
            DESCRIPTION
                "This object represent the current copyright
                 string of the firmware release like next:

                    Copyright by Phoenix Contact GmbH & Co. KG, 2003
                            
                 All alphanumeric characters (writeble) allowed."
        ::= { flWorkFWInfo 5 }

    flWorkFWInfoBootVersion
        OBJECT-TYPE
            SYNTAX      OCTET STRING
            MAX-ACCESS  read-only
            STATUS      current
            DESCRIPTION
                "This object represents the version string
                 of the boot loader release."
        ::= { flWorkFWInfo 6 }

    flWorkFWInfoBootState
        OBJECT-TYPE
            SYNTAX      OCTET STRING
            MAX-ACCESS  read-only
            STATUS      current
            DESCRIPTION
                "This object represent the current status
                 string of the boot loader release."
        ::= { flWorkFWInfo 7 }

    flWorkFWInfoBootDate
        OBJECT-TYPE
            SYNTAX      OCTET STRING
            MAX-ACCESS  read-only
            STATUS      current
            DESCRIPTION
                "This object represent the compiling date
                 string of the boot loader release."
        ::= { flWorkFWInfo 8 }

    flWorkFWInfoBootTime
        OBJECT-TYPE
            SYNTAX      OCTET STRING
            MAX-ACCESS  read-only
            STATUS      current
            DESCRIPTION
                "This object represent the compiling time
                 string of the boot loader release."
        ::= { flWorkFWInfo 9 }

    flWorkFWInfoOperStatus
        OBJECT-TYPE
            SYNTAX      INTEGER {
                            other(1),
                            ok(2),
                            notOk(3)
                        }
            MAX-ACCESS  read-only
            STATUS      current
            DESCRIPTION
                "This object indicates the operational state of
                 the firmware.
                 You get the state ok(2) if the device is in the
                 normal operation mode 'running'.
                 The state notOk(3) signals a failure.
                 The flWorkFWInfoHealthText object may be 
                 consulted for more specific information
                 about the state of the firmware's health."
        ::= { flWorkFWInfo 11 }

    flWorkFWInfoHealthText
        OBJECT-TYPE
            SYNTAX      DisplayString
            MAX-ACCESS  read-only
            STATUS      current
            DESCRIPTION
                "The health text object is a text string that
                 provides information relevant to the operational
                 state of the firmware. The firmware may use this
                 string to provide detailed information on current
                 failures, including how they detected, and/or
                 instructions for problem resolution. The content
                 are firmware-specific."
        ::= { flWorkFWInfo 12 }
    
    flWorkFWInfoDisplay
        OBJECT-TYPE
            SYNTAX      DisplayString
            MAX-ACCESS  read-only
            STATUS      current
            DESCRIPTION
                "Output to the display at the point of time of the 
                access to this object."
        ::= { flWorkFWInfo 13 }




    --
    -- flWorkFWInfoEventTable Group
    --
    --
    

   flWorkFWInfoEventTable
        OBJECT-TYPE
            SYNTAX      SEQUENCE OF FlWorkFWInfoEventEntry
            MAX-ACCESS  not-accessible
            STATUS      current
            DESCRIPTION
                "Table of Events."
        ::= { flWorkFWInfoEvent 1 }

    flWorkFWInfoEventEntry
        OBJECT-TYPE
            SYNTAX      FlWorkFWInfoEventEntry
            MAX-ACCESS  not-accessible
            STATUS      current
            DESCRIPTION
                "Each entry in the table contains one host ip
                 address for a trap destination."
            INDEX       { flWorkFWInfoEventIndex }
        ::= { flWorkFWInfoEventTable 1 }

    FlWorkFWInfoEventEntry
        ::= SEQUENCE {
            flWorkFWInfoEventIndex
                Integer32,
            flWorkFWInfoEventCode
                Integer32,
            flWorkFWInfoEventDescription
                OCTET STRING,
            flWorkFWInfoEventSystemUpTime
                TimeTicks,
            flWorkFWInfoEventSntpTime
                OCTET STRING,
            flWorkFWInfoEventSntpDate
                OCTET STRING,
            flWorkFWInfoEventSntpSeconds
                Unsigned32,
            flWorkFWInfoEventSntpFractionalSeconds
                Unsigned32
        }

    flWorkFWInfoEventIndex
        OBJECT-TYPE
            SYNTAX      Integer32 (1..400)
            MAX-ACCESS  read-only
            STATUS      current
            DESCRIPTION
                "This object contains a consecutive number
                between 1 and 400 for the event table entries."
        ::= { flWorkFWInfoEventEntry 1 }

    flWorkFWInfoEventCode
        OBJECT-TYPE
            SYNTAX      Integer32
            MAX-ACCESS  read-only
            STATUS      current
            DESCRIPTION
                "This object contains the event code assigned
                to every event."
        ::= { flWorkFWInfoEventEntry 2 }

    flWorkFWInfoEventDescription
        OBJECT-TYPE
            SYNTAX      OCTET STRING
            MAX-ACCESS  read-only
            STATUS      current
            DESCRIPTION
                "This object contains a description string 
                which explains the kind of event."
        ::= { flWorkFWInfoEventEntry 3 }
        
    flWorkFWInfoEventSystemUpTime
        OBJECT-TYPE
            SYNTAX      TimeTicks
            MAX-ACCESS  read-only
            STATUS      current
            DESCRIPTION
                "This object contains the system up time
                at which an event occured."
        ::= { flWorkFWInfoEventEntry 4 }
        
    flWorkFWInfoEventSntpTime
        OBJECT-TYPE
            SYNTAX      OCTET STRING
            MAX-ACCESS  read-only
            STATUS      current
            DESCRIPTION
                "This object contains the UTC time
                at which an event occured."
        ::= { flWorkFWInfoEventEntry 5 }
        
    flWorkFWInfoEventSntpDate
        OBJECT-TYPE
            SYNTAX      OCTET STRING
            MAX-ACCESS  read-only
            STATUS      current
            DESCRIPTION
                "This object contains the UTC date
                at which an event occured."
        ::= { flWorkFWInfoEventEntry 6 }
        
    flWorkFWInfoEventSntpSeconds
        OBJECT-TYPE
            SYNTAX      Unsigned32
            MAX-ACCESS  read-only
            STATUS      current
            DESCRIPTION
                "This object contains the UTC seconds
                used in NTP at which an event occured."
        ::= { flWorkFWInfoEventEntry 7 }
        
    flWorkFWInfoEventSntpFractionalSeconds
        OBJECT-TYPE
            SYNTAX      Unsigned32
            MAX-ACCESS  read-only
            STATUS      current
            DESCRIPTION
                "This object contains the UTC fractional 
                seconds used in NTP at which an 
                event occured."
        ::= { flWorkFWInfoEventEntry 8 }
        
    flWorkFWInfoEventTableClear
        OBJECT-TYPE
            SYNTAX      INTEGER {
                            noClear(1),
                            clear(2)
                        }
            MAX-ACCESS  read-write
            STATUS      current
            DESCRIPTION
                "Setting this object to clear(2) causes a
                 deletion of all objects in the event table.

                 Setting this object to noClear(1) has no
                 effect. The firmware will always return
                 the value noClear(1) when this object is
                 read."
            DEFVAL  {noClear}                 
        ::= { flWorkFWInfoEvent 2 }

    --
    --
    -- flWorkFWCtrlBasic Group
    --
    flWorkFWCtrlReset
        OBJECT-TYPE
            SYNTAX      INTEGER {
                            noReset(1),
                            reset(2)
                        }
            MAX-ACCESS  read-write
            STATUS      current
            DESCRIPTION
                "Setting this object to reset(2) causes a
                 hardware reset of the device and all
                 components.

                 Setting this object to noReset(1) has no
                 effect. The firmware will always return
                 the value noReset(1) when this object is
                 reading."
            DEFVAL  {noReset}                 
        ::= { flWorkFWCtrlBasic 1 }

    flWorkFWCtrlTrapDestCapacity
        OBJECT-TYPE
            SYNTAX      Integer32 (1..1024)
            MAX-ACCESS  read-only
            STATUS      obsolete
            DESCRIPTION
                "This object hold the number of trap destination
                 entries (host ip addresses) contained in the
                 table flWorkFWCtrlTrapDestTable."
        ::= { flWorkFWCtrlBasic 2 }

    flWorkFWCtrlWatchdog
        OBJECT-TYPE
            SYNTAX      INTEGER {
                            disable(1),
                            enable(2)
                        }
            MAX-ACCESS  read-write
            STATUS      current
            DESCRIPTION
                "Setting this object to enable(2) activates the
                 watchdog during the next restart.

                 This Watchdog monitors the reliable operation
                 of the device. If the reliable operation cannot
                 be ensured any longer, then the outputs of the 
                 modules are brought into the safe operating condition.
                 When this object is enabled then the switch is 
                 automatically restarted else, when disabled, should be
                 manually restarted. 

                 The modified adjustments become effective after
                 a restart of the device."
        ::= { flWorkFWCtrlBasic 3 }

    flWorkFWCtrlHTTP
        OBJECT-TYPE
            SYNTAX      INTEGER {
                            disable(1),
                            enable(2)
                        }
            MAX-ACCESS  read-write
            STATUS      deprecated
            DESCRIPTION
                "Setting this object to disable(1) disables the
                 web server of the device.

                 For some products, the modified adjustments become effective after
                 a restart of the device."
             DEFVAL  {enable}
        ::= { flWorkFWCtrlBasic 6 }        
        
    flWorkFWCtrlTelnet
        OBJECT-TYPE
            SYNTAX      INTEGER {
                            disable(1),
                            enable(2)
                        }
            MAX-ACCESS  read-write
            STATUS      deprecated
            DESCRIPTION
                "Setting this object to disable(1) disables the
                 telnet server of the device.

                 For some products, the modified adjustments become effective after
                 a restart of the device."
             DEFVAL  {enable}
        ::= { flWorkFWCtrlBasic 7 }        
   
    flWorkFWCtrlWebPageRefresh
        OBJECT-TYPE
              SYNTAX   INTEGER (0..3600)
              MAX-ACCESS   read-write
              STATUS   current
              DESCRIPTION
                      "The refresh interval in seconds for refreshing
                       the web pages by the web browser. The granularity
                       of this timer is 1 second.
                       A value of zero disables the refreshing."
              DEFVAL  {30}
              ::= { flWorkFWCtrlBasic 8 }        

    flWorkFWCtrlSNMP
        OBJECT-TYPE
            SYNTAX      INTEGER {
                            disable(1),
                            enable(2)
                        }
            MAX-ACCESS  read-write
            STATUS      deprecated
            DESCRIPTION
                "Setting this object to disable(1) disables the
                 snmp agent of the device.

                 For some products, the modified adjustments become effective after
                 a restart of the device."
             DEFVAL  {enable}
        ::= { flWorkFWCtrlBasic 9 }
        
    flWorkFWCtrlOperatingMode OBJECT-TYPE
        SYNTAX INTEGER {
               default(1),
               profinet(2),
               ethernetIP(3)
        }
        MAX-ACCESS read-write
        STATUS current
        DESCRIPTION
            "This object allows the user to preselect
             a configuration for a special application.
             Please read the manual for additional
             information about the various settings."
        DEFVAL  { default }
        ::= { flWorkFWCtrlBasic 10 }

    flWorkFWCtrlIfCounters
        OBJECT-TYPE
            SYNTAX      INTEGER {
                            noClear(1),
                            clear(2)
                        }
            MAX-ACCESS  read-write
            STATUS      current
            DESCRIPTION
                "When set this object to clear(2), the statistic
                 counters of all ports will be cleared.

                Setting this object to noClear(1) has no effect. 
                Reading this object you get always
                the value noClear(1)."
        ::= { flWorkFWCtrlBasic 11 }

    flWorkFWCtrlHTTPSecure
        OBJECT-TYPE
            SYNTAX      INTEGER {
                            disable(1),
                            enable(2)
                        }
            MAX-ACCESS  read-write
            STATUS      deprecated
            DESCRIPTION
                "Setting this object enables or disables the HTTPS
                 server on this device."
             DEFVAL  {disable}
        ::= { flWorkFWCtrlBasic 12 }        
        
    flWorkFWCtrlSSH
        OBJECT-TYPE
            SYNTAX      INTEGER {
                            disable(1),
                            enable(2)
                        }
            MAX-ACCESS  read-write
            STATUS      deprecated
            DESCRIPTION
                "Setting this object enables or disables the SSH
                 server on this device."
             DEFVAL  {disable}
        ::= { flWorkFWCtrlBasic 13 } 

    flWorkFWCtrlSNMPv3
        OBJECT-TYPE
            SYNTAX      INTEGER {
                            disable(1),
                            enable(2)
                        }
            MAX-ACCESS  read-write
            STATUS      deprecated
            DESCRIPTION
                "Setting this object enables or disables version 3 of 
                 of SNMP which is used for secure connection to the device."
             DEFVAL  {disable}
        ::= { flWorkFWCtrlBasic 14 }

      flWorkFwCtrlCpuOverloadStopForwarding
          OBJECT-TYPE
            SYNTAX      INTEGER {
                            doNotStop(1),
                            stopForwarding(2)
                        }
            MAX-ACCESS  read-write
            STATUS      current
            DESCRIPTION
                "When set to stopForwarding(2) the 
                device will stop forwarding packets
                if a CPU overload condition occurs which
                is shown by errorcode 89 in the display.
                If set to doNotStop(1) only errorcode
                will be shown in the display but the 
                device will try to continue forwarding
                operation. 
                (1) is factory default"
        ::= { flWorkFWCtrlBasic 15 }
    
     flWorkFWCtrlDisplayRights
        OBJECT-TYPE
            SYNTAX      INTEGER {
                            disable(1),
                            enable(2)
                        }
            MAX-ACCESS  read-write
            STATUS      current
            DESCRIPTION
                "Setting this object enables or disables configuration settings via display."
             DEFVAL  {disable}
        ::= { flWorkFWCtrlBasic 16 }

     flWorkFWCtrlDisplayContrast
        OBJECT-TYPE
            SYNTAX      INTEGER (1..255)
            MAX-ACCESS  read-write
            STATUS      current
            DESCRIPTION
                "Set or get the current display contrast of the device display"             
        ::= { flWorkFWCtrlBasic 17 }
    
     flWorkFWCtrlCLIIPSock
        OBJECT-TYPE
             SYNTAX      INTEGER {
                            disable(1),
                            enable(2)
                        }
            MAX-ACCESS  read-write
            STATUS      current
            DESCRIPTION
                "Setting this object enables or disables CLI IP-Socket Interface."             
        ::= { flWorkFWCtrlBasic 18 }


    flWorkFWCtrlLEDsOff OBJECT-TYPE
             SYNTAX      INTEGER {
                            disable(1),
                            enable(2)
                        }
        MAX-ACCESS read-write
        STATUS current
        DESCRIPTION
            "Enable or disable LEDs Off Mode on the Device. In LEDs Off Mode
            no LEDs will be active."
        DEFVAL  { disable }
        ::= { flWorkFWCtrlBasic 20 }


   flWorkFWCtrlWebServerMode OBJECT-TYPE
             SYNTAX      INTEGER {
                            disable(1),
                            http(2),
                            https(3)
                        }
        MAX-ACCESS read-write
        STATUS current
        DESCRIPTION
            "Control the mode of the web server. The following modes exist:
            
                DISABLE (Deactivates the web interface!)
                HTTP    (standard, unsecured),
                HTTPS   (secured, use https://<ip> as url)"
                 
        DEFVAL  { http }
        ::= { flWorkFWCtrlBasic 21 }
        
    flWorkFWCtrlSnmpAgentMode OBJECT-TYPE
             SYNTAX      INTEGER {
                            disable(1),
                            snmpV2c(2),
                            snmpV3(3)
                        }
        MAX-ACCESS read-write
        STATUS current
        DESCRIPTION
            "Control the mode of the snmp agent. The following modes exist:
            
                DISABLE (Deactivates the snmp agent!)
                SNMPv2c (unsecured)
                SNMPv3  (secured, Authentication protocol: MD5, privacy protocol: DES)"
                 
        DEFVAL  { snmpV2c }
        ::= { flWorkFWCtrlBasic 22 }
        
    flWorkFWCtrlCliServiceMode OBJECT-TYPE
             SYNTAX      INTEGER {
                            disable(1),
                            telnet(2),
                            ssh(3)
                        }
        MAX-ACCESS read-write
        STATUS current
        DESCRIPTION
            "Control the mode of the snmp agent. The following modes exist:
            
                DISABLE (Deactivates the cli service!)
                TELNET  (unsecured)
                SSH     (secured)"
                 
        DEFVAL  { telnet }
        ::= { flWorkFWCtrlBasic 23 }
		
    flWorkFWCtrlPersistentEventLoggingMode OBJECT-TYPE
             SYNTAX      INTEGER {
                            disable(1),
                            enable(2)
                        }
        MAX-ACCESS read-write
        STATUS current
        DESCRIPTION
            "Enable or disable persistent storage of event table entries"
        DEFVAL  { disable }
        ::= { flWorkFWCtrlBasic 24 }
		
	flWorkFWCtrlSmartModeGblEnable OBJECT-TYPE
             SYNTAX      INTEGER {
                            disable(1),
                            enable(2)
                        }
        MAX-ACCESS read-write
        STATUS current
        DESCRIPTION
            "Enable or disable the smart mode functionality (mode button)"
        DEFVAL  { enable }
        ::= { flWorkFWCtrlBasic 25 }
		
	flWorkFWCtrlHostnameResolutionEnable OBJECT-TYPE
             SYNTAX      INTEGER {
                            disable(1),
                            enable(2)
                        }
        MAX-ACCESS read-write
        STATUS current
        DESCRIPTION
            "Enable or disable the hostname resolution via mDNS and LLMNR"
        DEFVAL  { enable }
        ::= { flWorkFWCtrlBasic 26 }
		
	 flWorkFWCtrlHostname OBJECT-TYPE
		SYNTAX      DisplayString
		MAX-ACCESS  read-write
		STATUS      current
		DESCRIPTION
			"The device will always return his hostname.

			 At the delivery time to the customer a default value
			 is already present. The default value consists of the device 
			 type and the second half of the MAC address of the device.

			 As far as he is concerned the customer can write his
			 own hostname later.
			 The hostname must have a length of 2 to 63 characters.
			 Only letters, numbers and hyphens (apart from the first character) are allowed.
			 
			 If the hostname resolution is enabled, the device can be reached 
			 via his hostname. If mDNS is used for name resolution an additional 
			 .local suffix is appended to the hostname."            
        ::= { flWorkFWCtrlBasic 27 }	
		
	flWorkFWCtrlSdCardGblEnable OBJECT-TYPE
             SYNTAX      INTEGER {
                            disable(1),
                            enable(2)
                        }
        MAX-ACCESS read-write
        STATUS current
        DESCRIPTION
            "Enable or disable the SD card slot."
        DEFVAL  { enable }
        ::= { flWorkFWCtrlBasic 28 }

	flWorkFWCtrlWebLoginRequired OBJECT-TYPE
             SYNTAX      INTEGER {
                            disable(1),
                            enable(2)
                        }
        MAX-ACCESS read-write
        STATUS current
        DESCRIPTION
            "Enable or disable a required user login for the web server."
        DEFVAL  { disable }
        ::= { flWorkFWCtrlBasic 29 }

	flWorkFWCtrlTopologyBasedIpPort OBJECT-TYPE 
			SYNTAX Integer32
			MAX-ACCESS read-write
			STATUS current
			DESCRIPTION
				 "The port on which topology based ip is activated. 
				 Setting the port to zero disables the feature."
			DEFVAL  {0}    
			::= { flWorkFWCtrlBasic 30 } 

    flWorkFWCtrlTopologyBasedIpState
        OBJECT-TYPE
            SYNTAX      INTEGER {
                                disabled(0),
                                client(1),
                                root(2)
                        }
            MAX-ACCESS  read-only
            STATUS      current
            DESCRIPTION
                "The state of the topology based ip feature (disabled/client/root)."
        ::= { flWorkFWCtrlBasic 31 }
		
    --
    --
    -- flWorkFWCtrlTrapDest Group
    --
    flWorkFWCtrlTrapDestTable
        OBJECT-TYPE
            SYNTAX      SEQUENCE OF FlWorkFWCtrlTrapDestEntry
            MAX-ACCESS  not-accessible
            STATUS      current
            DESCRIPTION
                "Table of host ip addresses for available trap
                 destinations."
        ::= { flWorkFWCtrlTrapDest 1 }

    flWorkFWCtrlTrapDestEntry
        OBJECT-TYPE
            SYNTAX      FlWorkFWCtrlTrapDestEntry
            MAX-ACCESS  not-accessible
            STATUS      current
            DESCRIPTION
                "Each entry in the table contains one host ip
                 address for a trap destination."
            INDEX       { flWorkFWCtrlTrapDestIndex }
        ::= { flWorkFWCtrlTrapDestTable 1 }

    FlWorkFWCtrlTrapDestEntry
        ::= SEQUENCE {
            flWorkFWCtrlTrapDestIndex
                Integer32,
            flWorkFWCtrlTrapDestIPAddr
                IpAddress,
            flWorkFWCtrlTrapDestName
                DisplayString
        }

    flWorkFWCtrlTrapDestIndex
        OBJECT-TYPE
            SYNTAX      Integer32 (1..255)
            MAX-ACCESS  read-only
            STATUS      current
            DESCRIPTION
                "This object identifies the trap destination over
                 host ip address which this entry named. This value
                 is never greater then flWorkFWCtrlTrapDestCapacity."
        ::= { flWorkFWCtrlTrapDestEntry 1 }

    flWorkFWCtrlTrapDestIPAddr
        OBJECT-TYPE
            SYNTAX      IpAddress
            MAX-ACCESS  read-write
            STATUS      current
            DESCRIPTION
                "This ip address named a trap destination host
                 who is using to receive trap events. Values in
                 the form 0.0.0.0 are non valid ip addresses and
                 will be understanding as an inactive trap
                 destination entry."
        ::= { flWorkFWCtrlTrapDestEntry 2 }

    flWorkFWCtrlTrapDestName
    	OBJECT-TYPE
	        SYNTAX DisplayString
	        MAX-ACCESS read-write
	        STATUS current
	        DESCRIPTION
	            "Hostname of a trap destination host
                 who is used to receive trap events.
	             The maximum size of the string is 255 characters."       
	        DEFVAL  {""}
        ::= { flWorkFWCtrlTrapDestEntry 4 }

    flWorkFWCtrlTrapDestCapacityMax
        OBJECT-TYPE
            SYNTAX      Integer32 (1..1024)
            MAX-ACCESS  read-only
            STATUS      current
            DESCRIPTION
                "This object hold the maximal number of trap destination
                 entries (host ip addresses) contained in the
                 table flWorkFWCtrlTrapDestTable."
        ::= { flWorkFWCtrlTrapDest 2 }


    flWorkFWCtrlTrapDestEnable
        OBJECT-TYPE
            SYNTAX      INTEGER {
                            disable(1),
                            enable(2)
                        }    
            MAX-ACCESS  read-write
            STATUS      current
            DESCRIPTION
                "Determines whether this device will
                 transmit traps to SNMP management stations.
                 If this object is set to disable(1) no traps
                 will be sent."
            DEFVAL  {disable}
        ::= { flWorkFWCtrlTrapDest 3 }

    flWorkFWCtrlTrapLink
        OBJECT-TYPE
            SYNTAX      INTEGER {
                            phyPortNumber(1),
                            snmpIfIndex(2)
                        }    
            MAX-ACCESS  read-write
            STATUS      current
            DESCRIPTION
                "Setting this object to phyPortNumber(1) the
                 link up and link down traps contain as binding 'ifIndex'
                 the physikal port number. The binding is set to the interface
                 number of the mib2 interface table when setting this
                 object to snmpIfIndex(2)."
            DEFVAL  {phyPortNumber}
        ::= { flWorkFWCtrlTrapDest 4 }
   
    flWorkFWCtrlTrapConnectionTest
        OBJECT-TYPE
            SYNTAX      INTEGER {
                            noTrap(1),
                            sendTrap(2)
                        }    
            MAX-ACCESS  read-write
            STATUS      current
            DESCRIPTION
                "Setting this object to sendTrap(2) the snmp agent sends
                 the trap trapManagerConnection.
                 Setting this object to noTrap(1) has no effect."            
        ::= { flWorkFWCtrlTrapDest 5 }


    flWorkFWCtrlTrapEnableTable
        OBJECT-TYPE
            SYNTAX      SEQUENCE OF FlWorkFWCtrlTrapEnableEntry
            MAX-ACCESS  not-accessible
            STATUS      current
            DESCRIPTION
                "Table to enable/disable the different kind of traps."
        ::= { flWorkFWCtrlTrapDest 10 }

    flWorkFWCtrlTrapEnableEntry
        OBJECT-TYPE
            SYNTAX      FlWorkFWCtrlTrapEnableEntry
            MAX-ACCESS  not-accessible
            STATUS      current
            DESCRIPTION
                "Each entry in the table contains information
                 for one trap."
            INDEX       { flWorkFWCtrlTrapEnableIndex }
        ::= { flWorkFWCtrlTrapEnableTable 1 }

    FlWorkFWCtrlTrapEnableEntry
        ::= SEQUENCE {
            flWorkFWCtrlTrapEnableIndex
                Integer32,
            flWorkFWCtrlTrapEnableOid
                OBJECT IDENTIFIER,
            flWorkFWCtrlTrapEnableName
                DisplayString,                
            flWorkFWCtrlTrapEnableStatus
                INTEGER
        }

    flWorkFWCtrlTrapEnableIndex
        OBJECT-TYPE
            SYNTAX      Integer32 (1..255)
            MAX-ACCESS  read-only
            STATUS      current
            DESCRIPTION
                "This object identifies the trap by the last part 
                 of the trap oid (see list of traps in group 
                 flWorkTrapsDelemeter)."
        ::= { flWorkFWCtrlTrapEnableEntry 1 }

    flWorkFWCtrlTrapEnableOid
        OBJECT-TYPE
            SYNTAX      OBJECT IDENTIFIER
            MAX-ACCESS  read-only
            STATUS      current
            DESCRIPTION
                "OID of the trap (see list of traps in group 
                 flWorkTrapsDelemeter)."
        ::= { flWorkFWCtrlTrapEnableEntry 2 }
        
    flWorkFWCtrlTrapEnableName
        OBJECT-TYPE
            SYNTAX      DisplayString
            MAX-ACCESS  read-only
            STATUS      current
            DESCRIPTION
                "The name of this trap to identify the trap."
        ::= { flWorkFWCtrlTrapEnableEntry 3 }
        
    flWorkFWCtrlTrapEnableStatus
        OBJECT-TYPE
            SYNTAX      INTEGER {
                            disable(1),
                            enable(2)
                        }    
            MAX-ACCESS  read-write
            STATUS      current
            DESCRIPTION
                "Status of sending this kind of trap.
                 Each trap can be disabled separately when the 
                 sending traps is enabled for the snmp agent (see
                 object flWorkFWCtrlTrapDestEnable)."
            DEFVAL  {enable}
        ::= { flWorkFWCtrlTrapEnableEntry 4 }



    --
    --
    -- flWorkNetIfParameter Group
    --
    flWorkNetIfParamPhyAddress
        OBJECT-TYPE
            SYNTAX      MacAddress
            MAX-ACCESS  read-only
            STATUS      current
            DESCRIPTION
               "The interface's address at the protocol layer
                immediately `below' the network layer in the
                protocol stack."
        ::= { flWorkNetIfParameter 1 }

    flWorkNetIfParamIpAddress
        OBJECT-TYPE
            SYNTAX      IpAddress
            MAX-ACCESS  read-write
            STATUS      current
            DESCRIPTION
               "The ip address of this device.
                Changing this object will take effect
                after setting the object flWorkNetIfParamSave
                to apply(2).
                Note: For some products a reboot is required instead of the 
                      flWorkNetIfParamSave object, to load the
                      new Ip-Parameter settings."
        ::= { flWorkNetIfParameter 2 }
    
    flWorkNetIfParamSubnetmask
        OBJECT-TYPE
            SYNTAX      IpAddress
            MAX-ACCESS  read-write
            STATUS      current
            DESCRIPTION
               "The subnet mask associated with the IP address of
                this entry.  The value of the mask is an IP
                address with all the network bits set to 1 and all
                the hosts bits set to 0.
                Changing this object will take effect
                after setting the object flWorkNetIfParamSave
                to apply(2).
                Note: For some products a reboot is required instead of the 
                      flWorkNetIfParamSave object, to load the
                      new Ip-Parameter settings."
        ::= { flWorkNetIfParameter 3 }
        
    flWorkNetIfParamGwIpAddress
        OBJECT-TYPE
            SYNTAX      IpAddress
            MAX-ACCESS  read-write
            STATUS      current
            DESCRIPTION
               "IP address of the default gateway.
                Changing this object will take effect
                after setting the object flWorkNetIfParamSave
                to appFor some products a reboot is required instead of the 
                      flWorkNetIfParamSave object, to load the
                      new Ip-Parameter settings."
        ::= { flWorkNetIfParameter 4 }
    
    flWorkNetIfParamStatus
        OBJECT-TYPE
            SYNTAX      INTEGER {
                            notModified(1),
                            modified(2)
                            }
            MAX-ACCESS  read-only
            STATUS      current
            DESCRIPTION
                "This object is used to synchronize the modification of the IP
                parameters used by the protocol stack based on the 
                flWorkNetIfParameter MIB objects. 
                If flWorkNetIfParamStatus returns notModified(1), no modifications 
                were made to flWorkNetIfParamIpAddress, flWorkNetIfParamSubnetmask 
                and flWorkNetIfParamGwIpAddress. If flWorkNetIfParamStatus returns 
                modified(2), one or more objects were changed, but have not been 
                applied."
        ::= { flWorkNetIfParameter 5 }

    flWorkNetIfParamSave
        OBJECT-TYPE
            SYNTAX      INTEGER {
                            restore(1),
                            apply(2)
                            }
            MAX-ACCESS  read-write
            STATUS      current
            DESCRIPTION
                "This object is used to save the modification of the IP
                parameters used by the protocol stack based on the flWorkNetIfParameter
                MIB objects. This allows the user to change flWorkNetIfParamIpAddress, 
                flWorkNetIfParamSubnetmask and flWorkNetIfParamGwIpAddress and then 
                apply the changes to the unit using apply(2).
                If one or more of the flWorkNetIfParameter objects were modified, 
                the user can restore the parameters to a mirror of the NVM values 
                using restore(1).
                Note: You can apply(2) to modified ip parameter only if the object
                      flWorkNetIfParamAssignment has been set to static(1)!
                      Otherwise you get an snmp response indicating an error."
            DEFVAL  {restore}
        ::= { flWorkNetIfParameter 6 }

    flWorkNetIfParamAssignment
        OBJECT-TYPE
            SYNTAX      INTEGER {
                            static(1),                            
                            bootp(2),
                            dhcp(3),
                            dcp(4),
							topology(6)
                        }
            MAX-ACCESS  read-write
            STATUS      current
            DESCRIPTION
                "Kind of the IP address assignment.

                 The supported options of the device are described in the 
                 user manual of the product. Some options become effective after
                 restarting the device.
				 Option 6 (topology) cannot be set manually."
            DEFVAL  {bootp}
        ::= { flWorkNetIfParameter 7 }

    flWorkNetIfParamManagementVlanId
        OBJECT-TYPE
            SYNTAX      Integer32 (1..4094)
            MAX-ACCESS  read-write
            STATUS      current
            DESCRIPTION
                "Vlan ID of the management agent in the case the device
                 is running in mode VLAN Tagging."
            DEFVAL  {1}
        ::= { flWorkNetIfParameter 8 }

    flWorkNetIfParamConflictDetection 
        OBJECT-TYPE
            SYNTAX      INTEGER {
                            none(1),                            
                            acd(2)
                        }
            MAX-ACCESS  read-write
            STATUS      current
            DESCRIPTION
                "Kind of mechanism to detect IP address conflict."
                         
            DEFVAL  {none}
        ::= { flWorkNetIfParameter 9 }

    --
    --
    -- flWorkNetIfParamDnsServer Group
    --
    flWorkNetIfParamDnsServerTable
        OBJECT-TYPE
            SYNTAX      SEQUENCE OF FlWorkNetIfParamDnsServerEntry
            MAX-ACCESS  not-accessible
            STATUS      current
            DESCRIPTION
                "Table of host ip addresses for available DNS
                 servers."
        ::= { flWorkNetIfParameter 10 }

    flWorkNetIfParamDnsServerEntry
        OBJECT-TYPE
            SYNTAX      FlWorkNetIfParamDnsServerEntry
            MAX-ACCESS  not-accessible
            STATUS      current
            DESCRIPTION
                "Each entry in the table contains one host ip
                 address for a DNS server."
            INDEX       { flWorkNetIfParamDnsServerIndex }
        ::= { flWorkNetIfParamDnsServerTable 1 }

    FlWorkNetIfParamDnsServerEntry
        ::= SEQUENCE {
            flWorkNetIfParamDnsServerIndex
                Integer32,
            flWorkNetIfParamDnsServerIPAddr
                IpAddress
        }

    flWorkNetIfParamDnsServerIndex
        OBJECT-TYPE
            SYNTAX      Integer32 (1..255)
            MAX-ACCESS  read-only
            STATUS      current
            DESCRIPTION
                "This object identifies the DNS server over
                 host ip address which this entry named."
        ::= { flWorkNetIfParamDnsServerEntry 1 }

    flWorkNetIfParamDnsServerIPAddr
        OBJECT-TYPE
            SYNTAX      IpAddress
            MAX-ACCESS  read-write
            STATUS      current
            DESCRIPTION
                "DNS server IP address. This must be configured if hostnames
                 are used on the device."
        ::= { flWorkNetIfParamDnsServerEntry 2 }


    --
    --
    -- flWorkNetPort Group
    --
    flWorkNetPortCapacity
        OBJECT-TYPE
            SYNTAX      Integer32 (1..1024)
            MAX-ACCESS  read-only
            STATUS      current
            DESCRIPTION
               "This object will always return the number 
                of network ports."
        ::= { flWorkNetPort 1 }

    flWorkNetPortTable
        OBJECT-TYPE
            SYNTAX      SEQUENCE OF FlWorkNetPortEntry
            MAX-ACCESS  not-accessible
            STATUS      current
            DESCRIPTION
                "Table of network ports."
        ::= { flWorkNetPort 2 }

    flWorkNetPortEntry
        OBJECT-TYPE
            SYNTAX      FlWorkNetPortEntry
            MAX-ACCESS  not-accessible
            STATUS      current
            DESCRIPTION
                "An entry in the table, containing information 
                 of one network port."
            INDEX       { flWorkNetPortIndex }
        ::= { flWorkNetPortTable 1 }

    FlWorkNetPortEntry
        ::= SEQUENCE {
            flWorkNetPortIndex
                Integer32,
            flWorkNetPortLinkState
                INTEGER,
            flWorkNetPortSpeed
                Gauge32,
            flWorkNetPortDuplexMode
                INTEGER,
            flWorkNetPortNegotiation
                INTEGER,
            flWorkNetPortName
                DisplayString,
            flWorkNetPortEnable
                INTEGER,       
            flWorkNetPortLinkMonitoring
                INTEGER,
            flWorkNetPortModus
                INTEGER,
            flWorkNetPortSTPEnable
                INTEGER,
            flWorkNetPortIfIndex
                Integer32,
            flWorkNetPortLLWHPort
                Integer32,
            flWorkNetPortType
                DisplayString,
            flWorkNetPortModuleName
                DisplayString,
            flWorkNetPortInterfaceName 
                DisplayString,
            flWorkNetPortPriorityLevel
                INTEGER,
            flWorkNetPortPofTransmittingPower
                INTEGER,
            flWorkNetPortStpMode
                INTEGER,
            flWorkNetPortFlowControl
                INTEGER,
            flWorkNetPortMaxFrameSize
                INTEGER,
            flWorkNetPortJumboFrame
                INTEGER,
            flWorkNetPortCableLength
                DisplayString,
            flWorkNetPortPHYcompatibility
                INTEGER
        }

    flWorkNetPortIndex
        OBJECT-TYPE
            SYNTAX      Integer32 (1..1024)
            MAX-ACCESS  read-only
            STATUS      current
            DESCRIPTION
                "This object identifies the port. This value
                 is never greater then flWorkNetPortCapacity."
        ::= { flWorkNetPortEntry 1 }

    flWorkNetPortLinkState
        OBJECT-TYPE
            SYNTAX      INTEGER {
                            connected(1),
                            notConnected(2),
                            farEndFault(3)
                            }
            MAX-ACCESS  read-only
            STATUS      current
            DESCRIPTION
                "Get back the current state of the port link.
                 The state farEndFault(3) indicates that this
                 fiber optic port receives a signal but the 
                 other port of the path don't get a signal.
                 The state farEndFault(3) is supported by the
                 fx interfaces of the FL SWITCH MM HS."
        ::= { flWorkNetPortEntry 2 }

    flWorkNetPortSpeed
        OBJECT-TYPE
            SYNTAX      Gauge32
            MAX-ACCESS  read-only
            STATUS      current
            DESCRIPTION
                "The current interface's bandwidth in bits per second."
        ::= { flWorkNetPortEntry 3 }

    flWorkNetPortDuplexMode
        OBJECT-TYPE
            SYNTAX      INTEGER {
                                noLink(0),
                                full(1),
                                half(2)
                                }
            MAX-ACCESS  read-only
            STATUS      current
            DESCRIPTION
                "The current duplex mode of this port."
        ::= { flWorkNetPortEntry 4 }

    flWorkNetPortNegotiation
        OBJECT-TYPE
            SYNTAX      INTEGER {
                                auto(1),
                                manual(2)
                                }
            MAX-ACCESS  read-only
            STATUS      current
            DESCRIPTION
                "This object gives an information 
                 if auto negotiation is active or not."
        ::= { flWorkNetPortEntry 5 }

    flWorkNetPortName 
        OBJECT-TYPE
            SYNTAX     DisplayString
            MAX-ACCESS  read-write
            STATUS      current
            DESCRIPTION
                "The textual name of this interface, e.g., 'robot 1'."
            DEFVAL  {"Port x"}
        ::= { flWorkNetPortEntry 6 }
                                
    flWorkNetPortEnable 
        OBJECT-TYPE
            SYNTAX      INTEGER {
                                disable(1),                                
                                enable(2)
                                }
            MAX-ACCESS  read-write
            STATUS      current
            DESCRIPTION
                "This object is enable(2) when this interface is enabled and
                disable(1) when it is disabled. A disabled interfaces doesn't
                send any data packets."
            DEFVAL  {enable}
        ::= { flWorkNetPortEntry 7 }
      
    flWorkNetPortLinkMonitoring
        OBJECT-TYPE
            SYNTAX      INTEGER {
                                disable(1),                                
                                enable(2)
                                }
            MAX-ACCESS  read-write
            STATUS      current
            DESCRIPTION
                "Setting this object to enable(2) activates the 
                 link monitoring for this."
            DEFVAL  {disable}
        ::= { flWorkNetPortEntry 8 }

    flWorkNetPortModus
        OBJECT-TYPE
            SYNTAX      INTEGER {
                                autonegotiation(1),
                                half-10(2),
                                full-10(3),
                                half-100(4),
                                full-100(5),
                                autoneg10-100(20), 
                                fast-startup(21)
                                }
            MAX-ACCESS  read-write
            STATUS      current
            DESCRIPTION
                "The modus of this port defined by the user:
                        autonegotiation(1) - auto negotiation
                                half-10(2) -  10 MBit Half Duplex
                                full-10(3) -  10 MBit Full Duplex
                               half-100(4) - 100 MBit Half Duplex
                               full-100(5) - 100 MBit Full Duplex
                         autoneg10-100(20) - auto negotiation 10/100MBit only
                          fast-startup(21) - fast startup                               
                               
                 Note: 
                   a) The ports support auto crossover only in
                      the modus auto negotiation!
                   b) FX and HCS ports only support 100 MBit/s full
                      duplex.
                      If you try to set a FX or HCS port to a 
                      port modus not equal full-100(5) you get 
                      a snmp response indicating an error!"
            DEFVAL  {autonegotiation}
        ::= { flWorkNetPortEntry 9 }
                
    flWorkNetPortSTPEnable 
        OBJECT-TYPE
            SYNTAX      INTEGER {
                                disable(1),
                                enable(2)                                
                                }
            MAX-ACCESS  read-write
            STATUS      deprecated
            DESCRIPTION
                "Firmware with Rapid Spanning Tree:
                The value of this object is equal to the status
                of the object dot1dStpPortEnable. 
                When Rapid Spanning Tree is operating this objects
                handles the behaviour of the port regarding
                bridge protocol data units (BPDUs). 
                Set this object to disable(1) the interface doesn't
                send BPDUs when Rapid Spanning Tree operation is
                enabled. BPDUs will be send by this interface if
                the object is set to enable(2).

                Firmware with Spanning Tree:
                When spanning tree has been activated (see object 
                flSwitchCtrlSpanTree) this object handles the behaviour 
                of the port regarding bridge protocol data units (BPDUs). 
                Set this object to disable(1) the interface doesn't
                send BPDUs when Spanning Tree operation is enabled. 
                BPDUs will be send by this interface if the object 
                is set to enable(2).
                When the port stp status has been set to disable(1) the port
                uses fast forwarding to change from the port state disabled
                into the port state forwarding immediately (see object
                dot1dStpPortState of the bridge mib (rfc 1493)."
            DEFVAL  {enable}
        ::= { flWorkNetPortEntry 10 }

    flWorkNetPortIfIndex
        OBJECT-TYPE
            SYNTAX      Integer32
            MAX-ACCESS  read-only
            STATUS      current
            DESCRIPTION
                "The ifIndex of this application 'logical port' (see
                 interface table of the mib2)."
        ::= { flWorkNetPortEntry 11 }

    flWorkNetPortLLWHPort
        OBJECT-TYPE
            SYNTAX      Integer32 (8193..8296)
            MAX-ACCESS  read-only
            STATUS      current
            DESCRIPTION
                "A value that uniquely identifies a application 'logical port'
                (i.e., IEEE 802.3ad Aggregator) in the stack. This is
                a 'Layered Linear With Holes' (LLWH) port number that may may have
                holes for missing ports or units."
        ::= { flWorkNetPortEntry 12 }

    flWorkNetPortType
        OBJECT-TYPE
            SYNTAX      DisplayString
            MAX-ACCESS  read-only
            STATUS      current
            DESCRIPTION
                "The media type of this port."
        ::= { flWorkNetPortEntry 13 }        
    
    flWorkNetPortModuleName 
        OBJECT-TYPE
            SYNTAX      DisplayString
            MAX-ACCESS  read-only
            STATUS      current
            DESCRIPTION
                "The textual name of this module."
        ::= { flWorkNetPortEntry 14 }
        
    flWorkNetPortInterfaceName 
        OBJECT-TYPE
            SYNTAX      DisplayString
            MAX-ACCESS  read-only
            STATUS      current
            DESCRIPTION
                "The textual name of this interface
                 according to the labeling of the device."
        ::= { flWorkNetPortEntry 15 }

    flWorkNetPortPriorityLevel
        OBJECT-TYPE
            SYNTAX      INTEGER (0..7)
            MAX-ACCESS  read-write
            STATUS      current
            DESCRIPTION
                "Choose the priority level for the incoming
                 packets of one port in the switch
                 by selecting a level in the range from 0 to 7."
            DEFVAL  {0}
        ::= { flWorkNetPortEntry 16 }
        
    flWorkNetPortPofTransmittingPower
        OBJECT-TYPE
            SYNTAX      INTEGER {
                            unknown(1),
                            low(2),
                            normal(3)
                            }
            MAX-ACCESS  read-only
            STATUS      current
            DESCRIPTION
               "This objects shows the selected
                 transmitting power of POF ports.
                 For polymer fiber (POF) paths < 20 m
                 (65.62 ft.) the transmission power must
                 be reduced by sliding the switch on the
                 top of the interface module to the OFF
                 position. This objects returns the value
                 low(2) if the transmitting power has
                 been reduced.
                 For each other port type than POF this
                 object has the value unknown(1)."
        ::= { flWorkNetPortEntry 17 }

    flWorkNetPortStpMode
        OBJECT-TYPE
            SYNTAX      INTEGER {
                            stp(1),
                            rstp(2),
                            none(3)                            
                            }
            MAX-ACCESS  read-only
            STATUS      current
            DESCRIPTION
               "The mode of Spanning Tree Protocol the
                port is currently running. The value stp(1)
                indicates the Spanning Tree Protocol,
                rstp(2) indicates the Rapid Spanning
                Tree Protocol and none(3) indicates that
				stp/rstp are disabled."
        ::= { flWorkNetPortEntry 18 }

   flWorkNetPortFlowControl
        OBJECT-TYPE
            SYNTAX      INTEGER {
                                disable(1),                                
                                enable(2)
                                }
            MAX-ACCESS  read-write
            STATUS      current
            DESCRIPTION
                "Setting this object to disable(1) inactivates the 
                 flow control mechanism for this port."
            DEFVAL  {enable}
        ::= { flWorkNetPortEntry 20 }

   flWorkNetPortMaxFrameSize
    	OBJECT-TYPE
    	    SYNTAX 		INTEGER
    	    MAX-ACCESS  read-write
    	    STATUS      current
    	    DESCRIPTION
    	       "This object configures the maximum transmission unit(MTU) or
    	        the size of the largest packet that can be sent/received on the
    	        interface."
    	::= { flWorkNetPortEntry 21 }

    	
    flWorkNetPortJumboFrame
    	OBJECT-TYPE
    	    SYNTAX 		INTEGER {
    	    				 disable(0),
    	    				 enable(1)
        	    				}
    	    MAX-ACCESS  read-write
    	    STATUS      current
    	    DESCRIPTION
    	       "This object enables/disables jumbo frames on an interface."
    	::= { flWorkNetPortEntry 22 }

    flWorkNetPortCableLength
        OBJECT-TYPE
            SYNTAX      DisplayString
            MAX-ACCESS  read-only
            STATUS      current
            DESCRIPTION
                "The length of the table connected to this port in meters."
        ::= { flWorkNetPortEntry 23 }

    flWorkNetPortPHYcompatibility
    	OBJECT-TYPE
    	    SYNTAX 		INTEGER 
    	    MAX-ACCESS  read-write
    	    STATUS      current
    	    DESCRIPTION
    	       "This object activates some compatibility modes for PHY."
    	::= { flWorkNetPortEntry 24 }
        
    
    --
    --
    -- flWorkNetPortPoETable Group
    --
       

    flWorkNetPortPoETable
        OBJECT-TYPE
            SYNTAX      SEQUENCE OF FlWorkNetPortPoEEntry
            MAX-ACCESS  not-accessible
            STATUS      current
            DESCRIPTION
                "Table of PoE (Pover over Ethernet) properties of network ports."
        ::= { flWorkNetPort 3 }
        
     flWorkNetPortPoEEntry
        OBJECT-TYPE
            SYNTAX      FlWorkNetPortPoEEntry
            MAX-ACCESS  not-accessible
            STATUS      current
            DESCRIPTION
                "An entry in the table, containing information 
                 of PoE of one network port."
            INDEX       { flWorkNetPortPoEIndex }
        ::= { flWorkNetPortPoETable 1 }
    
     FlWorkNetPortPoEEntry
        ::= SEQUENCE {
        flWorkNetPortPoEIndex
            Integer32,
        flWorkNetPortPoEPowerEnable
            INTEGER,
        flWorkNetPortPoECurrentLimitation
            INTEGER,
        flWorkNetPortPoEDeviceClass
            INTEGER,
        flWorkNetPortPoEOutputCurrent
            Integer32,
        flWorkNetPortPoEOutputVoltage
            Integer32,
        flWorkNetPortPoEFaultStatus
            INTEGER,
        flWorkNetPortPoeFaultMonitoring
            INTEGER
        }
        
      flWorkNetPortPoEIndex
        OBJECT-TYPE
            SYNTAX      Integer32 (1..1024)
            MAX-ACCESS  read-only
            STATUS      current
            DESCRIPTION
                "This object identifies the port. This value
                 is never greater then flWorkNetPortCapacity."
        ::= { flWorkNetPortPoEEntry 1 }
        
      flWorkNetPortPoEPowerEnable
        OBJECT-TYPE
            SYNTAX      INTEGER {
                            enabled(1),
                            disabled(2),                           
                            unknown(3)
                            }
            MAX-ACCESS  read-write
            STATUS      current
            DESCRIPTION
                "Get back or set the current state of the PoE
                 device on this port.
                 enabled(1)  = power on this port is/should be enabled
                 disabled(2) = power on this port is/should be disabled
                 unknown(3)  = power state of this port is unknown
                               this value can not be set!"
        ::= { flWorkNetPortPoEEntry 2 }
        
      flWorkNetPortPoECurrentLimitation
        OBJECT-TYPE
            SYNTAX      INTEGER {
                            on(1),     
                            off(2),                              
                            unknown(3)
                            }
            MAX-ACCESS  read-write
            STATUS      current
            DESCRIPTION
                "Get back or set the current limitation state of the PoE
                 device on this port.
                 on(1)       = limits output current to 90mA if a class 1 device is connected
                 off(2)      = current is delivered up to general overcurrent protection value (350mA)
                 unknown(3)  = current limitation status on this port is unknown
                                          this value can not be set!"
        ::= { flWorkNetPortPoEEntry 3 }
       

     flWorkNetPortPoEDeviceClass
        OBJECT-TYPE
            SYNTAX      INTEGER {
                            class0(0),
                            class1(1),                          
                            class2(2),
                            class3(3),
                            class4(4),
                            unknown(5)
                            }
            MAX-ACCESS  read-only
            STATUS      current
            DESCRIPTION
                "Get back the device class type of the device connected to 
                 this port or recently connected to this port.
                 class0(0)
                 class1(1)
                 class2(2)
                 class3(3)
                 class4(4)
                 Device class unknown(5)"       
        ::= { flWorkNetPortPoEEntry 4 } 
        
    flWorkNetPortPoEOutputCurrent
        OBJECT-TYPE
            SYNTAX      Integer32 (1..400)
            MAX-ACCESS  read-only
            STATUS      current
            DESCRIPTION
                "Get back output current in mA actually delivered on this port"                      
        ::= { flWorkNetPortPoEEntry 5 } 
        
    flWorkNetPortPoEOutputVoltage
        OBJECT-TYPE
            SYNTAX      Integer32 (45000..56000)
            MAX-ACCESS  read-only
            STATUS      current
            DESCRIPTION
                "Get back output voltage in mV actually delivered on this port"                      
        ::= { flWorkNetPortPoEEntry 6 }
        
    flWorkNetPortPoEFaultStatus
        OBJECT-TYPE
            SYNTAX      INTEGER {
                            noFault(0),
                            voltage(1),                          
                            thermal(2),
                            overload(3),
                            loadDisconnected(4),
                            powerSupplyMissing(5),
                            noPse(6),
                            noPoeSupport(7),
                            noPoeDeviceConnected(8)
                            }
            MAX-ACCESS  read-only
            STATUS      current
            DESCRIPTION
                "Get back the fault status of the PoE device on this port
                 noFault(0)              = no fault status detected at all
                 voltage(1)              = external supply voltage fault 
                 thermal(2)              = over temperature
                 overload(3)             = overload (current limitation active?)
                 loadDisconnected(4)     = load has been disconnected  
                 powerSupplyMissing(5)   = PoE controller not responding. 48V supply missing?
                 noPse(6)                = No PSE interface module has been plugged on this port
                 noPoeSupport(7)         = Switch device does not support PoE devices e.g. because of 
                                           unsufficient hardware revision. 
                 noPoeDeviceConnected(8) = No PoE enabled powered device has been externally 
                                           connected to this PoE port"
                                                                    
        ::= { flWorkNetPortPoEEntry 7 }
           

    flWorkNetPortPoeFaultMonitoring
        OBJECT-TYPE
            SYNTAX      INTEGER {
                            disable(1),
                            enable(2)                            
                            }
            MAX-ACCESS  read-write
            STATUS      current
            DESCRIPTION
                "This object can be set to 'enable' if the user wants any error 
                 concerning an PoE module on this port to be monitored. If errors
                 are monitored and if any malfunctions concerning PoE are detected on 
                 this port they will cause the display of the device to show
                 an error code and will cause the alarm contact to open
                 if the contact is configured that way (see MIB-group flWorkFWCtrlAlarmContactEvents).
                 
                 disable(1)         = errors are not monitored
                 enable(2)          = errors are monitored " 
                 
            DEFVAL  {disable}                                                                    
            
        ::= { flWorkNetPortPoEEntry 8 }



    --
    --
    -- flWorkNetPofScrjIfGroup
    --
       
    flWorkNetPortPofScrjIfTable
        OBJECT-TYPE
            SYNTAX      SEQUENCE OF FlWorkNetPortPofScrjIfEntry
            MAX-ACCESS  not-accessible
            STATUS      current
            DESCRIPTION
                "Table of POF SCRJ port properties."
        ::= { flWorkNetPort 4 }
        
    flWorkNetPortPofScrjIfEntry
        OBJECT-TYPE
            SYNTAX      FlWorkNetPortPofScrjIfEntry
            MAX-ACCESS  not-accessible
            STATUS      current
            DESCRIPTION
                "An entry in the table, containing information 
                 about one POF SCRJ port."
            INDEX       { flWorkNetPortPofScrjIfIndex }
        ::= { flWorkNetPortPofScrjIfTable 1 }
    
    FlWorkNetPortPofScrjIfEntry
        ::= SEQUENCE {               
        flWorkNetPortPofScrjIfIndex  
            Integer32,
        flWorkNetPortPofScrjIfStatus
            INTEGER,
        flWorkNetPortPofScrjIfSupplyVoltage
            Integer32,
        flWorkNetPortPofScrjIfTxPower
            Integer32,
        flWorkNetPortPofScrjIfRxPower 
            Integer32,
        flWorkNetPortPofScrjIfSystemReserve
            Integer32,
        flWorkNetPortPofScrjIfRxPowerHighAlarm
            INTEGER,
        flWorkNetPortPofScrjIfRxPowerLowAlarm
            INTEGER,
        flWorkNetPortPofScrjIfRxPowerHighWarning
            INTEGER,
        flWorkNetPortPofScrjIfRxPowerLowWarning
            INTEGER,
        flWorkNetPortPofScrjIfManufacturer
            OCTET STRING,
        flWorkNetPortPofScrjIfManufactOui
            OCTET STRING,
        flWorkNetPortPofScrjIfRevision
            OCTET STRING,
        flWorkNetPortPofScrjIfWavelength
            Integer32,
        flWorkNetPortPofScrjIfTransceiverOptions
            Integer32,
        flWorkNetPortPofScrjIfSerialNumber
            OCTET STRING,
        flWorkNetPortPofScrjIfDatecodeAndLot
            OCTET STRING,
        flWorkNetPortPofScrjIfAlarmContactEnable
            INTEGER          
        }
        
    flWorkNetPortPofScrjIfIndex
        OBJECT-TYPE
            SYNTAX      Integer32 (1..1024)
            MAX-ACCESS  read-only
            STATUS      current
            DESCRIPTION
                "This object identifies the port. This value
                 is never greater then flWorkNetPortCapacity."
        ::= { flWorkNetPortPofScrjIfEntry 1 }
        
    flWorkNetPortPofScrjIfStatus 
        OBJECT-TYPE
            SYNTAX      INTEGER {
                            notSupported(1),
                            noModule(2),
                            ok(3),
                            systemReserveLow(4),
                            systemReserveExhausted(5)
                            }
            MAX-ACCESS  read-only
            STATUS      current
            DESCRIPTION
                "This delivers the current status of the POF SCRJ interface
                 on the selected port. Meanings are:
                 notSupported(1)           = The actual hw does not support POF SCRJ interface diagnostics.
                                             Plugged modules will transmit and receive data but the user will
                                             not be able to read out any diagnostic data.
                 noModule(2)               = No POF SCRJ hardware on this port.                           
                 ok(3),                    = An POF SCRJ hardware is present, rx power is ok. 
                 systemReserveLow(4),      = An POF SCRJ hardware is present, link is ok but rx light power is low.
                                             Data transmission is endangered if light power decreases.  (System reserver < 2 dB)
                 systemReserveExhausted(5) = An POF SCRJ hardware is present, link is ok but rx light power is very low.
                                             Data transmission is most probably not possible any more. (Rx power low)"
        ::= { flWorkNetPortPofScrjIfEntry 2 }       

    flWorkNetPortPofScrjIfSupplyVoltage
        OBJECT-TYPE
            SYNTAX      Integer32(0..65)
            MAX-ACCESS  read-only
            STATUS      current
            DESCRIPTION
                "Delivers the actual supply voltage of the
                 transceiver device on the given port
                 in 0.1 Volt. (i.e. range is von 0 to 6,5V)"       
        ::= { flWorkNetPortPofScrjIfEntry 4 } 
        
    flWorkNetPortPofScrjIfTxPower   
        OBJECT-TYPE
            SYNTAX      Integer32 (1..6553)
            MAX-ACCESS  read-only
            STATUS      current
            DESCRIPTION
                "Delivers the actual transmission power of the
                 transceiver device on the given port
                 in 0.1uW. (i.e. range is von 0 to 0,006553 W)"                      
        ::= { flWorkNetPortPofScrjIfEntry 6 } 
        
    flWorkNetPortPofScrjIfRxPower    
        OBJECT-TYPE
            SYNTAX      Integer32 (0..6553)
            MAX-ACCESS  read-only
            STATUS      current
            DESCRIPTION
                "Delivers the actual reception power of the
                 transceiver device on the given port
                 in 0.1uW. (i.e. range is von 0 to 0,006553 W)"                      
        ::= { flWorkNetPortPofScrjIfEntry 7 }
        
    flWorkNetPortPofScrjIfSystemReserve   
        OBJECT-TYPE                                             
            SYNTAX      Integer32 (0..255)
            MAX-ACCESS  read-only
            STATUS      current
            DESCRIPTION
                "Delivers the remaining system reserve in units of 0.1dB"                                                                   
        ::= { flWorkNetPortPofScrjIfEntry 8 }
        

     flWorkNetPortPofScrjIfRxPowerHighAlarm 
        OBJECT-TYPE
            SYNTAX      INTEGER {
                            notPresent(1),
                            present(2)                            
                            }
            MAX-ACCESS  read-only
            STATUS      current
            DESCRIPTION
                "Deliverst if the Rx power high alarm for a given port is
                 set (present(2)) or not set (notPresent(1))"
        ::= { flWorkNetPortPofScrjIfEntry 9 }

    flWorkNetPortPofScrjIfRxPowerLowAlarm
        OBJECT-TYPE
            SYNTAX      INTEGER {
                            notPresent(1),
                            present(2)                            
                            }
            MAX-ACCESS  read-only
            STATUS      current
            DESCRIPTION
                "Deliverst if the Rx power low alarm for a given port is
                 set (present(2)) or not set (notPresent(1))"
        ::= { flWorkNetPortPofScrjIfEntry 10 }
        
    flWorkNetPortPofScrjIfRxPowerHighWarning
        OBJECT-TYPE
            SYNTAX      INTEGER {
                            notPresent(1),
                            present(2)                            
                            }
            MAX-ACCESS  read-only
            STATUS      current
            DESCRIPTION
                "Deliverst if the Rx power high warning for a given port is
                 set (present(2)) or not set (notPresent(1))"
        ::= { flWorkNetPortPofScrjIfEntry 11 }
        
    flWorkNetPortPofScrjIfRxPowerLowWarning
        OBJECT-TYPE
            SYNTAX      INTEGER {
                            notPresent(1),
                            present(2)                            
                            }
            MAX-ACCESS  read-only
            STATUS      current
            DESCRIPTION
                "Delivers if the Rx power low warning for a given port is
                 set (present(2)) or not set (notPresent(1))"
        ::= { flWorkNetPortPofScrjIfEntry 12 }
        
    flWorkNetPortPofScrjIfManufacturer
        OBJECT-TYPE
            SYNTAX      OCTET STRING 
            MAX-ACCESS  read-only
            STATUS      current
            DESCRIPTION
                "Delivers the name of the manufacturer that
                 did produce the POF SCRJ transceiver device
                 on the given port"
        ::= { flWorkNetPortPofScrjIfEntry 13 }
        
    flWorkNetPortPofScrjIfManufactOui
        OBJECT-TYPE
            SYNTAX      OCTET STRING 
            MAX-ACCESS  read-only
            STATUS      current
            DESCRIPTION
                "Delivers the IEEE manufacturer ID of the
                 manufacturer that did produce the POF SCRJ 
                 transceiver device on the given port"
        ::= { flWorkNetPortPofScrjIfEntry 14 }

    flWorkNetPortPofScrjIfRevision
        OBJECT-TYPE
            SYNTAX      OCTET STRING 
            MAX-ACCESS  read-only
            STATUS      current
            DESCRIPTION
                "Delivers the revision of the POF SCRJ 
                 transceiver device on the given port"
        ::= { flWorkNetPortPofScrjIfEntry 16 }
        

    flWorkNetPortPofScrjIfWavelength
        OBJECT-TYPE
            SYNTAX      Integer32 
            MAX-ACCESS  read-only
            STATUS      current
            DESCRIPTION
                "Delivers the wavelength in units of nm the POF SCRJ 
                 transceiver device on the given port is using for signal
                 generation"
        ::= { flWorkNetPortPofScrjIfEntry 17 }
        
    flWorkNetPortPofScrjIfTransceiverOptions
        OBJECT-TYPE
            SYNTAX      Integer32 
            MAX-ACCESS  read-only
            STATUS      current
            DESCRIPTION
                "Gives detailed informations about the 
                 implemented features of th POF SCRJ transceiver 
                 on the given port.
                 You have to take a look at the binary representation
                 of the returned number. Bits are counted from 0 (LSB)
                 to 31 (MSB).
                 Bit 1 set means: RX_LOS implemented 
                 Bit 3 set means: TX_FAULT implemented
                 Bit 4 set means: TX_DISABLE implemented
                 Bit 5 set means: RATE_SELECT implemented"
        ::= { flWorkNetPortPofScrjIfEntry 18 }
        
    flWorkNetPortPofScrjIfSerialNumber
        OBJECT-TYPE
            SYNTAX      OCTET STRING 
            MAX-ACCESS  read-only
            STATUS      current
            DESCRIPTION
                "Delivers the serial number of the POF SCRJ 
                 transceiver device on the given port"
        ::= { flWorkNetPortPofScrjIfEntry 19 }
        
    flWorkNetPortPofScrjIfDatecodeAndLot
        OBJECT-TYPE
            SYNTAX      OCTET STRING 
            MAX-ACCESS  read-only
            STATUS      current
            DESCRIPTION
                "Delivers the manufacturing date an lot number of 
                the POF SCRJ transceiver on the given port.
                BYTE 1 + 2: Year
                BYTE 3 + 4: MONTH
                BYTE 5 + 6: DAY
                BYTE 7 + 8: LOT Number"
        ::= { flWorkNetPortPofScrjIfEntry 20 }   
        
    flWorkNetPortPofScrjIfAlarmContactEnable
        OBJECT-TYPE
            SYNTAX      INTEGER {
                                disable(1),                                
                                enable(2)
                                }
 
            MAX-ACCESS  read-write
            STATUS      current
            DESCRIPTION
                "If this object is switched to enable
                 the alarm contact will open if this
                 POF SCRJ transceiver reaches a critical
                 RX power state.
                 See object 
                 flWorkFWCtrlAlarmContactEventPoFScrjTransCritical 
                 for global enabling and disabling of alarm contact 
                 actions for this sort of event."
        ::= { flWorkNetPortPofScrjIfEntry 21 }        
                                     

   -- 
   -- 
   -- SFP Table
   --

    flWorkNetSFPModuleTable
        OBJECT-TYPE
            SYNTAX      SEQUENCE OF FlWorkNetSFPModuleEntry
            MAX-ACCESS  not-accessible
            STATUS      current
            DESCRIPTION
                "Table of available sfp modules."
        ::= { flWorkNetPort 5 }

    flWorkNetSFPModuleEntry
        OBJECT-TYPE
            SYNTAX      FlWorkNetSFPModuleEntry
            MAX-ACCESS  not-accessible
            STATUS      current
            DESCRIPTION
                "An entry in the table, containing information 
                 of one sfp module."
            INDEX       { flWorkNetSFPModuleIndex }
        ::= { flWorkNetSFPModuleTable 1 }

    FlWorkNetSFPModuleEntry
        ::= SEQUENCE {
            flWorkNetSFPModuleIndex
                Integer32,
            flWorkNetSFPModuleType
                INTEGER,
            flWorkNetSFPModuleMedia
                INTEGER,
            flWorkNetSFPModuleVendor
                DisplayString,
            flWorkNetSFPModulePartNo
                DisplayString,
            flWorkNetSFPModuleSerialNo
                DisplayString,
            flWorkNetSFPModuleRev
                DisplayString,
            flWorkNetSFPModuleLinkLength
                Integer32,       
            flWorkNetSFPModuleBitrate
                Integer32,
            flWorkNetSFPModuleTransceiverCode
                DisplayString,
            flWorkNetSFPModuleEncoding
                INTEGER,     
            flWorkNetSFPPortTxPower
                Integer32,
            flWorkNetSFPPortRxPower
                Integer32                           
       }

    flWorkNetSFPModuleIndex
        OBJECT-TYPE
            SYNTAX      Integer32 (1..1024)
            MAX-ACCESS  read-only
            STATUS      current
            DESCRIPTION
                "This object identifies the sfp slot. This value
                 is never greater then flWorkNetPortCapacity."
        ::= { flWorkNetSFPModuleEntry 1 }

    flWorkNetSFPModuleType
        OBJECT-TYPE
            SYNTAX      INTEGER {
                            unknown(1),
                            eth-1000BASE-SX(2),
                            eth-1000BASE-LX(3),
                            eth-1000BASE-LH(4),
                            eth-1000BASE-CX(5),
                            eth-1000BASE-T(6)
                            }
            MAX-ACCESS  read-only
            STATUS      current
            DESCRIPTION
               "This object identifies the gigabit ethernet 
                compliance type."
        ::= { flWorkNetSFPModuleEntry 2 }

    flWorkNetSFPModuleMedia
        OBJECT-TYPE
            SYNTAX      INTEGER {
                            unknown(1),
                            single-Mode(2),
                            multi-Mode(3),
                            multi-Mode-50um(4),
                            multi-Mode-62um(5),
                            twisted-Pair(6)
                            }
            MAX-ACCESS  read-only
            STATUS      current
            DESCRIPTION
               "This object identifies the media type which 
                should be used with this module. Multi-mode types
                can be differed by the core diameter 50um or 62,5 um.
                Some modules support both of them."
        ::= { flWorkNetSFPModuleEntry 3 } 
        
   flWorkNetSFPModuleVendor
        OBJECT-TYPE
            SYNTAX      DisplayString
            MAX-ACCESS  read-only
            STATUS      current
            DESCRIPTION
                "This object represent the vendor name string."
        ::= { flWorkNetSFPModuleEntry 4 }

   flWorkNetSFPModulePartNo
        OBJECT-TYPE
            SYNTAX      DisplayString
            MAX-ACCESS  read-only
            STATUS      current
            DESCRIPTION
                "This object represent the part number of this kind 
                  of module."
        ::= { flWorkNetSFPModuleEntry 5 }

   flWorkNetSFPModuleSerialNo
        OBJECT-TYPE
            SYNTAX      DisplayString
            MAX-ACCESS  read-only
            STATUS      current
            DESCRIPTION
                "This object represent the serial number."
        ::= { flWorkNetSFPModuleEntry 6 }

   flWorkNetSFPModuleRev
        OBJECT-TYPE
            SYNTAX      DisplayString
            MAX-ACCESS  read-only
            STATUS      current
            DESCRIPTION
                "This object represent the revision string."
        ::= { flWorkNetSFPModuleEntry 7 }

   flWorkNetSFPModuleLinkLength
        OBJECT-TYPE
            SYNTAX      Integer32 
            MAX-ACCESS  read-only
            STATUS      current
            DESCRIPTION
               "This object represents the link length in meter
                which is supported by this module."
        ::= { flWorkNetSFPModuleEntry 8 }

   flWorkNetSFPModuleBitrate
        OBJECT-TYPE
            SYNTAX      Integer32 
            MAX-ACCESS  read-only
            STATUS      current
            DESCRIPTION
               "This object represents the nominal bitrate
                in units of 100MBit/s."
        ::= { flWorkNetSFPModuleEntry 9 }

   flWorkNetSFPModuleTransceiverCode
        OBJECT-TYPE
            SYNTAX      DisplayString
            MAX-ACCESS  read-only
            STATUS      current
            DESCRIPTION
               "This object returns the unchanged transceiver
                identify code of the SFP module."
        ::= { flWorkNetSFPModuleEntry 10 }

   flWorkNetSFPModuleEncoding
        OBJECT-TYPE
            SYNTAX      INTEGER {
                            unknown(1),
                            cod-8B10B(2),
                            cod-4B5B(3),
                            cod-NRZ(4),
                            cod-Manchester(5)
                            }
            MAX-ACCESS  read-only
            STATUS      current
            DESCRIPTION
               "This object represents the encoding mechanism used
                by this module."
        ::= { flWorkNetSFPModuleEntry 11 }

   flWorkNetSFPPortTxPower
        OBJECT-TYPE
            SYNTAX      Integer32 
            MAX-ACCESS  read-only
            STATUS      current
            DESCRIPTION
               "This object represents the current optical power
               of the Transmitter unit in increments of 0,1dBm."
        ::= { flWorkNetSFPModuleEntry 12 }

   flWorkNetSFPPortRxPower
        OBJECT-TYPE
            SYNTAX      Integer32 
            MAX-ACCESS  read-only
            STATUS      current
            DESCRIPTION
               "This object represents the current received optical 
                power in increments of 0,1dBm."
        ::= { flWorkNetSFPModuleEntry 13 }
      
      --
    --
    -- flWorkNetIfList Group
    --
    flWorkNetIfTable
        OBJECT-TYPE
            SYNTAX      SEQUENCE OF FlWorkNetIfEntry
            MAX-ACCESS  not-accessible
            STATUS      current
            DESCRIPTION
                "Table of descriptive information about the available
                 components of the product group Factory Line, which
                 can be used together with this administrable component."
        ::= { flWorkNetIfList 1 }

    flWorkNetIfEntry
        OBJECT-TYPE
            SYNTAX      FlWorkNetIfEntry
            MAX-ACCESS  not-accessible
            STATUS      current
            DESCRIPTION
                "An entry in the table, containing information about a
                 single component (product) from Factory Line."
            INDEX       { flComponentsIndex }
        ::= { flWorkNetIfTable 1 }

    FlWorkNetIfEntry
        ::= SEQUENCE {
            flWorkNetIfPhyAddress
                MacAddress,
            flWorkNetIfIpAddress
                IpAddress,
            flWorkNetIfSubnetmask
                IpAddress,
            flWorkNetIfGwIpAddress
                IpAddress,
            flWorkNetIfStatus
                INTEGER,
            flWorkNetIfSave
                INTEGER,
            flWorkNetIfAssignment
                INTEGER,
            flWorkNetIfManagementVlanId
                Integer32
        }


    flWorkNetIfPhyAddress
        OBJECT-TYPE
            SYNTAX      MacAddress
            MAX-ACCESS  read-only
            STATUS      current
            DESCRIPTION
               "The interface's address at the protocol layer
                immediately `below' the network layer in the
                protocol stack."
        ::= { flWorkNetIfEntry 1 }

    flWorkNetIfIpAddress
        OBJECT-TYPE
            SYNTAX      IpAddress
            MAX-ACCESS  read-write
            STATUS      current
            DESCRIPTION
               "The ip address of this device.
                Changing this object will take effect
                after setting the object flWorkNetIfParamSave
                to apply(2).
                Note: For some products a reboot is required instead of the 
                      flWorkNetIfParamSave object, to load the
                      new Ip-Parameter settings."
        ::= { flWorkNetIfEntry 2 }
    
    flWorkNetIfSubnetmask
        OBJECT-TYPE
            SYNTAX      IpAddress
            MAX-ACCESS  read-write
            STATUS      current
            DESCRIPTION
               "The subnet mask associated with the IP address of
                this entry.  The value of the mask is an IP
                address with all the network bits set to 1 and all
                the hosts bits set to 0.
                Changing this object will take effect
                after setting the object flWorkNetIfParamSave
                to apply(2).
                Note: For some products a reboot is required instead of the 
                      flWorkNetIfParamSave object, to load the
                      new Ip-Parameter settings."
        ::= { flWorkNetIfEntry 3 }
        
    flWorkNetIfGwIpAddress
        OBJECT-TYPE
            SYNTAX      IpAddress
            MAX-ACCESS  read-write
            STATUS      current
            DESCRIPTION
               "IP address of the default gateway.
                Changing this object will take effect
                after setting the object flWorkNetIfParamSave
                to appFor some products a reboot is required instead of the 
                      flWorkNetIfParamSave object, to load the
                      new Ip-Parameter settings."
        ::= { flWorkNetIfEntry 4 }
    

    flWorkNetIfStatus
        OBJECT-TYPE
            SYNTAX      INTEGER {
                            notModified(1),
                            modified(2)
                            }
            MAX-ACCESS  read-only
            STATUS      current
            DESCRIPTION
                "This object is used to synchronize the modification of the IP
                parameters used by the protocol stack based on the 
                flWorkNetIfParameter MIB objects. 
                If flWorkNetIfParamStatus returns notModified(1), no modifications 
                were made to flWorkNetIfParamIpAddress, flWorkNetIfParamSubnetmask 
                and flWorkNetIfParamGwIpAddress. If flWorkNetIfParamStatus returns 
                modified(2), one or more objects were changed, but have not been 
                applied."
        ::= { flWorkNetIfEntry 5 }

    flWorkNetIfSave
        OBJECT-TYPE
            SYNTAX      INTEGER {
                            restore(1),
                            apply(2)
                            }
            MAX-ACCESS  read-write
            STATUS      current
            DESCRIPTION
                "This object is used to save the modification of the IP
                parameters used by the protocol stack based on the flWorkNetIfParameter
                MIB objects. This allows the user to change flWorkNetIfParamIpAddress, 
                flWorkNetIfParamSubnetmask and flWorkNetIfParamGwIpAddress and then 
                apply the changes to the unit using apply(2).
                If one or more of the flWorkNetIfParameter objects were modified, 
                the user can restore the parameters to a mirror of the NVM values 
                using restore(1).
                Note: You can apply(2) to modified ip parameter only if the object
                      flWorkNetIfParamAssignment has been set to static(1)!
                      Otherwise you get an snmp response indicating an error."
            DEFVAL  {restore}
        ::= { flWorkNetIfEntry 6 }

    flWorkNetIfAssignment
        OBJECT-TYPE
            SYNTAX      INTEGER {
                            static(1),                            
                            bootp(2),
                            dhcp(3),
                            dcp(4)
                        }
            MAX-ACCESS  read-write
            STATUS      current
            DESCRIPTION
                "Kind of the IP address assignment.

                 Setting the kind of assignment to bootp(2) 
                 or dcp(4) become effective after a restart
                 of the device."
            DEFVAL  {bootp}
        ::= { flWorkNetIfEntry 7 }

    flWorkNetIfManagementVlanId
        OBJECT-TYPE
            SYNTAX      Integer32 (1..4094)
            MAX-ACCESS  read-write
            STATUS      current
            DESCRIPTION
                "Vlan ID of the management agent in the case the device
                 is running in mode VLAN Tagging."
            DEFVAL  {1}
        ::= { flWorkNetIfEntry 8 }

  
    --
    -- flWorkNetACD Group
    --	
	
	flWorkNetACDStatus
        OBJECT-TYPE
            SYNTAX      INTEGER {
                            unknown(1),
                            noConflict(2),
							conflictDetected(3)
                            }
            MAX-ACCESS  read-only
            STATUS      current
            DESCRIPTION
                "Status of the detection mechanism."
        ::= { flWorkNetACD 1 }
		
	flWorkNetACDIP 
        OBJECT-TYPE
            SYNTAX      IpAddress
            MAX-ACCESS  read-only
            STATUS      current
            DESCRIPTION
               "IP address of the last detected conflict."
        ::= {flWorkNetACD 2 }
		
	flWorkNetACDMAC 
        OBJECT-TYPE
            SYNTAX      MacAddress
            MAX-ACCESS  read-only
            STATUS      current
            DESCRIPTION
               "MAC address of the last detected conflict."
		::= { flWorkNetACD 3 }		
		


    --
    --
    -- flWorkFWCtrlPasswd Group
    --
    flWorkFWCtrlPasswdSet
        OBJECT-TYPE
            SYNTAX      OCTET STRING (SIZE(16..128))
            MAX-ACCESS  read-write
            STATUS      current
            DESCRIPTION
                "This write only object changes the current
                 password to a given new password. The character
                 mask is defined as below:

                    1.) The password length is min. 8 and max. 64 characters.
                    2.) All ASCII codes allowd (except code 0x00).
                    3.) For redundancy check the password is giving
                        twice as shown below:
                        
                            password:                   nimbus3
                            
                            octetstr = 2 x password:    nimbus3nimbus3
                            
                    4.) As an result of this the absolut length of
                        octet string is even and min. 16 and max. 128 characters.
                        
                 The firmware will always return a string of five
                 asterics (*****) when this object is reading.
                 NOTE: If the device supports either SNMPv2c or SNMPv3,
                       this object will work in SNMPv2c mode only since
                       SNMPv3 provides own objects for user management."
            DEFVAL  {"private"}
        ::= { flWorkFWCtrlPasswd 1 }

    flWorkFWCtrlPasswdSuccess
        OBJECT-TYPE
            SYNTAX      INTEGER {
                            notChanged(1),
                            notSuccessful(2),
                            successful(3)
                        }
            MAX-ACCESS  read-only
            STATUS      current
            DESCRIPTION
                "The firmware will always return the last access
                 result to the object flWorkFWCtrlPasswdSet.

                 In case of new system startup without any try of
                 manipulations onto flWorkFWCtrlPasswdSet the object
                 always bring back notChanged(1) state.

                 Every write access to flWorkFWCtrlPasswdSet or rather
                 the setting of new password over the web interface which
                 was not successful lead to noTSuccessful(2) state. Every
                 successful write access lead to successful(3) state.

                 The states notSuccessful(2) and successful(3) are hold
                 up for ten minutes from the time of the last change.
                 After this the state notChanged(1) is adjusted."
        ::= { flWorkFWCtrlPasswd 2 }

    flWorkFWCtrlLoginExpire OBJECT-TYPE
        SYNTAX Integer32 (30..3600)
        MAX-ACCESS read-write
        STATUS current
        DESCRIPTION
            "When the user configures the device using the web interface
             it is necessary to enter the password. After the first
             authentication the user is registered for the log in expiring
             time and it is not necessary to enter the password again.
             After the expiration of the login expiring time the user will
             be invite to enter the password again.
             The login expiring time can be chosen in the range from 30 up
             to 3600 seconds. The value of zero disables the automatically
             login.
             The granularity of this timer is 1 second."
        DEFVAL  {1200}
        ::= { flWorkFWCtrlPasswd 3 }


    --
    --
    -- flWorkFWCtrlUpdate Group
    --

    flWorkFWCtrlTftpIPAddr
        OBJECT-TYPE
            SYNTAX      IpAddress
            MAX-ACCESS  read-write
            STATUS      current
            DESCRIPTION
                "Write to this object sets the IP address for
                 the TFTP server needed by the update process."
    --      DEFVAL  {0}
        ::= { flWorkFWCtrlUpdate 2 }

    flWorkFWCtrlTftpFile
        OBJECT-TYPE
            SYNTAX      OCTET STRING (SIZE(0..64))
            MAX-ACCESS  read-write
            STATUS      current
            DESCRIPTION
                "Write to this object sets the file name on
                 the TFTP server needed by the update process."
            DEFVAL  {""}
        ::= { flWorkFWCtrlUpdate 3 }

    flWorkFWCtrlUpdateStatus
        OBJECT-TYPE
            SYNTAX      INTEGER {
                                updateOk(1),
                                updateFault(2),
                                noUpdate(3),
                                unknown(4)
                        }
            MAX-ACCESS  read-only
            STATUS      current
            DESCRIPTION
                "Information about the update process before
                 the last restart of the device."
        ::= { flWorkFWCtrlUpdate 4 }

    flWorkFWCtrlUpdateExecute
        OBJECT-TYPE
            SYNTAX      INTEGER {
                            noFwUpdate(1),
                            startFwUpdate(2)
                        }
            MAX-ACCESS  read-write
            STATUS      current
            DESCRIPTION
                "Setting this object to startFwUpdate(2) causes a
                 tftp download to update the current firmware.
                 The object flWorkFWCtrlRunningUpdate gives 
                 additional information about the update process.
                 When the update will be finished ( see 
                 flWorkFWCtrlRunningUpdate), you have to restart 
                 the device ( see flWorkFWCtrlReset ).
                                  
                 Setting this object to noFwUpdate(1) has no effect."
            DEFVAL  {noFwUpdate}
        ::= { flWorkFWCtrlUpdate 5 }
    
    flWorkFWCtrlRunningUpdate 
        OBJECT-TYPE
            SYNTAX INTEGER {
               notStarted(1),       -- download has not yet started
               inProgress(2),       -- download has not yet finished
               success(3),          -- download has finished successfully
               errorConnection(4),  -- download cannot connect
               errorFilename(5),    -- download has bad image path/filename
               errorFault(6),       -- download has fault condition on device
               errorParameter(7)    -- download has wrong tftp parameter
            }
            MAX-ACCESS read-only 
            STATUS current
            DESCRIPTION
                "Provides status on the running tftp file download progress."
        ::= { flWorkFWCtrlUpdate 6 }
 
    flWorkFWCtrlAutoUpdate
        OBJECT-TYPE
            SYNTAX      INTEGER {
                            noAutoFwUpdate(1),
                            startAutoFwUpdate(2)
                        }
            MAX-ACCESS  read-write
            STATUS      current
            DESCRIPTION
                "Setting this object to startAutoFwUpdate(2) causes a
                 tftp download to update the current firmware.
                 When the update will be finished, the device initiates 
                 a restart.                                  
                 Setting this object to noAutoFwUpdate(1) has no effect."
            DEFVAL  {noAutoFwUpdate}
        ::= { flWorkFWCtrlUpdate 7 }

    flWorkFWCtrlTftpImage                 -- KSP!!!
    	OBJECT-TYPE
    		SYNTAX 	  INTEGER {
    							image1(1),
    							image2(2)
    						  }
    	    MAX-ACCESS read-write
    	    STATUS 	   current
    	    DESCRIPTION
    	        " This object sets the image that should be updated.
    	          
    	          If there are 2 different images available on the device, the
                  one which should be updated (overwritten) is specified by this
                  object. If the updated image is faulty then the backup image 
                  starts operation."     	    
    ::= { flWorkFWCtrlUpdate 8 }
  
  
    --*** switchimage starts ***
    --**************************************************************************************
    -- flWorkFWCtrlImageConfig
    --
    --**************************************************************************************

    

    flWorkFWCtrlImage1  OBJECT-TYPE
         SYNTAX      DisplayString (SIZE(1..32))
         MAX-ACCESS  read-only
         STATUS      current
         DESCRIPTION
                     "The image1 softwate version ."
         ::= { flWorkFWCtrlImage 1 }
    flWorkFWCtrlImage2   OBJECT-TYPE
         SYNTAX      DisplayString (SIZE(1..32))
         MAX-ACCESS  read-only
         STATUS      current
         DESCRIPTION
                     "The image2 software version."
         ::= { flWorkFWCtrlImage 2 }

    flWorkFWCtrlActiveImage OBJECT-TYPE
         SYNTAX      DisplayString (SIZE(1..32))
         MAX-ACCESS  read-only
         STATUS      current
         DESCRIPTION
                     "The active image name. image1 or image2.
                      "
         ::= { flWorkFWCtrlImage 3 }
   flWorkFWCtrlNextActiveImage OBJECT-TYPE
         SYNTAX      DisplayString (SIZE(1..32))
         MAX-ACCESS  read-write
         STATUS      current
         DESCRIPTION
                     "The next active image name.
                      This image is loaded when the system is reset
                      user assigns either image1 or image2. "
         ::= { flWorkFWCtrlImage 4 }   
         


    --**************************************************************************************
    -- flWorkFWCtrlUserConfigGroup
    --
    --**************************************************************************************

    


    flWorkFWCtrlUserConfigCreate OBJECT-TYPE
         SYNTAX      DisplayString (SIZE(1..8))
         MAX-ACCESS  read-write
         STATUS      current
         DESCRIPTION
                     "Create a new user.
                     When set with a non-empty string, a new user with that name will be created.
                     This object will only return an empty string.
                     This string is limited to alpha-numeric strings (uncluding the '-' and '_' characters)."
         ::= { flWorkFWCtrlUserConfigGroup 1 }

    --**************************************************************************************

    flWorkFWCtrlUserConfigTable OBJECT-TYPE
         SYNTAX      SEQUENCE OF FlWorkFWCtrlUserConfigEntry
         MAX-ACCESS  not-accessible
         STATUS      current
         DESCRIPTION
                     "User Config Table"
         ::= { flWorkFWCtrlUserConfigGroup 2 }

    flWorkFWCtrlUserConfigEntry OBJECT-TYPE
         SYNTAX      FlWorkFWCtrlUserConfigEntry
         MAX-ACCESS  not-accessible
         STATUS      current
         DESCRIPTION
                     "User Config Entry"
         INDEX { flWorkFWCtrlUserIndex }
         ::= { flWorkFWCtrlUserConfigTable 1 }

    FlWorkFWCtrlUserConfigEntry ::= SEQUENCE {
                 flWorkFWCtrlUserIndex
                     Integer32,
                 flWorkFWCtrlUserName
                     DisplayString,
                 flWorkFWCtrlUserPassword
                     DisplayString,
                 flWorkFWCtrlUserAccessMode
                     INTEGER,
                 flWorkFWCtrlUserStatus
                     RowStatus,
                 flWorkFWCtrlUserAuthenticationType
                     INTEGER,
                 flWorkFWCtrlUserEncryptionType
                     INTEGER,
                 flWorkFWCtrlUserEncryptionPassword
                     DisplayString,
                 flWorkFWCtrlUserLockoutStatus
                     INTEGER,
                 flWorkFWCtrlUserPasswordExpireTime
                     DateAndTime
             }

    flWorkFWCtrlUserIndex OBJECT-TYPE
         SYNTAX      Integer32 (1..255)
         MAX-ACCESS  not-accessible
         STATUS      current
         DESCRIPTION
                     "Agent User Config Index"
         ::= { flWorkFWCtrlUserConfigEntry 1 }

    flWorkFWCtrlUserName OBJECT-TYPE
         SYNTAX      DisplayString (SIZE(1..8))
         MAX-ACCESS  read-write
         STATUS      current
         DESCRIPTION
                     "Agent User Name.
                     This string is limited to alpha-numeric strings (including the '-' and '_' characters)."
         ::= { flWorkFWCtrlUserConfigEntry 2 }

    flWorkFWCtrlUserPassword OBJECT-TYPE
         SYNTAX      DisplayString (SIZE(8..64))
         MAX-ACCESS  read-write
         STATUS      current
         DESCRIPTION
                     "Agent User Password
                     This object will return an empty string even if a password is set."
         ::= { flWorkFWCtrlUserConfigEntry 3 }

    flWorkFWCtrlUserAccessMode OBJECT-TYPE
         SYNTAX      INTEGER {
                     read(1),
                     write(2)
                  }
         MAX-ACCESS  read-only
         STATUS      current
         DESCRIPTION
                     "Agent User Access Mode"
         ::= { flWorkFWCtrlUserConfigEntry 4 }

    flWorkFWCtrlUserStatus OBJECT-TYPE
         SYNTAX      RowStatus
         MAX-ACCESS  read-write
         STATUS      current
         DESCRIPTION
                     "Agent User Status.
                     active(1)  - This user account is active.
                     destroy(6) - Set to this value to remove this user account."
         ::= { flWorkFWCtrlUserConfigEntry 5 }

    flWorkFWCtrlUserAuthenticationType OBJECT-TYPE
         SYNTAX      INTEGER {
                     none(1),
                     hmacmd5(2),
                     hmacsha(3)
                  }
         MAX-ACCESS  read-write
         STATUS      current
         DESCRIPTION
                     "SNMPv3 User Authentication.  The user passsword must be set
                     to a string greater than or equal to 8 characters for this to be
                     set to anything but none(1).

                     none(1)      - no authentication used
                     hmacmd5(1)   - Use HMAC-MD5 authentication
                     hmacsha(1)   - Use HMAC-SHA authentication"
         ::= { flWorkFWCtrlUserConfigEntry 6 }

    flWorkFWCtrlUserEncryptionType OBJECT-TYPE
         SYNTAX      INTEGER {
                     none(1),
                     des(2)
                  }
         MAX-ACCESS  read-write
         STATUS      current
         DESCRIPTION
                     "SNMPv3 User Encryption
                     Can not be set to des(2) if agentUserAuthenticationType is set to
                     none(1).

                     none(1) - no encryption used
                     des(2)  - DES encryption used"
         ::= { flWorkFWCtrlUserConfigEntry 7 }

    flWorkFWCtrlUserEncryptionPassword OBJECT-TYPE
         SYNTAX      DisplayString (SIZE(8..64))
         MAX-ACCESS  read-write
         STATUS      current
         DESCRIPTION
                     "SNMPv3 User Encryption Password
                     This object will return an empty string even if a password is
                     set. agentUserEncryptionType must be set to des(2) before this
                     object can be configured.
                     This object will return an empty string even if a password is set."
         ::= { flWorkFWCtrlUserConfigEntry 8 }

    flWorkFWCtrlUserLockoutStatus OBJECT-TYPE
         SYNTAX      INTEGER {
                     false(0),
                     true(1)
                     }
         MAX-ACCESS  read-only
         STATUS      current
         DESCRIPTION
                     "Displays whether the user account is locked due to excessive failed login attempts."
         ::= { flWorkFWCtrlUserConfigEntry 9 }

    flWorkFWCtrlUserPasswordExpireTime OBJECT-TYPE
         SYNTAX      DateAndTime
         MAX-ACCESS  read-only
         STATUS      current
         DESCRIPTION
                     "Date and time when the user's password expires (past or present).  Only valid when
                      password aging is enabled."
         ::= { flWorkFWCtrlUserConfigEntry 10 }   


    -- *************************************************************************************
    -- Digital input group
    -- flWorkFWCtrlDigitalInput
    -- *************************************************************************************

    flWorkFWCtrlDigitalInputTable
        OBJECT-TYPE
            SYNTAX      SEQUENCE OF FlWorkFWCtrlDigitalInputEntry
            MAX-ACCESS  not-accessible
            STATUS      current
            DESCRIPTION
                "Table to control digital inputs"
        ::= { flWorkFWCtrlDigitalInput 1 }
        
     flWorkFWCtrlDigitalInputEntry
        OBJECT-TYPE
            SYNTAX      FlWorkFWCtrlDigitalInputEntry
            MAX-ACCESS  not-accessible
            STATUS      current
            DESCRIPTION
                "An entry in the table, containing information 
                 of regarding digital inputs"
            INDEX       { flWorkFWCtrlDigitalInputIndex }
        ::= { flWorkFWCtrlDigitalInputTable 1 }
    
     FlWorkFWCtrlDigitalInputEntry
        ::= SEQUENCE {
        flWorkFWCtrlDigitalInputIndex
            Integer32,
        flWorkFWCtrlDigitalInputStatus
            INTEGER,
        flWorkFWCtrlDigitalInputEvents
            INTEGER
        }
        
      flWorkFWCtrlDigitalInputIndex
        OBJECT-TYPE
            SYNTAX      Integer32 (1..1024)
            MAX-ACCESS  read-only
            STATUS      current
            DESCRIPTION
                "This object identifies the digital input"
        ::= { flWorkFWCtrlDigitalInputEntry 1 }
        
      flWorkFWCtrlDigitalInputStatus
        OBJECT-TYPE
            SYNTAX      INTEGER {
                            on(1),
                            off(2),                           
                            unknown(3)
                            }
            MAX-ACCESS  read-only
            STATUS      current
            DESCRIPTION
                "Get back  the current state of a digital input.
                
                 on(1)          = signal present at input
                 off(2)         = signal not present at input
                 unknown(3)     = signal status is unkonwn"
        ::= { flWorkFWCtrlDigitalInputEntry 2 }
        
	flWorkFWCtrlDigitalInputEvents
		OBJECT-TYPE
			SYNTAX      INTEGER {
							none(0),
							wlan(1),
							roam(2)
							}
			MAX-ACCESS  read-only
			STATUS      current
			DESCRIPTION
			 "Configuration of digital input events.

			  none(0)   = no event configured
			  wlan(1)   = if the digital input changes from low to high the wlan interface is enabled
						  if the digital input changes from high to low the wlan interface is disabled
			  roam(2)   = if the digital input changes from low to high a wlan roaming process is initiated"
		::= { flWorkFWCtrlDigitalInputEntry 3 }        
        
        
        
    -- *************************************************************************************
    -- Energy Saving Group
    -- flWorkFWCtrlEnergy
    -- *************************************************************************************
      flWorkFWCtrlEnergyTest
        OBJECT-TYPE
            SYNTAX      INTEGER {
                            disable(1),
                            enable(2)
                        }  
            MAX-ACCESS  read-write
            STATUS      current
            DESCRIPTION
                "This object identifies the Energy Saving mode"
             DEFVAL  {disable}
        ::= { flWorkFWCtrlEnergy 1 }        

      flWorkEnergyPortTable
        OBJECT-TYPE
            SYNTAX      SEQUENCE OF FlWorkEnergyPortEntry
            MAX-ACCESS  not-accessible
            STATUS      current
            DESCRIPTION
                "Table of network ports."
        ::= { flWorkFWCtrlEnergy 2 }

      flWorkEnergyPortEntry
        OBJECT-TYPE
            SYNTAX      FlWorkEnergyPortEntry
            MAX-ACCESS  not-accessible
            STATUS      current
            DESCRIPTION
                "An entry in the table, containing information
                 about energy savig mode of one network port."
            INDEX       { flWorkEnergyPortIndex }
        ::= { flWorkEnergyPortTable 1 }

      FlWorkEnergyPortEntry
        ::= SEQUENCE {
            flWorkEnergyPortIndex
                Integer32,
            flWorkEnergyPortModus
                INTEGER
        }

      flWorkEnergyPortIndex
        OBJECT-TYPE
            SYNTAX      Integer32 (1..1024)
            MAX-ACCESS  read-only
            STATUS      current
            DESCRIPTION
                "This object identifies the port. This value
                 is never greater then flWorkNetPortCapacity."
        ::= { flWorkEnergyPortEntry 1 }
      
      flWorkEnergyPortModus
        OBJECT-TYPE
            SYNTAX      INTEGER {
                                   ignore(1),
                                switch-off(2),
                                 slow-down(3)
                                }
            MAX-ACCESS  read-write
            STATUS      current
            DESCRIPTION
                "The modus of this port defined by the user:
                        ignore(1) - Energy Saving settings are ignored for this port
                    switch-off(2) - Port is switched off if global Energy Saving mode is enabled
                     slow-down(3) - Portspeed is slowed down if global Energy Saving mode is enabled "                            

              DEFVAL  {ignore}
        ::= { flWorkEnergyPortEntry 2 }

    -- *************************************************************************************
    -- Digital output group
    -- flWorkFWCtrlDigitalOutput
    -- *************************************************************************************

    flWorkFWCtrlDigitalOutputTable
        OBJECT-TYPE
            SYNTAX      SEQUENCE OF FlWorkFWCtrlDigitalOutputEntry
            MAX-ACCESS  not-accessible
            STATUS      current
            DESCRIPTION
                "Table to control digital outputs"
        ::= { flWorkFWCtrlDigitalOutput 1 }

     flWorkFWCtrlDigitalOutputEntry
        OBJECT-TYPE
            SYNTAX      FlWorkFWCtrlDigitalOutputEntry
            MAX-ACCESS  not-accessible
            STATUS      current
            DESCRIPTION
                "An entry in the table, containing information
                 and settings regarding digital outputs"
            INDEX       { flWorkFWCtrlDigitalOutputIndex }
        ::= { flWorkFWCtrlDigitalOutputTable 1 }

     FlWorkFWCtrlDigitalOutputEntry
        ::= SEQUENCE {
        flWorkFWCtrlDigitalOutputIndex
            Integer32,
        flWorkFWCtrlDigitalOutputStatus
            INTEGER,
        flWorkFWCtrlDigitalOutputEnable
            INTEGER,
        flWorkFWCtrlDigitalOutputEventDigitalInState
            INTEGER,
	    flWorkFWCtrlDigitalOutputEventWlanState
	        INTEGER,
	    flWorkFWCtrlDigitalOutputEventWlanConnection
	        INTEGER
        }

      flWorkFWCtrlDigitalOutputIndex
        OBJECT-TYPE
            SYNTAX      Integer32 (1..1024)
            MAX-ACCESS  read-only
            STATUS      current
            DESCRIPTION
                "This object identifies the digital output"
        ::= { flWorkFWCtrlDigitalOutputEntry 1 }

      flWorkFWCtrlDigitalOutputStatus
        OBJECT-TYPE
            SYNTAX      INTEGER {
                            on(1),
                            off(2),
                            unknown(3)
                            }
            MAX-ACCESS  read-write
            STATUS      current
            DESCRIPTION
                "Get back  or set the current state of a digital output.

                 on(1)          = signal present at output
                 off(2)         = signal not present at output
                 unknown(3)     = signal status is unkonwn"
        ::= { flWorkFWCtrlDigitalOutputEntry 2 }

      flWorkFWCtrlDigitalOutputEnable
              OBJECT-TYPE
                  SYNTAX      INTEGER {
                                  disable(1),
                                  enable(2)
                                  }
                  MAX-ACCESS  read-write
                  STATUS      current
                  DESCRIPTION
                      "Setting this object to disable(1) disables the direct access to the digital output
                      from WEB, CLI and SNMP. Regardless of that, the digital out might be controlled by 
                      'flWorkFWCtrlDigitalOutputEvent_xxx'."
	     ::= { flWorkFWCtrlDigitalOutputEntry 3 }

      flWorkFWCtrlDigitalOutputEventDigitalInState
              OBJECT-TYPE
              	SYNTAX      INTEGER {
                              	disable(1),
                              	enable(2)
                              	}
                  MAX-ACCESS  read-write
                  STATUS      current
                  DESCRIPTION
                  	"Setting this object to enable(2) leads to
                   	activating the digital output, if the digital input
                   	drives high state."

	     ::= { flWorkFWCtrlDigitalOutputEntry 4 }

      flWorkFWCtrlDigitalOutputEventWlanState
              OBJECT-TYPE
            	SYNTAX      INTEGER {
                            	disable(1),
                            	enable(2)
                            	}
                MAX-ACCESS  read-write
                STATUS      current
                  DESCRIPTION
                  "Setting this object to enable(2) leads to
                  activating the digital output, if the WLAN interface is activated."
	     ::= { flWorkFWCtrlDigitalOutputEntry 5 }

      flWorkFWCtrlDigitalOutputEventWlanConnection
              OBJECT-TYPE
          		SYNTAX      INTEGER {
                          	disable(1),
                          	enable(2)
                          	}
              MAX-ACCESS  read-write
              STATUS      current
                DESCRIPTION
                "Setting this object to enable(2) leads to
                activating the digital output, if the device is associated to an access point"
	     ::= { flWorkFWCtrlDigitalOutputEntry 6 }


    -- *************************************************************************************
    -- Fan group
    -- flWorkFWCtrlFan
    -- *************************************************************************************
    -- 
    -- flWorkFWCtrlFanOperationMode OBJECT-TYPE
    --      SYNTAX      INTEGER {
    --                  on(1),
    --                  off(2),
    --                  auto(3)
    --               }
    --      MAX-ACCESS  read-write
    --      STATUS      current
    --      DESCRIPTION
    --                  "Set Operation Mode for optional Fan.
    --                  
    --                  on(1)        = fan is always running full-speed
    --                  off(2)       = fan is off
    --                  auto(3)      = fan is controlled automatically"
    --       ::= { flWorkFWCtrlFan 1 }


    
    --
    --
    -- flWorkFWCtrlConf Group
    --
    flWorkFWCtrlConfStatus
        OBJECT-TYPE
            SYNTAX      INTEGER {
                            configOK(1),
                            configFault(2),
                            configSaved(3),
                            configSaveInProgress(4),
                            replaced(5)
                        }
            MAX-ACCESS  read-only
            STATUS      current
            DESCRIPTION
                "A GET of this object will return the status 
                 of the current device configuration. 
                
                 The status configOK(1) shows that the current 
                 configuration is equal to the saved configuration. 
                 That means that the switch starts with the same 
                 configuration after a power down or a reset. 
                
                 The status configFault(2) signals that the current 
                 configuration is not equal to the saved one.
                 If you reboot the device under this situation the 
                 device may be reboots with a different configuration.
                 
                 The status saved(3) is the response of the 
                 first snmp get request after saving the current 
                 configuration. The information configSaveInProgress(4) 
                 signals that the device saves his configuration right 
                 now.
                 
                 This object signals only the status configFault(2) if
                 an object of the private MIB has been changed!"
                 
        ::= { flWorkFWCtrlConf 1 }

    flWorkFWCtrlConfSave
        OBJECT-TYPE
            SYNTAX      INTEGER {
                            noSave(1),
                            save(2)
                        }
            MAX-ACCESS  read-write
            STATUS      current
            DESCRIPTION
                "When set to save(2), all non volatile configuration 
                parameters are saved to NVM (Nonvolatile Memory).

                Setting this object to noSave(1) has no effect. 
                The firmware will always return the value noSave(1) 
                when this object is reading."                                                                 
            DEFVAL  {noSave}
        ::= { flWorkFWCtrlConf 2 }

    flWorkFWCtrlDefaultUponDelivery
        OBJECT-TYPE
            SYNTAX      INTEGER {
                            noDefaultUponDelivery(1),
                            defaultUponDelivery(2)
                        }
            MAX-ACCESS  read-write
            STATUS      current
            DESCRIPTION
                "Setting this object to default upon delivery(2) 
                 brings the device into the default upon delivery.
                 For example: 
                        - the IP addresses is set on 0.0.0.0,
                        - the password is adjusted to private 
                        - the adjustments for the firmware update
                          are cleared
                        - bootp enabled.
                        
                 Additionally a restart of the device is released
                 automatically!

                 Setting this object noDefaultUponDelivery(1)
                 has no effect. The firmware will always return
                 the value noDefaultUponDelivery(1) when this
                 object is reading."
            DEFVAL  {noDefaultUponDelivery} 
        ::= { flWorkFWCtrlConf 3 }

    flWorkFWCtrlConfName
        OBJECT-TYPE
            SYNTAX      OCTET STRING (SIZE(0..64))
            MAX-ACCESS  read-write
            STATUS      current
            DESCRIPTION
                "This object informs about the descriptive
                 name of the non volatile configuration. 
                 A set operation to this object sets the
                 name of the stored configuration."
            DEFVAL  {"MMS configuration"}            
        ::= { flWorkFWCtrlConf 4 }

    flWorkFWCtrlConfSource
        OBJECT-TYPE
            SYNTAX      INTEGER {
                            nonVolatileMemoryDevice(1),
                            pluggableMemory(2)
                        }
            MAX-ACCESS  read-only
            STATUS      current
            DESCRIPTION
                "This object informs about the storage location
                 from which the device reads the configuration at
                 startup."
        ::= { flWorkFWCtrlConf 5 }

 flWorkFWCtrlLoginSessions OBJECT-TYPE
         SYNTAX      INTEGER {
                     enable(1),
                     disable(2)
                  }
         MAX-ACCESS  read-write
         STATUS      current
         DESCRIPTION
                     "close all telnet sessions"
         ::= { flWorkFWCtrlConf 6 }

     flWorkFWCtrlPasswords OBJECT-TYPE
         SYNTAX      INTEGER {
                     enable(1),
                     disable(2)
                  }
         MAX-ACCESS  read-write
         STATUS      current
         DESCRIPTION
                     "reset passwords"
         ::= { flWorkFWCtrlConf 7 }

     flWorkFWCtrlSwitchStats OBJECT-TYPE
         SYNTAX      INTEGER {
                     enable(1),
                     disable(2)
                  }
         MAX-ACCESS  read-write
         STATUS      current
         DESCRIPTION
                     "clear all switch statistics"
         ::= { flWorkFWCtrlConf 8 }

     flWorkFWCtrlTrapLog OBJECT-TYPE
         SYNTAX      INTEGER {
                     enable(1),
                     disable(2)
                  }
         MAX-ACCESS  read-write
         STATUS      current
         DESCRIPTION
                     "clear trap log"
         ::= { flWorkFWCtrlConf 9 }

    flWorkFWConfigTftpIPAddr
        OBJECT-TYPE
            SYNTAX      IpAddress
            MAX-ACCESS  read-write
            STATUS      current
            DESCRIPTION
                "Write to this object sets the IP address for
                 the TFTP server needed by the file transfer process."
        ::= { flWorkFWConfig 2 }

    flWorkFWConfigTftpFile
        OBJECT-TYPE
            SYNTAX      OCTET STRING (SIZE(0..64))
            MAX-ACCESS  read-write
            STATUS      current
            DESCRIPTION
                "Writing to this object sets the file name
                 for the file transfer process."
            DEFVAL  {""}
        ::= { flWorkFWConfig 3 }

    flWorkFWConfigStatus
        OBJECT-TYPE
            SYNTAX      INTEGER {
                                transferOk(1),
                                transferFault(2),
                                noTransfer(3),
                                unknown(4)
                        }
            MAX-ACCESS  read-only
            STATUS      current
            DESCRIPTION
                "Information about the last file transfer process."
        ::= { flWorkFWConfig 4 }

    flWorkFWConfigExecute
        OBJECT-TYPE
            SYNTAX      INTEGER {
                            noTransfer(1),
                            hostToDevice(2),
                            deviceToHost(3)
                        }
            MAX-ACCESS  read-write
            STATUS      current
            DESCRIPTION
                "Setting this object to hostToDevice(2) causes a
                 download of the configuration file from a 
                 TFTP server (host) to this device.
                 
                 Setting this object to deviceToHost(3) sends the 
                 configuration file to the tftp server named by the
                 object flWorkFWConfigTftpIPAddr.
                 This object always return the value 
                 noTransfer(1) when this object is reading."
            DEFVAL  {noTransfer}
        ::= { flWorkFWConfig 5 }

        
    flWorkFWRunningConfig 
        OBJECT-TYPE
            SYNTAX INTEGER {
               notStarted(1),       -- transfer has not yet started
               inProgress(2),       -- transfer has not yet finished
               success(3),          -- transfer has finished successfully
               errorConnection(4),  -- transfer cannot connect
               errorFilename(5),    -- transfer has bad image path/filename
               errorFault(6)        -- transfer has fault condition on device
            }
            MAX-ACCESS read-only 
            STATUS current
            DESCRIPTION
                "Provides status on the running tftp 
                 configuration file transfer progress."
        ::= { flWorkFWConfig 6 }
   
    
    --
    --
    -- flWorkFWCtrlConfigPluggable Group
    --

    flWorkFWCtrlConfPluggableStatus
        OBJECT-TYPE
            SYNTAX      INTEGER {
                            plugmemPresent(1),
                            plugmemBusy(2),
                            plugmemNotSupported(3),
                            plugmemNotPresent(4),
                            plugmemDefect(5),
                            plugmemWrongType(6)
                        }
            MAX-ACCESS  read-only
            STATUS      current
            DESCRIPTION
                "This object informs about the status
                 of the pluggable memory module."
        ::= { flWorkFWCtrlConfigPluggable 1 }

    flWorkFWCtrlConfPluggableClear
        OBJECT-TYPE
            SYNTAX      INTEGER {
                            noClear(1),
                            clear(2)
                        }
            MAX-ACCESS  read-write
            STATUS      current
            DESCRIPTION
                "When set this object to clear(2), the 
                memory module will be cleared.
                A switch with an empty memory module loads the
                configuration out of the non volatile memory of
                the head station during the startup phase. 
                A new configuration will be stored in the 
                memory module when you save the current
                configuration or the device is booting.

                Setting this object to noClear(1) has no effect. 
                Reading this object you get always
                the value noClear(1)."
        ::= { flWorkFWCtrlConfigPluggable 2 }

    flWorkFWCtrlConfPluggableCompare
        OBJECT-TYPE
            SYNTAX      INTEGER {
                            noCompare(1),
                            compare(2)
                        }
            MAX-ACCESS  read-write
            STATUS      current
            DESCRIPTION
                "Setting this object to compare(2) starts
                a comparison between the configuration in
                module module and the non volatile memory
                of head station.
                
                Setting this object to noCompare(1) has no effect. 
                Reading this object you get always the
                value noCompare(1)."
        ::= { flWorkFWCtrlConfigPluggable 3 }

    flWorkFWCtrlConfPluggableCompareStatus
        OBJECT-TYPE
            SYNTAX      INTEGER {
                            unknown(1),
                            compareInProgress(2),
                            configEqual(3),
                            configNotEqual(4),
                            memoryModuleEmpty(5)
                        }
            MAX-ACCESS  read-only
            STATUS      current
            DESCRIPTION
                "This object informs about the result of comparing
                 the configuration in the memory module
                 and in the non volatile memory of the head station.
                 You get the value unknown(1) if the object
                 flWorkFWCtrlConfMemoryModuleStatus returns a value
                 not equal to plugmemPresent(1)." 
        ::= { flWorkFWCtrlConfigPluggable 4 }

    
    flWorkFWCtrlConfigMemConfName
        OBJECT-TYPE
            SYNTAX      OCTET STRING
            MAX-ACCESS  read-only
            STATUS      current
            DESCRIPTION
                "This object informs about the descriptive
                 name of the configuration stored in the
                 memory module.
                 The object will be set to the current 
                 configuration name each time the 
                 configuration will be write into the
                 memory module."            
        ::= { flWorkFWCtrlConfigMemInfo 1 }
        
    flWorkFWCtrlConfigMemFwVersion
        OBJECT-TYPE
            SYNTAX      OCTET STRING
            MAX-ACCESS  read-only
            STATUS      current
            DESCRIPTION
                "This object informs about the firmware
                 version with which the configuration was
                 stored."
        ::= { flWorkFWCtrlConfigMemInfo 2 }
        
    flWorkFWCtrlConfigMemIpAddress
        OBJECT-TYPE
            SYNTAX      OCTET STRING
            MAX-ACCESS  read-only
            STATUS      current
            DESCRIPTION
               "IP address of the device writing the
                configuration file into the memory module."
        ::= { flWorkFWCtrlConfigMemInfo 3 }
        
    flWorkFWCtrlConfigMemMrmFunctionality
        OBJECT-TYPE
            SYNTAX      INTEGER {
                            notAvailable(0),
                            available(1)                           
                        }

            MAX-ACCESS  read-only
            STATUS      current
            DESCRIPTION
               "Indicates if the plugable memory module
                carries MRP master functionality 
                that can be used on the system."
        ::= { flWorkFWCtrlConfigMemInfo 4 }

     flWorkFWCtrlConfigMemSerialNumber
        OBJECT-TYPE
            SYNTAX      Unsigned32 

            MAX-ACCESS  read-only
            STATUS      current
            DESCRIPTION               
	       "This is the one-to-one serial number of
	        the plugable memory module."
        ::= { flWorkFWCtrlConfigMemInfo 5 }

    flWorkFWCtrlConfigMemManufacturingId
        OBJECT-TYPE
            SYNTAX      INTEGER

            MAX-ACCESS  read-only
            STATUS      current
            DESCRIPTION
               "This is the manufacturing id of the
	        plugable memory module."
        ::= { flWorkFWCtrlConfigMemInfo 6 }

     flWorkFWCtrlConfigMemType
        OBJECT-TYPE
            SYNTAX      INTEGER {
                            unknown(0),
                            memPlug(1),
                            roConfigStick(2)                           
                        }

            MAX-ACCESS  read-only
            STATUS      current
            DESCRIPTION
               "Indicates the type of configuration memory beeing
                used."
        ::= { flWorkFWCtrlConfigMemInfo 7 } 
        
     flWorkFWCtrlConfigMemL3License
        OBJECT-TYPE
            SYNTAX      INTEGER {
                            noLicense(0),
                            licenseAvailable(1)                           
                        }

            MAX-ACCESS  read-only
            STATUS      current
            DESCRIPTION
               "Indicates if the plugable memory module
                carries an Layer 3 license that will
                enable this functionality on the system."
        ::= { flWorkFWCtrlConfigMemInfo 8 }


   -- 
   -- Telnet Group
   -- 

        flWorkFWCtrlTelnetLoginTimeout OBJECT-TYPE                    -- agentTelnetLoginTimeout
         SYNTAX      Integer32 (1..160)
         MAX-ACCESS  read-write
         STATUS      current
         DESCRIPTION
                     "Telnet login timeout (minutes)

                     Config telnet timeout  will set the telnet session timeout value.
                     A session is active as long as the session has not remained idle for
                     the value set. Specify a value from 1 to 160.
                     Note: Changing the timeout value for active
                     sessions does not become effective until the session is reaccessed.
                     Any keystroke will also activate the new timeout duration."
         ::= { flWorkFWCtrlTelnetGroup 1 }

    flWorkFWCtrlTelnetMaxSessions OBJECT-TYPE   					-- agentTelnetMaxSessions
         SYNTAX      Integer32 (0..5)
         MAX-ACCESS  read-write
         STATUS      current
         DESCRIPTION
                     "Maximum number of Telnet Sessions
                     Config telnet maxsessions is an integer value from 0 to 5 that specifies the
                     maximum number of telnet sessions that can be established.
                     If the value is 0, no Telnet session can be established.
                     "
         ::= { flWorkFWCtrlTelnetGroup 2 }

    flWorkFWCtrlTelnetAllowNewMode OBJECT-TYPE
         SYNTAX      INTEGER {
                     enable(1),
                     disable(2)
                  }
         MAX-ACCESS  read-write
         STATUS      current
         DESCRIPTION
                     "Allow new telnet sessions (enable or disable)
                     Config telnet disable means that no new Telnet sessions are to be
                     established. Any already established session remains active until
                     the session is ended or an abnormal network error ends it.
                     "
          ::= { flWorkFWCtrlTelnetGroup 3 }



    --
    --
    -- flWorkFWCtrlSerialBaud Group
    --
    flWorkFWCtrlSerialBaud OBJECT-TYPE
        SYNTAX INTEGER {
               baud2400(1),
               baud9600(2),
               baud19200(3),
               baud38400(4)
        } 
        MAX-ACCESS read-only
        STATUS current
        DESCRIPTION
            "The serial port baud rate."
        ::= { flWorkFWCtrlSerial 1 }


    flWorkFWCtrlSerialDataBits OBJECT-TYPE
        SYNTAX INTEGER { bits8(1) }
        MAX-ACCESS read-only
        STATUS current
        DESCRIPTION
            "The serial port number of data bits."
        ::= { flWorkFWCtrlSerial 2 }


    flWorkFWCtrlSerialStopBits OBJECT-TYPE
        SYNTAX INTEGER { one(1), two(2) } 
        MAX-ACCESS read-only 
        STATUS current
        DESCRIPTION
            "The serial port number of stop bits."
        ::= { flWorkFWCtrlSerial 3 }


    flWorkFWCtrlSerialParity OBJECT-TYPE
        SYNTAX INTEGER { no(1), odd(2), even(3) }
        MAX-ACCESS read-only
        STATUS current
        DESCRIPTION
            "The serial port parity."
        ::= { flWorkFWCtrlSerial 4 }


    flWorkFWCtrlSerialFlowControl OBJECT-TYPE
        SYNTAX INTEGER { no(1), hardware(2) }
        MAX-ACCESS read-only
        STATUS current
        DESCRIPTION
            "The serial port flow control."
        ::= { flWorkFWCtrlSerial 5 }

flWorkFWCtrlSerialTimeout OBJECT-TYPE
         SYNTAX      Integer32 (0..160)
         MAX-ACCESS  read-only
         STATUS      current
         DESCRIPTION
                     "flWorkFWCtrlSerialTimeout specifies the maximum connect time(in minutes)
                     without console activity. A value of 0 indicates that a console can
                     be connected indefinitely. The time range is 0 to 160. "
         ::= { flWorkFWCtrlSerial 6}


    --
    --
    -- flWorkFWCtrlAlarmContact Group
    --
    flWorkFWCtrlAlarmContactEvents
        OBJECT IDENTIFIER ::= { flWorkFWCtrlAlarmContact 1 }
    
    flWorkFWCtrlAlarmContactEventPowerSupply
        OBJECT-TYPE
            SYNTAX      INTEGER {
                            disable(1),
                            enable(2)
                        }    
            MAX-ACCESS  read-write
            STATUS      current
            DESCRIPTION
                "Setting this object to enable(2) leads to 
                 releasing the alarm contact, if only one 
                 power supply is present."
            DEFVAL  {enable}
        ::= { flWorkFWCtrlAlarmContactEvents 1 }

    flWorkFWCtrlAlarmContactEventLinkState
        OBJECT-TYPE
            SYNTAX      INTEGER {
                            disable(1),
                            enable(2)
                        }    
            MAX-ACCESS  read-write
            STATUS      current
            DESCRIPTION
                "Setting this object to enable(2) leads to 
                 releasing the alarm contact, if at least one 
                 port with an activated link monitoring 
                 (see object flWorkNetPortLinkMonitoring) 
                 detects a link down."
            DEFVAL  {disable}
        ::= { flWorkFWCtrlAlarmContactEvents 2 }            

    flWorkFWCtrlAlarmContactEventSecurityPortBlocked
        OBJECT-TYPE
            SYNTAX      INTEGER {
                            disable(1),
                            enable(2)
                        }    
            MAX-ACCESS  read-write
            STATUS      current
            DESCRIPTION
                "Setting this object to enable(2) leads to 
                 releasing the alarm contact, if the device
                 receives at one port a not allowed mac address
                 and the port security based at mac addresses
                 is enabled for the port.
                 (see object flWorkFWCtrlSecurityPortEnable
                 and objects in the table
                 flWorkFWCtrlSecurityPortTable)."
            DEFVAL  {enable}
        ::= { flWorkFWCtrlAlarmContactEvents 3 }
        

    flWorkFWCtrlAlarmContactEventPoeFaultDetected
        OBJECT-TYPE
            SYNTAX      INTEGER {
                            disable(1),
                            enable(2)
                        }    
            MAX-ACCESS  read-write
            STATUS      current
            DESCRIPTION
                "Setting this object to enable(2) leads to 
                 releasing the alarm contact, if the device
                 detects a fault on any Power over Ethernet
                 enabled port that has the object flWorkNetPortPoeFaultMonitoring
                 set to enabled"
            DEFVAL  {enable}
        ::= { flWorkFWCtrlAlarmContactEvents 4 }
        
    flWorkFWCtrlAlarmContactEventMrpRingFailure
        OBJECT-TYPE
            SYNTAX      INTEGER {
                            disable(1),
                            enable(2)
                        }    
            MAX-ACCESS  read-write
            STATUS      current
            DESCRIPTION
                "Setting this object to enable(2) leads to 
                 releasing the alarm contact, if an activated MRP Manager
                 detects a ring failure."
            DEFVAL  {disable}
        ::= { flWorkFWCtrlAlarmContactEvents 5 }

    flWorkFWCtrlAlarmContactEventConfigMemFail
        OBJECT-TYPE
            SYNTAX      INTEGER {
                            disable(1),
                            enable(2)
                        }    
            MAX-ACCESS  read-write
            STATUS      current
            DESCRIPTION
                "Setting this object to enable(2) leads to 
                 releasing the alarm contact, if a mem plug is missing
                 or the configuration on it is invalid."
            DEFVAL  {enable}
        ::= { flWorkFWCtrlAlarmContactEvents 6 }     
        
    flWorkFWCtrlAlarmContactEventPoFScrjTransCritical
        OBJECT-TYPE
            SYNTAX      INTEGER {
                            disable(1),
                            enable(2)
                        }    
            MAX-ACCESS  read-write
            STATUS      current
            DESCRIPTION
                "Setting this object to enable(2) leads to 
                 releasing the alarm contact, if any POF SCRJ
                 transceiver in the system has reached a 
                 critical low rx power level.
                 See object flWorkNetPortPofScrjIfAlarmContactEnable 
                 for individual enabling and disabling per port."
            DEFVAL  {enable}
        ::= { flWorkFWCtrlAlarmContactEvents 7 }

    flWorkFWCtrlAlarmContactEventDlrRingFailure
        OBJECT-TYPE
            SYNTAX      INTEGER {
                            disable(1),
                            enable(2)
                        }    
            MAX-ACCESS  read-write
            STATUS      current
            DESCRIPTION
                "Setting this object to enable(2) leads to 
                 releasing the alarm contact, if an activated DLR supervisor
                 detects a ring failure."
            DEFVAL  {disable}
        ::= { flWorkFWCtrlAlarmContactEvents 8 } 
        


    flWorkFWCtrlAlarmContactEnable
        OBJECT-TYPE
            SYNTAX      INTEGER {
                            disable(1),
                            enable(2)
                        }    
            MAX-ACCESS  read-write
            STATUS      current
            DESCRIPTION
                "Setting this object to enable(2) activates the monitoring
                 of the events which are listed in the group
                 flWorkFWCtrlAlarmContactEvents."
            DEFVAL  {enable}
        ::= { flWorkFWCtrlAlarmContact 2 }
    
    flWorkFWCtrlAlarmContactStatus
        OBJECT-TYPE
            SYNTAX      INTEGER {
                            open(1),
                            closed(2)
                        }    
            MAX-ACCESS  read-only
            STATUS      current
            DESCRIPTION
                "The object flWorkFWCtrlAlarmContactStatus presents
                 information about the status of the alarm contact."
        ::= { flWorkFWCtrlAlarmContact 3 }
    
    flWorkFWCtrlAlarmContactReason
        OBJECT-TYPE
            SYNTAX      DisplayString
            MAX-ACCESS  read-only
            STATUS      current
            DESCRIPTION
                "The reason the alarm contact has been activated."
        ::= { flWorkFWCtrlAlarmContact 4 }

       flWorkFWCtrlAlarmContact2Events
        OBJECT IDENTIFIER ::= { flWorkFWCtrlAlarmContact 11 }
    
    flWorkFWCtrlAlarmContact2EventPowerSupply
        OBJECT-TYPE
            SYNTAX      INTEGER {
                            disable(1),
                            enable(2)
                        }    
            MAX-ACCESS  read-write
            STATUS      current
            DESCRIPTION
                "Setting this object to enable(2) leads to 
                 releasing the alarm contact, if only one 
                 power supply is present."
            DEFVAL  {enable}
        ::= { flWorkFWCtrlAlarmContact2Events 1 }

    flWorkFWCtrlAlarmContact2EventLinkState
        OBJECT-TYPE
            SYNTAX      INTEGER {
                            disable(1),
                            enable(2)
                        }    
            MAX-ACCESS  read-write
            STATUS      current
            DESCRIPTION
                "Setting this object to enable(2) leads to 
                 releasing the alarm contact, if at least one 
                 port with an activated link monitoring 
                 (see object flWorkNetPortLinkMonitoring) 
                 detects a link down."
            DEFVAL  {disable}
        ::= { flWorkFWCtrlAlarmContact2Events 2 }            

    flWorkFWCtrlAlarmContact2EventSecurityPortBlocked
        OBJECT-TYPE
            SYNTAX      INTEGER {
                            disable(1),
                            enable(2)
                        }    
            MAX-ACCESS  read-write
            STATUS      current
            DESCRIPTION
                "Setting this object to enable(2) leads to 
                 releasing the alarm contact, if the device
                 receives at one port a not allowed mac address
                 and the port security based at mac addresses
                 is enabled for the port.
                 (see object flWorkFWCtrlSecurityPortEnable
                 and objects in the table
                 flWorkFWCtrlSecurityPortTable)."
            DEFVAL  {enable}
        ::= { flWorkFWCtrlAlarmContact2Events 3 }
        

    flWorkFWCtrlAlarmContact2EventPoeFaultDetected
        OBJECT-TYPE
            SYNTAX      INTEGER {
                            disable(1),
                            enable(2)
                        }    
            MAX-ACCESS  read-write
            STATUS      current
            DESCRIPTION
                "Setting this object to enable(2) leads to 
                 releasing the alarm contact, if the device
                 detects a fault on any Power over Ethernet
                 enabled port that has the object flWorkNetPortPoeFaultMonitoring
                 set to enabled"
            DEFVAL  {enable}
        ::= { flWorkFWCtrlAlarmContact2Events 4 }
        
    flWorkFWCtrlAlarmContact2EventMrpRingFailure
        OBJECT-TYPE
            SYNTAX      INTEGER {
                            disable(1),
                            enable(2)
                        }    
            MAX-ACCESS  read-write
            STATUS      current
            DESCRIPTION
                "Setting this object to enable(2) leads to 
                 releasing the alarm contact, if an activated MRP Manager
                 detects a ring failure."
            DEFVAL  {disable}
        ::= { flWorkFWCtrlAlarmContact2Events 5 }

       flWorkFWCtrlAlarmContact2EventConfigMemFail
        OBJECT-TYPE
            SYNTAX      INTEGER {
                            disable(1),
                            enable(2)
                        }    
            MAX-ACCESS  read-write
            STATUS      current
            DESCRIPTION
                "Setting this object to enable(2) leads to 
                 releasing the alarm contact, if a mem plug is missing
                 or the configuration on it is invalid."
            DEFVAL  {enable}
        ::= { flWorkFWCtrlAlarmContact2Events 6 }     
        
    flWorkFWCtrlAlarmContact2EventPoFScrjTransCritical
        OBJECT-TYPE
            SYNTAX      INTEGER {
                            disable(1),
                            enable(2)
                        }    
            MAX-ACCESS  read-write
            STATUS      current
            DESCRIPTION
                "Setting this object to enable(2) leads to 
                 releasing the alarm contact, if any POF SCRJ
                 transceiver in the system has reached a 
                 critical low rx power level.
                 See object flWorkNetPortPofScrjIfAlarmContactEnable 
                 for individual enabling and disabling per port."
            DEFVAL  {enable}
        ::= { flWorkFWCtrlAlarmContact2Events 7 }

   flWorkFWCtrlAlarmContact2EventDlrRingFailure
        OBJECT-TYPE
            SYNTAX      INTEGER {
                            disable(1),
                            enable(2)
                        }    
            MAX-ACCESS  read-write
            STATUS      current
            DESCRIPTION
                "Setting this object to enable(2) leads to 
                 releasing the alarm contact, if an activated DLR supervisor
                 detects a ring failure."
            DEFVAL  {disable}
        ::= { flWorkFWCtrlAlarmContact2Events 8 }        


    flWorkFWCtrlAlarmContact2Enable  
        OBJECT-TYPE
            SYNTAX      INTEGER {
                            disable(1),
                            enable(2)
                        }    
            MAX-ACCESS  read-write
            STATUS      current
            DESCRIPTION
                "Setting this object to enable(2) activates the monitoring
                 of the events which are listed in the group
                 flWorkFWCtrlAlarmContactEvents."
            DEFVAL  {enable}
        ::= { flWorkFWCtrlAlarmContact 12 }
    
    flWorkFWCtrlAlarmContact2Status
        OBJECT-TYPE
            SYNTAX      INTEGER {
                            open(1),
                            closed(2)
                        }    
            MAX-ACCESS  read-only
            STATUS      current
            DESCRIPTION
                "The object flWorkFWCtrlAlarmContactStatus presents
                 information about the status of the alarm contact."
        ::= { flWorkFWCtrlAlarmContact 13 }
    
    flWorkFWCtrlAlarmContact2Reason
        OBJECT-TYPE
            SYNTAX      DisplayString
            MAX-ACCESS  read-only
            STATUS      current
            DESCRIPTION
                "The reason the alarm contact has been activated."
        ::= { flWorkFWCtrlAlarmContact 14 }


                                 
    --
    --
    -- flWorkFWCtrlSecurity Group
    --
    flWorkFWCtrlSecurityAccess
        OBJECT IDENTIFIER ::= { flWorkFWCtrlSecurity 1 }
        
    flWorkFWCtrlSecurityPort
        OBJECT IDENTIFIER ::= { flWorkFWCtrlSecurity 2 }
                          
    --
    --
    -- flWorkFWCtrlSecurity Group
    --                          
        -- ip based access control for management interfaces
        --
    flWorkFWCtrlSecurityAccessTable
        OBJECT-TYPE
            SYNTAX      SEQUENCE OF FlWorkFWCtrlSecurityAccessEntry
            MAX-ACCESS  not-accessible
            STATUS      current
            DESCRIPTION
                "Table of client ip addresses for the
                access control for the user interfaces
                of the device based on ip addresses."
        ::= { flWorkFWCtrlSecurityAccess 1 }

    flWorkFWCtrlSecurityAccessEntry
        OBJECT-TYPE
            SYNTAX      FlWorkFWCtrlSecurityAccessEntry
            MAX-ACCESS  not-accessible
            STATUS      current
            DESCRIPTION
                "An entry in the table contains one client
                 ip address of the access control list."
            INDEX       { flWorkFWCtrlSecurityAccessIndex }
        ::= { flWorkFWCtrlSecurityAccessTable 1 }

    FlWorkFWCtrlSecurityAccessEntry
        ::= SEQUENCE {
            flWorkFWCtrlSecurityAccessIndex
                Integer32,
            flWorkFWCtrlSecurityAccessAddr
                IpAddress,
            flWorkFWCtrlSecurityAccessDescr
                OCTET STRING,
            flWorkFWCtrlSecurityAccessRight
                INTEGER
        }

    flWorkFWCtrlSecurityAccessIndex
        OBJECT-TYPE
            SYNTAX      Integer32 (1..1024)
            MAX-ACCESS  read-only
            STATUS      current
            DESCRIPTION
                "This object identifies the entry in the
                 access control list. This value is never
                 greater then flWorkFWCtrlSecurityAccessTableCapacityMax."
        ::= { flWorkFWCtrlSecurityAccessEntry 1 }

    flWorkFWCtrlSecurityAccessAddr
        OBJECT-TYPE
            SYNTAX      IpAddress
            MAX-ACCESS  read-write
            STATUS      current
            DESCRIPTION
                "This ip address named a client who have
                 access rights to this device.
                 Values in the form 0.0.0.0 are non valid
                 ip addresses and will be understanding
                 as an inactive entries."
        ::= { flWorkFWCtrlSecurityAccessEntry 2 }

    flWorkFWCtrlSecurityAccessDescr 
        OBJECT-TYPE
            SYNTAX      OCTET STRING (SIZE (0..32))
            MAX-ACCESS  read-write
            STATUS      current
            DESCRIPTION
                "A description of this client."
            DEFVAL  {"Allowed address x"}
        ::= { flWorkFWCtrlSecurityAccessEntry 3 }

    flWorkFWCtrlSecurityAccessRight
        OBJECT-TYPE
            SYNTAX      INTEGER {
                            readOnly(1),
                            readWrite(2)
                        }    
            MAX-ACCESS  read-write
            STATUS      current
            DESCRIPTION
                "Access rights of the client named by the
                 ip address (see object flWorkFWCtrlSecurityAccessAddr)."
            DEFVAL  {readOnly}
        ::= { flWorkFWCtrlSecurityAccessEntry 4 }
                                          
                                          
    flWorkFWCtrlSecurityAccessTableCapacityMax
        OBJECT-TYPE
            SYNTAX      Integer32
            MAX-ACCESS  read-only
            STATUS      current
            DESCRIPTION
                "Maximal number of entries in the 
                 security table for access control to the
                 management interfaces."
        ::= { flWorkFWCtrlSecurityAccess 2 }

    flWorkFWCtrlSecurityAccessEnable
        OBJECT-TYPE
            SYNTAX      INTEGER {
                            disable(1),
                            enable(2)
                        }    
            MAX-ACCESS  read-write
            STATUS      current
            DESCRIPTION
                "Status of the access control to management
                 interfaces based on client ip addresses.
                 Setting the object to disable(1) disables the
                 access control to management interfaces based
                 on the client ip address.
                 An active access security mechanism looks in the
                 flWorkFWCtrlSecurityAccessTable to decide about
                 the client access to the user interfaces of
                 the device.
                 If no valid ip address is given this object
                 will be set to disable(1)."
            DEFVAL  {disable}
        ::= { flWorkFWCtrlSecurityAccess 3 }            


               

    --
    --
    -- flWorkFWCtrlSecurityPort Group
    --                          
        -- port based access control to the network
        --  
        
        -- configure ports                 
    flWorkFWCtrlSecurityPortTable
        OBJECT-TYPE
            SYNTAX      SEQUENCE OF FlWorkFWCtrlSecurityPortEntry
            MAX-ACCESS  not-accessible
            STATUS      current
            DESCRIPTION
                "Table of port parameters to be configured for
                 port security based on source addresses."
        ::= { flWorkFWCtrlSecurityPort 1 }

    flWorkFWCtrlSecurityPortEntry
        OBJECT-TYPE
            SYNTAX      FlWorkFWCtrlSecurityPortEntry
            MAX-ACCESS  not-accessible
            STATUS      current
            DESCRIPTION
                "An entry in the table contains information
                 of one port of the device."
            INDEX       { flWorkFWCtrlSecurityPortIndex }
        ::= { flWorkFWCtrlSecurityPortTable 1 }

    FlWorkFWCtrlSecurityPortEntry
        ::= SEQUENCE {
            flWorkFWCtrlSecurityPortIndex
                Integer32,
            flWorkFWCtrlSecurityPortLastMacAddr
                MacAddress,
            flWorkFWCtrlSecurityPortMode
                INTEGER,
            flWorkFWCtrlSecurityPortState
                INTEGER,                                
            flWorkFWCtrlSecurityPortIllegalAddrCounter
                Gauge32
        }

    flWorkFWCtrlSecurityPortIndex
        OBJECT-TYPE
            SYNTAX      Integer32 (1..255)
            MAX-ACCESS  read-only
            STATUS      current
            DESCRIPTION
                "This object identifies the entry in the
                 port list. This value is never
                 greater then flWorkFWCtrlSecurityPortTableCapacityMax."
        ::= { flWorkFWCtrlSecurityPortEntry 1 }

    flWorkFWCtrlSecurityPortLastMacAddr
        OBJECT-TYPE
            SYNTAX      MacAddress
            MAX-ACCESS  read-only
            STATUS      current
            DESCRIPTION
                "This mac address is the last source 
                 mac address the device received at the port.
                 The corresponding Vlan Id is added to the end.
                 +-----------------+-------+    
                 |Mac Address      |Vlan Id|
                 +-----------------+-------+
                 |xx:xx:xx:xx:xx:xx:xx:xx  |
                 +-----------------+-------+ 
                 Values in the form 00:00:00:00:00:00:00:00 are
                 non valid addresses and will be understanding
                 as an inactive entries."
        ::= { flWorkFWCtrlSecurityPortEntry 2 }

    flWorkFWCtrlSecurityPortMode
        OBJECT-TYPE
            SYNTAX      INTEGER {
                            noSecurity(1),
                            trapOnly(2),
                            blockPackets(3),
                            blockPacketsWithAutoReenabling(4),
                            passPackets(5)
                        }
            MAX-ACCESS  read-write
            STATUS      current
            DESCRIPTION
                "Get back or set the current security mode of 
                 the port."                 
            DEFVAL { noSecurity }
        ::= { flWorkFWCtrlSecurityPortEntry 3 }
    
    flWorkFWCtrlSecurityPortState
        OBJECT-TYPE
            SYNTAX      INTEGER {
                            ok(1),
                            blocking(2),
                            reenabling(3)
                            }
            MAX-ACCESS  read-write
            STATUS      current
            DESCRIPTION
                "Get back the security operational state of the port.
                 The state blocking(2) indicates that this
                 port has received a not allowed mac address
                 and is blocked now. No received ethernet
                 packets will be forwarded to other ports.
                 If the user sets this object ot reenabling(3)
                 a blocked port will move to status ok(1).
                 NOTE: If the user reenables a port the port might
                 become blocking again immediately if there are still
                 invalid mac addresses located at this port and
                 securityMode of this port is still 3 or 4."
        ::= { flWorkFWCtrlSecurityPortEntry 4 }
            
    flWorkFWCtrlSecurityPortIllegalAddrCounter
        OBJECT-TYPE
            SYNTAX      Gauge32
            MAX-ACCESS  read-only
            STATUS      current
            DESCRIPTION
                "Number of received illegal mac addresses
                 at the port."
        ::= { flWorkFWCtrlSecurityPortEntry 5 }
        
    
    -- configure allowed mac addresses for all ports
    flWorkFWCtrlSecurityPortMacTable
        OBJECT-TYPE
            SYNTAX      SEQUENCE OF FlWorkFWCtrlSecurityPortMacEntry
            MAX-ACCESS  not-accessible
            STATUS      current
            DESCRIPTION
                "Table of allowed mac addresses for each port."
        ::= { flWorkFWCtrlSecurityPort 2 }

    flWorkFWCtrlSecurityPortMacEntry
        OBJECT-TYPE
            SYNTAX      FlWorkFWCtrlSecurityPortMacEntry
            MAX-ACCESS  not-accessible
            STATUS      current
            DESCRIPTION
                "An entry in the table contains information
                 about one allowed source mac address."
            INDEX       { 
                                flWorkFWCtrlSecurityPortIndex,
                                flWorkFWCtrlSecurityPortMacIndex
                                }
        ::= { flWorkFWCtrlSecurityPortMacTable 1 }

    FlWorkFWCtrlSecurityPortMacEntry
        ::= SEQUENCE {
            flWorkFWCtrlSecurityPortMacIndex
                Integer32,
            flWorkFWCtrlSecurityPortMacAddr
                MacAddress,
            flWorkFWCtrlSecurityPortMacDescr
                OCTET STRING,
            flWorkFWCtrlSecurityPortMacVlanID
                Integer32,
            flWorkFWCtrlSecurityPortMacDelete
                INTEGER
        }

    flWorkFWCtrlSecurityPortMacIndex
        OBJECT-TYPE
            SYNTAX      Integer32 (1..255)
            MAX-ACCESS  read-only
            STATUS      current
            DESCRIPTION
                "This object identifies the number of the
                 for one port. This value is never
                 greater then flWorkFWCtrlSecurityPortMacTableCapacityMax."
        ::= { flWorkFWCtrlSecurityPortMacEntry 1 }

    flWorkFWCtrlSecurityPortMacAddr
        OBJECT-TYPE
            SYNTAX      MacAddress
            MAX-ACCESS  read-write
            STATUS      current
            DESCRIPTION
                "A allowed mac address at the port.
                 Values in the form 00:00:00:00:00:00 are
                 non valid addresses and will be understanding
                 as an inactive entries.
                 Please take notice of the syntax of this object.
                 You have to enter mac addresses as values of 6 
                 bytes (for example using a MG Soft Mib Brower
                 in the notation: # 0x10 0x20 0x30 0x40 0x50 0x60)."
            DEFVAL  { "" }
        ::= { flWorkFWCtrlSecurityPortMacEntry 2 }
                                                          
    flWorkFWCtrlSecurityPortMacDescr 
        OBJECT-TYPE
            SYNTAX      OCTET STRING (SIZE (0..16))
            MAX-ACCESS  read-write
            STATUS      current
            DESCRIPTION
                "A description of the allowed mac address."
            DEFVAL  {"Allowed port xx"}
        ::= { flWorkFWCtrlSecurityPortMacEntry 3 }
        
    flWorkFWCtrlSecurityPortMacVlanID
        OBJECT-TYPE
            SYNTAX      Integer32 (1..4094)
            MAX-ACCESS  read-write
            STATUS      current
            DESCRIPTION
                "This object is only relevant for vlan tagging mode, to setup
                 the vlan ID for this entry."
        ::= { flWorkFWCtrlSecurityPortMacEntry 4 }   
        
    flWorkFWCtrlSecurityPortMacDelete
        OBJECT-TYPE
            SYNTAX      INTEGER {
                            keepMAC(1),
                            deleteMAC(2)
                        }
            MAX-ACCESS  read-write
            STATUS      current
            DESCRIPTION
                "When set this object to deleteMAC(2), the corresponding MAC entry will be deleted.

                Setting this object to keepMAC(1) has no effect. 
                Reading this object you get always
                the value keepMAC(1)."
        ::= { flWorkFWCtrlSecurityPortMacEntry 5 }
                                         
    -- scalar objects of the group flWorkFWCtrlSecurityPort                                         
    flWorkFWCtrlSecurityPortTableCapacityMax
        OBJECT-TYPE
            SYNTAX      Integer32
            MAX-ACCESS  read-only
            STATUS      current
            DESCRIPTION
                "Maximal number of entries in the 
                 security port table."
        ::= { flWorkFWCtrlSecurityPort 3 }
                                                      
    flWorkFWCtrlSecurityPortMacTableCapacityMax
        OBJECT-TYPE
            SYNTAX      Integer32
            MAX-ACCESS  read-only
            STATUS      current
            DESCRIPTION
                "Maximal number of allowed mac addresses
                 for each port.
                 The maximal number of the entries in the 
                 flWorkFWCtrlSecurityPortMacTable is the result
                 of the multiplication
                 flWorkFWCtrlSecurityPortMacTableCapacityMax *
                 flWorkFWCtrlSecurityPortTableCapacityMax."
        ::= { flWorkFWCtrlSecurityPort 4 }
                                                              
    flWorkFWCtrlSecurityPortEnable
        OBJECT-TYPE
            SYNTAX      INTEGER {
                            disable(1),
                            enable(2)
                        }    
            MAX-ACCESS  read-write
            STATUS      current
            DESCRIPTION
                "Status of the access control to the network
                 based on destination mac addresses received
                 by the device in ethernet packets.
                 Setting the object to disable(1) disables the
                 access control to the network based
                 on mac addresses.
                 If value is enable(2)the access security mechanism looks in the
                 flWorkFWCtrlSecurityPortTable to decide about
                 the client access to the network."
        ::= { flWorkFWCtrlSecurityPort 5 }

    flWorkFWCtrlSecurityPortIllegalAddrCounterClear
        OBJECT-TYPE
            SYNTAX      INTEGER {
                            noClear(1),
                            clear(2)
                        }    
            MAX-ACCESS  read-write
            STATUS      current
            DESCRIPTION
                "Setting this object to clear(2) sets all counter
                 flWorkFWCtrlSecurityPortIllegalAddrCounter to zero.
                 Setting this object to noClear(1) has no effect.
                 Reading this object you get always
                 the value noClear(1)."
        ::= { flWorkFWCtrlSecurityPort 6 }                                                              


 		-- configure allowed IP addresses for all ports
    flWorkFWCtrlSecurityPortIpFilterTable
        OBJECT-TYPE
            SYNTAX      SEQUENCE OF FlWorkFWCtrlSecurityPortIpFilterEntry
            MAX-ACCESS  not-accessible
            STATUS      current
            DESCRIPTION
                "Table of allowed Ip addresses for each port."
        ::= { flWorkFWCtrlSecurityPort 7 }

    flWorkFWCtrlSecurityPortIpFilterEntry
        OBJECT-TYPE
            SYNTAX      FlWorkFWCtrlSecurityPortIpFilterEntry
            MAX-ACCESS  not-accessible
            STATUS      current
            DESCRIPTION
                "An entry in the table contains information
                 about one allowed destination Ip address."
            INDEX       { 
                                flWorkFWCtrlSecurityPortIndex,
                                flWorkFWCtrlSecurityPortIpFilterIndex
                                }
        ::= { flWorkFWCtrlSecurityPortIpFilterTable 1 }

    FlWorkFWCtrlSecurityPortIpFilterEntry
        ::= SEQUENCE {
            flWorkFWCtrlSecurityPortIpFilterIndex
                Integer32,
            flWorkFWCtrlSecurityPortIpFilterAddr
                IpAddress,
            flWorkFWCtrlSecurityPortIpFilterDescr
                OCTET STRING,
            flWorkFWCtrlSecurityPortIpFilterPort
                Integer32
        }

    flWorkFWCtrlSecurityPortIpFilterIndex
        OBJECT-TYPE
            SYNTAX      Integer32 (1..255)
            MAX-ACCESS  read-only
            STATUS      current
            DESCRIPTION
                "This object identifies the number of the entry index
                 for one port. This value is never
                 greater then flWorkFWCtrlSecurityPortIpFilterTableCapacityMax."
        ::= { flWorkFWCtrlSecurityPortIpFilterEntry 1 }

    flWorkFWCtrlSecurityPortIpFilterAddr
        OBJECT-TYPE
            SYNTAX      IpAddress
            MAX-ACCESS  read-write
            STATUS      current
            DESCRIPTION
                "An allowed destination Ip address (whitelist) at the port in the form
                 0.0.0.0"
            DEFVAL  { "" }
        ::= { flWorkFWCtrlSecurityPortIpFilterEntry 2 }
                                                          
    flWorkFWCtrlSecurityPortIpFilterDescr 
        OBJECT-TYPE
            SYNTAX      OCTET STRING (SIZE (0..16))
            MAX-ACCESS  read-write
            STATUS      current
            DESCRIPTION
                "A description of the allowed Ip address."
            DEFVAL  {"Allowed port xx"}
        ::= { flWorkFWCtrlSecurityPortIpFilterEntry 3 }
        
    flWorkFWCtrlSecurityPortIpFilterPort
        OBJECT-TYPE
            SYNTAX      Integer32 (0..65535)
            MAX-ACCESS  read-write
            STATUS      current
            DESCRIPTION
                "The combination of destination IP address from flWorkFWCtrlSecurityPortIpFilterAddr
				in combination with the destination Port (TCP/UDP Portnumber) forms a whitelist entry.
				A value of 0 means that IP traffic to all destination ports pass the filter "
        ::= { flWorkFWCtrlSecurityPortIpFilterEntry 4 }                                                          
                                         

                                                      
    flWorkFWCtrlSecurityPortIpFilterTableCapacityMax
        OBJECT-TYPE
            SYNTAX      Integer32
            MAX-ACCESS  read-only
            STATUS      current
            DESCRIPTION
                "Maximal number of allowed Ip addresses
                 for each port."
        ::= { flWorkFWCtrlSecurityPort 8 }  
        
    flWorkFWCtrlSecurityMAConMultiplePorts
        OBJECT-TYPE
            SYNTAX      INTEGER {
                            disable(1),
                            enable(2)
                        }    
            MAX-ACCESS  read-write
            STATUS      current
            DESCRIPTION    
                ""
        ::= { flWorkFWCtrlSecurityPort 9 }                                                         

        
flWorkFWCtrlSecurityDot1x
        OBJECT IDENTIFIER ::= { flWorkFWCtrlSecurity 3 }


   --
   --  flWorkFWCtrlSecurityDot1x - Global .1x configuration objects.
   --
   
      		
   flWorkFWCtrlSecurityDot1xPortTable
        OBJECT-TYPE
            SYNTAX      SEQUENCE OF FlWorkFWCtrlSecurityDot1xPortEntry
            MAX-ACCESS  not-accessible
            STATUS      current
            DESCRIPTION
                "Table of guest Vlan Ids in 802.1x configuration for each
                 port."
        ::= { flWorkFWCtrlSecurityDot1x 1 }

    flWorkFWCtrlSecurityDot1xPortEntry
        OBJECT-TYPE
            SYNTAX      FlWorkFWCtrlSecurityDot1xPortEntry
            MAX-ACCESS  not-accessible
            STATUS      current
            DESCRIPTION
                "An entry in the table contains information
                 about guest Vlan Ids and reauthentication
                 time."
            INDEX { ifIndex}
        ::= { flWorkFWCtrlSecurityDot1xPortTable 1 }

     FlWorkFWCtrlSecurityDot1xPortEntry
        ::= SEQUENCE {
            flWorkFWCtrlSecurityDot1xGuestVlanId
                Integer32,
            flWorkFWCtrlSecurityDot1xAssignTimeout
                Integer32
            }
            
     flWorkFWCtrlSecurityDot1xGuestVlanId
     		OBJECT-TYPE
     		SYNTAX      Integer32   
     		MAX-ACCESS  read-write
     		STATUS 	current
		DESCRIPTION
     			"This object sets the configurable guest vlan id
     			 for the current port." 
     	      DEFVAL { 0 }
	  ::= { flWorkFWCtrlSecurityDot1xPortEntry 1 }
     	
     flWorkFWCtrlSecurityDot1xAssignTimeout
     		OBJECT-TYPE
     		SYNTAX		Integer32 (0..65535)
     		MAX-ACCESS	read-write
     		STATUS		current
     		DESCRIPTION
     			"The value, in seconds, of the guestVlanPeriod constant
               	 currently in use for Guest Vlan Assignment for the 
                   interface ."
            DEFVAL { 90 }
        ::= { flWorkFWCtrlSecurityDot1xPortEntry 2 }
        
    flWorkFWCtrlSecurityDot1xVlanAssign
   		OBJECT-TYPE
   			SYNTAX		INTEGER {
   			          	    enable(1),
   			          	    disable(2)
   			          }              
   			MAX-ACCESS  read-write
   			STATUS		current
   			DESCRIPTION
   			  "When this object is enabled the authentication server 
   			  is able to assign the user to a specicified VLAN."
   		::= { flWorkFWCtrlSecurityDot1x 2 }

 
    flWorkFWCtrlSecurityRadiusAuthServTable
        OBJECT-TYPE
            SYNTAX      SEQUENCE OF FlWorkFWCtrlSecurityRadiusAuthServEntry
            MAX-ACCESS  not-accessible
            STATUS      current
            DESCRIPTION
                "The table is listing RADIUS authentication servers with which the client shares a secret."
        ::= { flWorkFWCtrlSecurityDot1x 3 }

    flWorkFWCtrlSecurityRadiusAuthServEntry
        OBJECT-TYPE
            SYNTAX      FlWorkFWCtrlSecurityRadiusAuthServEntry
            MAX-ACCESS  not-accessible
            STATUS      current
            DESCRIPTION
                "An entry in the table represents RADIUS authentication server with which the client shares a secret."
            INDEX { flWorkFWCtrlSecurityRadiusServIndex}
        ::= { flWorkFWCtrlSecurityRadiusAuthServTable 1 }

     FlWorkFWCtrlSecurityRadiusAuthServEntry
        ::= SEQUENCE {
            flWorkFWCtrlSecurityRadiusServIndex
                Integer32,
            flWorkFWCtrlSecurityRadiusServAddress
                IpAddress,
            flWorkFWCtrlSecurityRadiusServPort
            	Integer32,
            flWorkFWCtrlSecurityRadiusServSharedSecret
                OCTET STRING,
            flWorkFWCtrlSecurityRadiusServName
            	DisplayString
            }
            
     flWorkFWCtrlSecurityRadiusServIndex
     		OBJECT-TYPE
     		SYNTAX      Integer32 (1..255)    
     		MAX-ACCESS  read-only
     		STATUS 	current
		DESCRIPTION
     			"A number uniquly identifying each RADIUS authentication server." 
     	      DEFVAL { 1 }
	  ::= { flWorkFWCtrlSecurityRadiusAuthServEntry 1 }

     flWorkFWCtrlSecurityRadiusServAddress
     		OBJECT-TYPE
     		SYNTAX      IpAddress   
     		MAX-ACCESS  read-write
     		STATUS 	current
		DESCRIPTION
     			"IP address of the RADIUS authentication server." 
	  ::= { flWorkFWCtrlSecurityRadiusAuthServEntry 2 }

     flWorkFWCtrlSecurityRadiusServPort
     		OBJECT-TYPE
     		SYNTAX      Integer32   
     		MAX-ACCESS  read-write
     		STATUS 	current
		DESCRIPTION
     			"UDP port the this server is using to accept requests from the client." 
     	      DEFVAL { 1812 }
	  ::= { flWorkFWCtrlSecurityRadiusAuthServEntry 3 }
 
      flWorkFWCtrlSecurityRadiusServSharedSecret
     		OBJECT-TYPE
     		SYNTAX      OCTET STRING   
     		MAX-ACCESS  read-write
     		STATUS 	current
		DESCRIPTION
                "This write only object changes the current
                 shared secret to a given new shared secret. The character
                 mask is defined as below:

                    1.) The shared secret length is min. 8 and max. 64 characters.
                    2.) All ASCII codes allowd (except code 0x00).
                    3.) For redundancy check the shared secret is given
                        twice as shown below:
                        
                            Shared Secret:                   nimbus3
                            
                            octetstr = 2 x Shared Secret:    nimbus3nimbus3
                            
                    4.) As an result of this the absolut length of
                        octet string is even and min. 16 and max. 128 characters.
                        
                 The firmware will always return a string of five
                 asterics (*****) when this object is reading."

     	      DEFVAL { "2bchanged" }
	  ::= { flWorkFWCtrlSecurityRadiusAuthServEntry 4 }

    flWorkFWCtrlSecurityRadiusServName
    	OBJECT-TYPE
	        SYNTAX DisplayString
	        MAX-ACCESS read-write
	        STATUS current
	        DESCRIPTION
	            "Hostname of the RADIUS authentication server.
	             The maximum size of the string is 255 characters."       
	        DEFVAL  {""}
        ::= { flWorkFWCtrlSecurityRadiusAuthServEntry 5 }

    --
    --
    -- flWorkFWCtrlProfinet Group
    --
    

    
    flWorkFWCtrlProfinetAlarm
        OBJECT IDENTIFIER ::= { flWorkFWCtrlProfinet 1 }
 
         
    flWorkFWCtrlProfinetAlarmPortTable
        OBJECT-TYPE
            SYNTAX      SEQUENCE OF FlWorkFWCtrlProfinetAlarmPortEntry
            MAX-ACCESS  not-accessible
            STATUS      current
            DESCRIPTION
                "Table of network ports and the related profinet alarm
                 configuration."
        ::= { flWorkFWCtrlProfinetAlarm 1 }

    flWorkFWCtrlProfinetAlarmPortEntry
        OBJECT-TYPE
            SYNTAX      FlWorkFWCtrlProfinetAlarmPortEntry
            MAX-ACCESS  not-accessible
            STATUS      current
            DESCRIPTION
                "An entry in the table containing information 
                 of one network port and his profinet alarm
                 configuration."
            INDEX       { flWorkFWCtrlProfinetAlarmPortIndex }
        ::= { flWorkFWCtrlProfinetAlarmPortTable 1 }

    FlWorkFWCtrlProfinetAlarmPortEntry
        ::= SEQUENCE {
            flWorkFWCtrlProfinetAlarmPortIndex
                Integer32,
            flWorkFWCtrlProfinetAlarmPortLinkMonitoring
                INTEGER,
            flWorkFWCtrlProfinetAlarmPortPofScrjDiag
                INTEGER,
            flWorkFWCtrlProfinetAlarmPortSFPMissing
                INTEGER
        }

    flWorkFWCtrlProfinetAlarmPortIndex
        OBJECT-TYPE
            SYNTAX      Integer32 (1..1024)
            MAX-ACCESS  read-only
            STATUS      current
            DESCRIPTION
                "This object identifies the port. This value
                 is never greater then flWorkNetPortCapacity."
        ::= { flWorkFWCtrlProfinetAlarmPortEntry 1 }

    flWorkFWCtrlProfinetAlarmPortLinkMonitoring
        OBJECT-TYPE
            SYNTAX      INTEGER {
                            disable(1),
                            enable(2)                            
                        }    
            MAX-ACCESS  read-write
            STATUS      current
            DESCRIPTION
                "In the operation mode Profinet a slot is
                 able to send an alarm when the link status 
                 (see object flWorkNetPortLinkState) changes
                 from connected(1) to notConnected(2)."
            DEFVAL  {disable}
        ::= { flWorkFWCtrlProfinetAlarmPortEntry 2 }

    flWorkFWCtrlProfinetAlarmPortPofScrjDiag
        OBJECT-TYPE
            SYNTAX      INTEGER {
                            disable(1),
                            enable(2)
                        }    
            MAX-ACCESS  read-write
            STATUS      current
            DESCRIPTION
                "In the operation mode Profinet a slot is
                 able to send an alarm when the receive power
                 of a POF SCRJ port reaches a the warning
                 threshold or changes into a critical state.
                 
                 Only the FL SWITCH MM HS support this profinet
                 alarm."
            DEFVAL  {disable}
        ::= { flWorkFWCtrlProfinetAlarmPortEntry 3 }

    flWorkFWCtrlProfinetAlarmPortSFPMissing
        OBJECT-TYPE
            SYNTAX      INTEGER {
                            disable(1),
                            enable(2)
                        }    
            MAX-ACCESS  read-write
            STATUS      current
            DESCRIPTION
                "In the operation mode Profinet a slot is
                 able to send an alarm when the SFP module
                 is missing."
            DEFVAL  {disable}
        ::= { flWorkFWCtrlProfinetAlarmPortEntry 4 }


    flWorkFWCtrlProfinetAlarmPowerSupply
        OBJECT-TYPE
            SYNTAX      INTEGER {
                            disable(1),
                            enable(2)
                        }    
            MAX-ACCESS  read-write
            STATUS      current
            DESCRIPTION
                "In the operation mode Profinet the device is able
                 to send an alarm when one redundant power supply
                 has been lost."
            DEFVAL  {disable}
        ::= { flWorkFWCtrlProfinetAlarm 10 }

    flWorkFWCtrlProfinetAlarmModuleRemove
        OBJECT-TYPE
            SYNTAX      INTEGER {
                            disable(1),
                            enable(2)
                        }    
            MAX-ACCESS  read-write
            STATUS      current
            DESCRIPTION
                "In the operation mode Profinet the device is able
                 to send an alarm when one interface module has been
                 removed.
                 
                 Only the FL SWITCH MM HS support this profinet
                 alarm."
            DEFVAL  {disable}
        ::= { flWorkFWCtrlProfinetAlarm 11 }   

   flWorkFWCtrlProfinetAlarmPlugableMemory
            OBJECT-TYPE
            SYNTAX      INTEGER {
                            disable(1),
                            enable(2)
                        }    
            MAX-ACCESS  read-write
            STATUS      current
            DESCRIPTION
                "In the operation mode Profinet the device is able
                 to send an alarm when the plug mem or SD card is
                 missing."
            DEFVAL  {disable}
        ::= { flWorkFWCtrlProfinetAlarm 12 }   

    flWorkFWCtrlProfinetAlarmMRPRingFailure
            OBJECT-TYPE
            SYNTAX      INTEGER {
                            disable(1),
                            enable(2)
                        }    
            MAX-ACCESS  read-write
            STATUS      current
            DESCRIPTION
                "In the operation mode Profinet the device is able
                 to send an alarm when this device works as MRP Manager and
      	         has detected an failure in the ring.                
                 Only the devices with MRP Manager functionality will support this profinet
                 alarm."
            DEFVAL  {disable}
        ::= { flWorkFWCtrlProfinetAlarm 20 }        

   flWorkFWCtrlProfinetStatus
        OBJECT IDENTIFIER ::= { flWorkFWCtrlProfinet 2 }
        
   flWorkFWCtrlProfinetStatusActiveARs 
        OBJECT-TYPE
        SYNTAX Integer32
        MAX-ACCESS read-only
        STATUS current
        DESCRIPTION
                "The count of currentlcy active application relations." 
        ::={ flWorkFWCtrlProfinetStatus 1 }

    flWorkFWCtrlProfinetStatusConReqCount
        OBJECT-TYPE
        SYNTAX Integer32
        MAX-ACCESS read-only
        STATUS current
        DESCRIPTION
                "The count of connect requests received by this switch." 
        ::={ flWorkFWCtrlProfinetStatus 2 }       

    flWorkFWCtrlProfinetStatusDiagStatus
        OBJECT-TYPE
        SYNTAX INTEGER {
                        inactive(0),
                        good(1),
			maintenanceRequired(2),
                        maintenanceDemanded(3),
                        diagnosis(4)	}
        MAX-ACCESS read-only
        STATUS current
        DESCRIPTION
                "The current diagnosis status of the device. " 
        ::={ flWorkFWCtrlProfinetStatus 3 }

   flWorkFWCtrlProfinetBoundarySettings
        OBJECT IDENTIFIER ::= { flWorkFWCtrlProfinet 3 }

   flWorkFWCtrlProfinetBoundarySettingsTable
        OBJECT-TYPE
            SYNTAX      SEQUENCE OF FlWorkFWCtrlProfinetBoundarySettingsEntry
            MAX-ACCESS  not-accessible
            STATUS      current
            DESCRIPTION
                "Table of profinet boundary settings."
        ::= { flWorkFWCtrlProfinetBoundarySettings 1 }
        
    flWorkFWCtrlProfinetBoundarySettingsEntry
        OBJECT-TYPE
            SYNTAX      FlWorkFWCtrlProfinetBoundarySettingsEntry
            MAX-ACCESS  not-accessible
            STATUS      current
            DESCRIPTION
                "An entry in the table, containing profinet boundary 
                 settings of one physical port."
            INDEX       { flWorkFWCtrlProfinetBoundarySettingsPortIndex }
        ::= { flWorkFWCtrlProfinetBoundarySettingsTable 1 }
        
    FlWorkFWCtrlProfinetBoundarySettingsEntry
        ::= SEQUENCE {
            flWorkFWCtrlProfinetBoundarySettingsPortIndex
                INTEGER,
            flWorkFWCtrlProfinetBoundarySettingsDcpIdentify
                INTEGER,
            flWorkFWCtrlProfinetBoundarySettingsDcpHello
                INTEGER,
            flWorkFWCtrlProfinetBoundarySettingsLLDP
                INTEGER
        }
    
    flWorkFWCtrlProfinetBoundarySettingsPortIndex OBJECT-TYPE
       SYNTAX  INTEGER (1..1024)
        MAX-ACCESS read-only
        STATUS current
        DESCRIPTION
            "Number of the physical port for which the profinet
             boundary settings are made."
        ::= { flWorkFWCtrlProfinetBoundarySettingsEntry 1 }    
        
    flWorkFWCtrlProfinetBoundarySettingsDcpIdentify OBJECT-TYPE
       SYNTAX      INTEGER {
                            notActive(1),
                            active(2)
                            }
        MAX-ACCESS read-write
        STATUS current
        DESCRIPTION
            "Decide if DCP identify frames
             should be dropped (active(2)) or forwarded (notActive (1)) for the dedicated port."
        DEFVAL  {notActive}
        ::= { flWorkFWCtrlProfinetBoundarySettingsEntry 2 }


    flWorkFWCtrlProfinetBoundarySettingsDcpHello OBJECT-TYPE
        SYNTAX     INTEGER {
                            notActive(1),
                            active(2)
                            }
        MAX-ACCESS read-write
        STATUS current
        DESCRIPTION
            "Decide if DCP hello frames
             should be dropped (active(2)) or forwarded (notActive (1)) for the dedicated port."
        DEFVAL  {notActive}
        ::= { flWorkFWCtrlProfinetBoundarySettingsEntry 3 }

    flWorkFWCtrlProfinetBoundarySettingsLLDP OBJECT-TYPE
       SYNTAX      INTEGER {
                            notActive(1),
                            active(2)
                            }
        MAX-ACCESS read-write
        STATUS current
        DESCRIPTION
            "Decide if receiving and transmitting lldp frames
             is disabled (active(2)) or enabled (notActive (1)) for the dedicated port."
        DEFVAL  {notActive}
        ::= { flWorkFWCtrlProfinetBoundarySettingsEntry 4 }

-- MIB-Module for Profinet Media-Redundancy-Protocol

 
    flWorkFWCtrlMRPConfigDomainTable 
    		OBJECT-TYPE
            SYNTAX          SEQUENCE OF FlWorkFWCtrlMRPConfigDomainEntry
            MAX-ACCESS          not-accessible
            STATUS          current
            DESCRIPTION     "Every entry into the table contains information about
                                 a MRP domain."
            ::= { flWorkFWCtrlMRPConfig 1 }

    flWorkFWCtrlMRPConfigDomainEntry     
    		OBJECT-TYPE
            SYNTAX          FlWorkFWCtrlMRPConfigDomainEntry
            MAX-ACCESS          not-accessible
            STATUS          current
            DESCRIPTION     "An entry in the flWorkFWCtrlMRPConfigDomainTable."
            INDEX           { flWorkFWCtrlMRPConfigDomainIdx }
            ::= { flWorkFWCtrlMRPConfigDomainTable 1 }
   
    FlWorkFWCtrlMRPConfigDomainEntry 
    		::= SEQUENCE {
                flWorkFWCtrlMRPConfigDomainIdx	                
                	INTEGER,
                flWorkFWCtrlMRPConfigDomainUdid	                
                	OCTET STRING,
                flWorkFWCtrlMRPConfigDomainName                     
                	OCTET STRING,
                flWorkFWCtrlMRPConfigDomainRole                     
                	INTEGER,
                flWorkFWCtrlMRPConfigDomainManagerPriority          
                	Integer32,
                flWorkFWCtrlMRPConfigDomainVlanID                   
                	INTEGER,
                flWorkFWCtrlMRPConfigDomainRingPort1                
                	INTEGER, 
                flWorkFWCtrlMRPConfigDomainRingPort2                
                	INTEGER,
                flWorkFWCtrlMRPConfigDomainResetRoundTripDelays     
                	INTEGER
                } 
    
	flWorkFWCtrlMRPConfigDomainIdx 
			OBJECT-TYPE
			SYNTAX INTEGER (1..255)
			MAX-ACCESS read-only
			STATUS current
			DESCRIPTION
				"The Index of the entry"
			::={ flWorkFWCtrlMRPConfigDomainEntry 1 }
		
	flWorkFWCtrlMRPConfigDomainUdid 
			OBJECT-TYPE
			SYNTAX OCTET STRING
			MAX-ACCESS read-write
			STATUS current
			DESCRIPTION
				"The IEC 61158-5-10 defines the structure of the UUID
	                         as a data type numberic identifier 1025"
			DEFVAL { 'ffffffffffffffffffffffffffffffff'h}
			::={ flWorkFWCtrlMRPConfigDomainEntry 2 }
	                
	flWorkFWCtrlMRPConfigDomainName 
			OBJECT-TYPE
			SYNTAX OCTET STRING
			MAX-ACCESS read-write
			STATUS current
			DESCRIPTION
				"A logical name for the domain to ease the management of MRP domains"
			DEFVAL { "MRP-DOMAIN"}
			::={ flWorkFWCtrlMRPConfigDomainEntry 3 }


	flWorkFWCtrlMRPConfigDomainRole 
			OBJECT-TYPE
			SYNTAX INTEGER {
                        disable(0),
                        client(1),
						manager(2),
                        delete(3),
						create(4)
						}
			MAX-ACCESS read-write
			STATUS current
			DESCRIPTION
					"Control the MRP behaviour of the system per
                    domain. Setting this value to disable(0) disables 
                    the MRP entity of this domain.

                    If the value is set to client(1) the entity will
                    be set to a client role.

                    If the value is set to manager(2) the entity will
                    be set to a manager role.
                    
                    To activate the new settings, the create(4) option should
                    be used.
                    
                    To delete a MRP domain and disable the protocol, delete(3) 
                    should be used."
			DEFVAL { 0}
			::={ flWorkFWCtrlMRPConfigDomainEntry 4 }

	flWorkFWCtrlMRPConfigDomainManagerPriority 
			OBJECT-TYPE
			SYNTAX Integer32 (0..65535)
			MAX-ACCESS read-write
			STATUS current
			DESCRIPTION
					"The priority of this MRP entity. If the device 
                        is client only, the value of this object   
                        will be ignored by the MRP entity.
                        Only the four most significant bits shall be used,
                        the bits 0 to 11 are reserved.
                        The smaller value has the higher priority.
                        
                        To activate the new settings, create(4) of 
                        flWorkFWCtrlMRPConfigDomainRole have to been used." 
			DEFVAL { 32768 }
			::={ flWorkFWCtrlMRPConfigDomainEntry 5 }

	flWorkFWCtrlMRPConfigDomainVlanID 
			OBJECT-TYPE
			SYNTAX INTEGER (0..4094)
			MAX-ACCESS read-write
			STATUS current
			DESCRIPTION
					"VlanID used by MRP
                                        
                     To activate the new settings, create(4) of 
                     flWorkFWCtrlMRPConfigDomainRole have to been used." 
			DEFVAL {1 }
			::={ flWorkFWCtrlMRPConfigDomainEntry 6 }

	flWorkFWCtrlMRPConfigDomainRingPort1 
			OBJECT-TYPE
			SYNTAX INTEGER
			MAX-ACCESS read-write
			STATUS current
			DESCRIPTION
					"First Ring-Port Number of this device.
                                        
                     To activate the new settings, create(4) of 
                     flWorkFWCtrlMRPConfigDomainRole have to been used."
			DEFVAL {1}
			::={ flWorkFWCtrlMRPConfigDomainEntry 7 }
		
	flWorkFWCtrlMRPConfigDomainRingPort2 
			OBJECT-TYPE
			SYNTAX INTEGER
			MAX-ACCESS read-write
			STATUS current
			DESCRIPTION
					"Second Ring-Port Number of this device.
                                        
                     To activate the new settings, create(4) of 
                     flWorkFWCtrlMRPConfigDomainRole have to been used."
			DEFVAL { 2}
			::={ flWorkFWCtrlMRPConfigDomainEntry 8 } 
		
	flWorkFWCtrlMRPConfigDomainResetRoundTripDelays 
			OBJECT-TYPE
			SYNTAX INTEGER
			MAX-ACCESS read-write
			STATUS current
			DESCRIPTION
					"Reset the max/min round trip delays"
			DEFVAL { 1}
			::={ flWorkFWCtrlMRPConfigDomainEntry 9 }

        
    flWorkFWCtrlMRPInfoDomainTable 
   			OBJECT-TYPE
            SYNTAX          SEQUENCE OF FlWorkFWCtrlMRPInfoDomainEntry
            MAX-ACCESS          not-accessible
            STATUS          current
            DESCRIPTION     "This table contains variables to define
                            an entry in the mrpInfo database."
            ::= { flWorkFWCtrlMRPInfo 1 }

	flWorkFWCtrlMRPInfoDomainEntry     
			OBJECT-TYPE
            SYNTAX          FlWorkFWCtrlMRPInfoDomainEntry
            MAX-ACCESS          not-accessible
            STATUS          current
            DESCRIPTION     "An entry in flWorkFWCtrlMRPInfoDomainTable"
            INDEX           { flWorkFWCtrlMRPInfoDomainIdx }
            ::= { flWorkFWCtrlMRPInfoDomainTable 1 }
   
   FlWorkFWCtrlMRPInfoDomainEntry 
   			::= SEQUENCE {
                flWorkFWCtrlMRPInfoDomainIdx			 
                	INTEGER,
                flWorkFWCtrlMRPInfoDomainUuid                        
                	OCTET STRING,
                flWorkFWCtrlMRPInfoDomainName                       
                	OCTET STRING,
                flWorkFWCtrlMRPInfoDomainAdminRole			 
                	INTEGER,
                flWorkFWCtrlMRPInfoDomainOperRole			 
                	INTEGER,
                flWorkFWCtrlMRPInfoDomainManagerPriority	         
                	Integer32,
                flWorkFWCtrlMRPInfoDomainRingPort1	                 
                	Integer32,
                flWorkFWCtrlMRPInfoDomainRingPort1State              
                	INTEGER,
                flWorkFWCtrlMRPInfoDomainRingPort2			 
                	Integer32,
                flWorkFWCtrlMRPInfoDomainRingPort2State     	 
                	INTEGER,
                flWorkFWCtrlMRPInfoDomainState	                
                	INTEGER,
                flWorkFWCtrlMRPInfoDomainError                       
                	INTEGER,
                flWorkFWCtrlMRPInfoDomainRingOpenCount               
                	Integer32, 
                flWorkFWCtrlMRPInfoDomainLastRingOpenChange          
                	TimeTicks,
                flWorkFWCtrlMRPInfoDomainRoundTripDelayMax           
                	Integer32,
                flWorkFWCtrlMRPInfoDomainRoundTripDelayMin           
                	Integer32
                }
	
	flWorkFWCtrlMRPInfoDomainIdx 
			OBJECT-TYPE
			SYNTAX INTEGER (1..255)
			MAX-ACCESS read-only
			STATUS current
			DESCRIPTION
					"Index number of the Mrp-Domain."
			::={ flWorkFWCtrlMRPInfoDomainEntry 1 } 
	
    flWorkFWCtrlMRPInfoDomainUuid 
    		OBJECT-TYPE
			SYNTAX OCTET STRING
			MAX-ACCESS read-only
			STATUS current
			DESCRIPTION
						"The IEC 61158-5-10 defines the structure of the UUID
                         as a data type numberic identifier 1025"
            ::={ flWorkFWCtrlMRPInfoDomainEntry 2 }
                
    flWorkFWCtrlMRPInfoDomainName 
    		OBJECT-TYPE
			SYNTAX OCTET STRING
			MAX-ACCESS read-only
			STATUS current
			DESCRIPTION
					"A logical name for the domain to ease the management of MRP domains"
			::={ flWorkFWCtrlMRPInfoDomainEntry 3 }
	
	flWorkFWCtrlMRPInfoDomainAdminRole 
			OBJECT-TYPE
			SYNTAX INTEGER {
                        disable(0),
                        client(1),
						manager(2)                     
						}
			MAX-ACCESS read-only
			STATUS current
			DESCRIPTION
					"Control the MRP behaviour of the system per
                    domain. Setting this value to disable(0) disables 
                    the MRP entity of this domain.

                    If the value is set to client(1) the entity will
                    be set to a client role.

                    If the value is set to manager(2) the entity will
                    be set to a manager role.
                    
                    The factory settings are recommended to adjust  
                    the value of this object to the client(1) 
                    capability of the component in order to prevent 
                    multiple managers are in ring (the order of 
                    the capabilities are not necessarily conform to 
                    the order of the object values here)."
		
			::={ flWorkFWCtrlMRPInfoDomainEntry 4 }
                
    flWorkFWCtrlMRPInfoDomainOperRole 
    		OBJECT-TYPE
			SYNTAX INTEGER {
                        disable(0),
                        client(1),
						manager(2)                     
						}
			MAX-ACCESS read-only
			STATUS current
			DESCRIPTION
					"The operational role of a MRP entity per
                    domain. A value of disabled(0) signals that the
                    entity doesn't work (whatever reason).
                    A value of client(1) signals that the entity is
                    in a client role.
                    A value of manager(2) signals that the entity is
                    the manager of this MRP domain."
		
			::={ flWorkFWCtrlMRPInfoDomainEntry 5 }

	flWorkFWCtrlMRPInfoDomainManagerPriority 
			OBJECT-TYPE
			SYNTAX Integer32 (0..65535)
			MAX-ACCESS read-only
			STATUS current
			DESCRIPTION
					"The priority of this MRP entity. If the device 
                    is client only, the value of this object   
                    will be ignored by the MRP entity.
                    Only the four most significant bits shall be used,
                    the bits 0 to 11 are reserved.
                    The smaller value has the higher priority." 
			::={ flWorkFWCtrlMRPInfoDomainEntry 6 }	
	
	flWorkFWCtrlMRPInfoDomainRingPort1 
			OBJECT-TYPE
			SYNTAX Integer32
			MAX-ACCESS read-only
			STATUS current
			DESCRIPTION
					"The ifIndex of the layer 2 interface which is  
                    used as ring port 1."
			::={ flWorkFWCtrlMRPInfoDomainEntry 7 }
	
	
	flWorkFWCtrlMRPInfoDomainRingPort1State 
			OBJECT-TYPE
			SYNTAX INTEGER {
						disable(1),
                        blocked(2),
		   				forwarding(3)
							}
			MAX-ACCESS read-only
			STATUS current
			DESCRIPTION
						"Status of the first Ring-Port."
			::={ flWorkFWCtrlMRPInfoDomainEntry 8 }

	flWorkFWCtrlMRPInfoDomainRingPort2 
			OBJECT-TYPE
			SYNTAX Integer32
			MAX-ACCESS read-only
			STATUS current
			DESCRIPTION
						"The ifIndex of the layer 2 interface which is 
                    	used as ring port 2."
			::={ flWorkFWCtrlMRPInfoDomainEntry 9 }
	
	
	flWorkFWCtrlMRPInfoDomainRingPort2State 
			OBJECT-TYPE
			SYNTAX INTEGER {
						disable(1),
                        blocked(2),
		   				forwarding(3)
							}
			MAX-ACCESS read-only
			STATUS current
			DESCRIPTION
						"Status of the second Ring-Port"
			::={ flWorkFWCtrlMRPInfoDomainEntry 10 }
                
    flWorkFWCtrlMRPInfoDomainState	
    		OBJECT-TYPE
	        SYNTAX INTEGER {
					disabled(0),
					invalid(1),
					ringClosed(2),
					ringOpen(3),
					rtOK(4),
					rtLost(5)
					}
	        MAX-ACCESS  read-only
	        STATUS current
	        DESCRIPTION		"
                    Operational status of the MRP entity.
                    disabled(0)    - MRP switched off
                    invalid(1)     - value not valid because of client
                                     role
                    ringClosed (2) - MRP ring redundancy ok
                    ringOpen (3)   - MRP ring redundancy lost
                    "
			::= {  flWorkFWCtrlMRPInfoDomainEntry 11  }

	flWorkFWCtrlMRPInfoDomainError	
			OBJECT-TYPE
	        SYNTAX INTEGER {         
					noError(0),
					invalid(1),	
					multipleMRM(2),
					singleSideReceive(3)
					}
	        MAX-ACCESS read-only
	        STATUS	current
	        DESCRIPTION		"
                    If the device couldn't switch to the desired 
                    administrative state (thus the value of
                    'pnoMRPDomainState' is not the expected one),
                    this value provides the reason.
                    
                    noError(0)  - the operational state of the device 
                                  is confom to administrative state
                    invalid (1) - value not valid because of client
                                  role
                    multipleMRM(2) - multiple active managers in ring
                                     domain
                    singleSideReceive(4) - the test frames of an MRM
                                           have been seen, but only 
                                           on one port
					"
			::= {  flWorkFWCtrlMRPInfoDomainEntry 12  }


	flWorkFWCtrlMRPInfoDomainRingOpenCount 
			OBJECT-TYPE
			SYNTAX Integer32
			MAX-ACCESS read-only
			STATUS current
			DESCRIPTION
					"Manager-only: Counter for ring-state changes."
			::={ flWorkFWCtrlMRPInfoDomainEntry 13 }

	flWorkFWCtrlMRPInfoDomainLastRingOpenChange 
			OBJECT-TYPE
			SYNTAX TimeTicks
			MAX-ACCESS read-only
			STATUS current
			DESCRIPTION
					"Manager-only: Timeticks since last change of ring-state."
			::={ flWorkFWCtrlMRPInfoDomainEntry 14 }

	flWorkFWCtrlMRPInfoDomainRoundTripDelayMax 
			OBJECT-TYPE
			SYNTAX Integer32
			MAX-ACCESS read-only
			STATUS current
			DESCRIPTION
					"Manager-only: The max. Round-Trip-Delay (in microseconds)
			 		which was measured since startup."
			::={ flWorkFWCtrlMRPInfoDomainEntry 15 }

	flWorkFWCtrlMRPInfoDomainRoundTripDelayMin 
			OBJECT-TYPE
			SYNTAX Integer32
			MAX-ACCESS read-only
			STATUS current
			DESCRIPTION
					"Manager-only: The min. Round-Trip-Delay (in microseconds) 
			 		which was measured since startup."
			::={ flWorkFWCtrlMRPInfoDomainEntry 16 }
    
    -- 1.2.2
	flWorkFWCtrlMRPInfoDeviceBlockingSupport 
			OBJECT-TYPE
			SYNTAX INTEGER {
					no-blocking(1),
					blocking(2)
					}
			MAX-ACCESS read-only
			STATUS current
			DESCRIPTION
					"Reads out the supported mechanism of the device."
			::={ flWorkFWCtrlMRPInfo 2 }

        


	--
	--		
    --  temperture monitoring     
    --
    flWorkFWCtrlActualDeviceTemperature
            OBJECT-TYPE
			SYNTAX Integer32
			MAX-ACCESS read-only
			STATUS current
			DESCRIPTION
					"Actual device temperature in Centigrade"
			::={ flWorkFWCtrlTemp 1 }  
			
    flWorkFWCtrlMinOperTemperature
            OBJECT-TYPE
			SYNTAX Integer32
			MAX-ACCESS read-only
			STATUS current
			DESCRIPTION
					"Minimum allowed operational temperature of device in Centigrade"
			::={ flWorkFWCtrlTemp 2 }  
			
	  flWorkFWCtrlMaxOperTemperature
            OBJECT-TYPE
			SYNTAX Integer32
			MAX-ACCESS read-only
			STATUS current
			DESCRIPTION
					"Maximum allowed operational temperature of device in Centigrade"
			::={ flWorkFWCtrlTemp 3 }   
			
	  	flWorkFWCtrlUserTempWarningThreshold
            OBJECT-TYPE
			SYNTAX Integer32
			MAX-ACCESS read-write
			STATUS current
			DESCRIPTION
					"A trap and display event will be generated if the actual
					 device temperature exceeds this value (value is in Centigrade)."
			::={ flWorkFWCtrlTemp 4 }  
			
	     flWorkFWCtrlTempShutdownPrevention
            OBJECT-TYPE
			SYNTAX INTEGER {
						off(1),
						on(2)
						}
			MAX-ACCESS read-write
			STATUS current
			DESCRIPTION
					"If this object is set to on(2) then the device will NOT shut
					 down if device temperature goes above values that might cause
					 serious damage to the device.
					 NOTE: USE WITH CARE!"
			::={ flWorkFWCtrlTemp 5 }


    --
    --
    -- Traps used by Firmware
    --
    trapPasswdAccess
        NOTIFICATION-TYPE
            OBJECTS     {
                            flWorkFWCtrlPasswdSuccess
                        }
            STATUS      current
            DESCRIPTION
                "Every write access to the device's password send out
                 this trap to all known trap destination named in
                 table flWorkFWCtrlTrapDestTable. So it informs the
                 management system about the successful/unsuccessful
                 operation or rather than non authorized password
                 write operations."
        ::= { flWorkTrapsDelemeter 1 }

    trapFWHealth
        NOTIFICATION-TYPE
            OBJECTS     {
                            flWorkFWInfoOperStatus,
                            flWorkFWInfoHealthText
                        }
            STATUS      current
            DESCRIPTION
                "The trap trapFWHealth conveys information related
                 to the operational status of the firmware. This
                 trap is send when the display changes and that is 
                 equivalent to the value of flWorkFWInfoHealthText.

                 The flWorkFWHealth trap contains the
                 flWorkFWInfoOperStatus object and the 
                 flWorkFWInfoHealthText object as varbinds for description
                 of the information that sent.

                 The agent must throttle the generation of
                 consecutive trapFWHealth traps so that there is at
                 least a five-second gab between, they are dropped,
                 not queued for sending at a future time. (Note
                 that 'generating' a trap means sending to all
                 configured recipients.)"
        ::= { flWorkTrapsDelemeter 2 }

    trapFWConf
        NOTIFICATION-TYPE
            OBJECTS     {
                            flWorkFWCtrlConfStatus
                        }
            STATUS      current
            DESCRIPTION
                "Every time the device's component configuration was
                 saved this trap is sending out to inform the management
                 system about successful operation (configSaved).
                 
                 Further with this trap type the device will inform
                 the management system about an faulty configuration
                 at least every ten minutes. Note that it includes the
                 flWorkFWCtrlConfStatus object as a varbind."
        ::= { flWorkTrapsDelemeter 3 }
        
    trapPowerSupply
        NOTIFICATION-TYPE
            OBJECTS     {
                            flWorkBasicPowerStat
                        }
            STATUS      current
            DESCRIPTION
                "Every time the redundant power supply has been lost
                 this trap is sending out to inform the management 
                 system about the event."
        ::= { flWorkTrapsDelemeter 4 }

    trapSecurityPort
        NOTIFICATION-TYPE
            OBJECTS     {
                            flWorkFWCtrlSecurityPortIndex,
                            flWorkFWCtrlSecurityPortLastMacAddr
                        }
            STATUS      current
            DESCRIPTION
                "Every time a not allowed mac address is received
                 at a port with active mac based security for the first time
                 this trap is sending out to inform the management 
                 system about the event.
                 Note: Trap might be sent again later if the 
                 forbidden mac address has been deleted from the 
                 switch mac database due to aging and is afterwards
                 received again."
        ::= { flWorkTrapsDelemeter 5 }
        
    trapRstpRingFailure
        NOTIFICATION-TYPE
            OBJECTS     {
                            flSwitchRSTPRingRootPort,
                            flWorkNetIfParamPhyAddress,
                            flWorkNetIfParamIpAddress,
                            flWorkBasicName
                        }
            STATUS      current
            DESCRIPTION
                "Every time the Rapid Spanning Tree Fast Ring Detection
                 detects a link failure at a ring port this trap is
                 sending out to inform the management system about the
                 location of the failure."
        ::= { flWorkTrapsDelemeter 6 }
        
    trapPofScrjPort
        NOTIFICATION-TYPE        
            OBJECTS     {
                            flWorkNetPortPofScrjIfIndex,
                            flWorkNetPortPofScrjIfStatus
                        }
            STATUS      current
            DESCRIPTION
                "Every time the interface status of a POF SCRJ
                 port changes into a critical state or leaves a critical state
                 this trap is sent out to inform the management 
                 system about the event."
        ::= { flWorkTrapsDelemeter 7 }
        
    trapPoEPort
        NOTIFICATION-TYPE
            OBJECTS     {
                            flWorkNetPortPoEIndex,
                            flWorkNetPortPoEFaultStatus
                        }
            STATUS      current
            DESCRIPTION
                "Every time the fault status of a PoE 
                 port changes this trap is sent out to inform the management 
                 system about the event."
        ::= { flWorkTrapsDelemeter 8 }
        
trapMrpStatusChange
        NOTIFICATION-TYPE
            OBJECTS     {
                            flWorkFWCtrlMRPInfoDomainIdx,
                            flWorkFWCtrlMRPInfoDomainName,
                            flWorkFWCtrlMRPInfoDomainState
                        }
            STATUS      current
            DESCRIPTION
                "Manager-only: It reports a ring-state change."
        ::= { flWorkTrapsDelemeter 9 }

       trapTemperatureManagement
            NOTIFICATION-TYPE
            STATUS      current
            DESCRIPTION
                "This is a trap that shows that an under- or overtemperature
                 condition did occour on the device."
        ::= { flWorkTrapsDelemeter 10 }

    trapDigitalInput
            NOTIFICATION-TYPE
              OBJECTS     {   
                            flWorkFWCtrlDigitalInputIndex,
                            flWorkFWCtrlDigitalInputStatus
                          }
            STATUS      current
            DESCRIPTION
                "This is a trap that shows that one of the digital inputs of the device 
                 did change its status."
        ::= { flWorkTrapsDelemeter 11 }    
        
      trapSDcardPluggedin
            NOTIFICATION-TYPE 
            OBJECTS     {   
                            flWorkFWCtrlConfPluggableStatus
                        }
            STATUS      current
            DESCRIPTION
                "This trap informs the manager that an SD card is plugged in to the
                 device which is sending this trap."
        ::= { flWorkTrapsDelemeter 12 }    
        
    trapSDcardPluggedout
            NOTIFICATION-TYPE
            STATUS      current
            DESCRIPTION
                "This trap informs the manager that an SD card is plugged out of the
                 device which is sending this trap."
        ::= { flWorkTrapsDelemeter 13 }

    trapConfSaved
        		NOTIFICATION-TYPE
            OBJECTS     {
                            flWorkFWCtrlConfStatus
                        }
            STATUS      current
            DESCRIPTION
                "Every time the device's component configuration was
                 saved this trap is sending out to inform the management
                 system about successful operation (configSaved)."
        ::= { flWorkTrapsDelemeter 16 }
        
    trapIPconflict
            NOTIFICATION-TYPE
            OBJECTS     {   
                            flWorkNetACDStatus,
                            flWorkNetACDIP,
                            flWorkNetACDMAC
                        }
            STATUS      current
            DESCRIPTION
                "Reports ip conflict only when flWorkNetACDStatus
		 has the value noConflict(2) before the conflict was
                 detected."				 
        ::= { flWorkTrapsDelemeter 18 }

    trapDLRRingChange
            NOTIFICATION-TYPE
            OBJECTS     {   
                            flWorkFWCtrlDLRRingStatus
                        }
            STATUS      current
            DESCRIPTION
                "This trap informs the manager that a DLR supervisor has discovered
                 a change in the ring state."
        ::= { flWorkTrapsDelemeter 19 }

	trapPowerSupplyLow
		NOTIFICATION-TYPE
		STATUS	current
		DESCRIPTION
		"Every time the device detects, that the power supply
		 voltage is below the warning level, the management system 
		 is informed about this by this trap."
	::= { flWorkTrapsDelemeter 20 }
	
    trapConfigDiff
            NOTIFICATION-TYPE
            OBJECTS     {
                            flWorkFWCtrlConfPluggableCompareStatus
                        }
            STATUS      current
            DESCRIPTION
                "This trap informs the manager that an Configuration Difference has
                been detected between Memory Module and internal memory."
        ::= { flWorkTrapsDelemeter 21 }
		
	trapCrcOk
            NOTIFICATION-TYPE
            OBJECTS     {
                            flWorkFWCtrlDiagSurveillanceCrcMonitoringPortIndex
                        }
            STATUS      current
            DESCRIPTION
                "The crc port status changed to Ok."
        ::= { flWorkTrapsDelemeter 25 }	
		
	trapCrcWarning
            NOTIFICATION-TYPE
            OBJECTS     {
                            flWorkFWCtrlDiagSurveillanceCrcMonitoringPortIndex
                        }
            STATUS      current
            DESCRIPTION
                "The crc port status changed to Warning."
        ::= { flWorkTrapsDelemeter 26 }			
        
	trapCrcCritical
            NOTIFICATION-TYPE
            OBJECTS     {
                            flWorkFWCtrlDiagSurveillanceCrcMonitoringPortIndex
                        }
            STATUS      current
            DESCRIPTION
                "The crc port status changed to Critical."
        ::= { flWorkTrapsDelemeter 27 }		
        
	trapCrcPeakIncreased
            NOTIFICATION-TYPE
            OBJECTS     {
                            flWorkFWCtrlDiagSurveillanceCrcMonitoringPortIndex,
							flWorkFWCtrlDiagSurveillanceCrcMonitoringProportionPeak
                        }
            STATUS      current
            DESCRIPTION
                "The crc proportion peak increased."
        ::= { flWorkTrapsDelemeter 28 }
		
	trapEventTableOverflow
            NOTIFICATION-TYPE
            STATUS      current
            DESCRIPTION
                "Event Table Overflow."
        ::= { flWorkTrapsDelemeter 29 }	
		
	trapUserConfigChanged
            NOTIFICATION-TYPE
            OBJECTS     {
                            flWorkFWInfoEventDescription
                        }
            STATUS      current
            DESCRIPTION
                "User Config Changed."
        ::= { flWorkTrapsDelemeter 30 }
		
	trapConfigParamChanged
            NOTIFICATION-TYPE
            OBJECTS     {
                            flWorkFWInfoEventDescription
                        }
            STATUS      current
            DESCRIPTION
                "Config Param Changed."
        ::= { flWorkTrapsDelemeter 31 }
        
    trapManagerConnection
        NOTIFICATION-TYPE
            STATUS      current
            DESCRIPTION
                "This is a trap to test the connection from the device 
                 to the trap manager(s)."
        ::= { flWorkTrapsDelemeter 99 }


    flWorkSecurityCtrl
        OBJECT IDENTIFIER ::= { flWorkSecGateway 1  }


    flWorkSecurityCtrlClientAuth
        OBJECT IDENTIFIER ::= { flWorkSecurityCtrl 5  }

    flWorkSecurityCtrlGenSecurityContext OBJECT-TYPE
        SYNTAX INTEGER { notGenerate(1), generate(2) } 
        MAX-ACCESS  read-write
            STATUS      current
            DESCRIPTION
			    "If set this object to generate(2), a new security context 
				 will be generated. This inlcudes a new a server CA, a new 
				 server certificate and SSH-key."
            DEFVAL  {notGenerate}
			::= { flWorkSecurityCtrlClientAuth 3 }


    --
    --
    -- flWorkTimeSynchSntp Group
    --
    
    flWorkTimeSynchSntpEnable OBJECT-TYPE
        SYNTAX INTEGER {
                disable(1),
                enable(2)
            }
        MAX-ACCESS read-write
        STATUS current
        DESCRIPTION
            "The status of the simple network time
            protocol.
            The value enable(2) activates sntp.
            The value disable(1) deactivates sntp."       
        DEFVAL  {disable}
        ::= { flWorkTimeSynchSntp 1 }
    
    
    flWorkTimeSynchSntpMode OBJECT-TYPE
        SYNTAX INTEGER {
                unicast(1),
                broadcast(2),
                manycast(3)
            }
        MAX-ACCESS read-write
        STATUS current
        DESCRIPTION
            "The mode the simple network time
            protocol runs in.
            unicast(1) for the unicast mode,
            broadcast(2) for the broadcast mode,
            manycast(3) for the manycast mode."       
        DEFVAL  {unicast}
        ::= { flWorkTimeSynchSntp 2 }
        

    flWorkTimeSynchSntpPollInterval OBJECT-TYPE
        SYNTAX INTEGER (4..17)
        MAX-ACCESS read-write
        STATUS current
        DESCRIPTION
            "Size of the interval the server is
            polled.
            This value is used as an exponent of two, 
            where the resulting value is the interval 
            between synchronization messages in seconds.
            The possible values are:
            o  4	: 16s
            o  5	: 32s
            o  6	: 1m 4s
            o  7	: 2m 8s
            o  8	: 4m 16s
            o  9	: 8m 32s
            o 10	: 17m 4s
            o 11	: 34m 8s
            o 12	: 1h 8m 16s
            o 13	: 2h 16m 32s
            o 14	: 4h 33m 4s
            o 15	: 9h 6m 8s
            o 16	: 18h 12m 16s
            o 17	: 1d 12h 24m 32s"       
        DEFVAL  {14}
        ::= { flWorkTimeSynchSntp 3 }
        

    flWorkTimeSynchSntpServerIpAddress OBJECT-TYPE
        SYNTAX IpAddress
        MAX-ACCESS read-write
        STATUS current
        DESCRIPTION
            "Writing to this object sets the IP address
            of the first ntp or sntp server needed for
            time synchronization" 
        ::= { flWorkTimeSynchSntp 4 }
        


    flWorkTimeSynchSntpBackupServerIpAddress OBJECT-TYPE
        SYNTAX IpAddress
        MAX-ACCESS read-write
        STATUS current
        DESCRIPTION
            "Writing to this object sets the IP address
            of the second ntp or sntp server which is 
            used as backup for the first server."
        ::= { flWorkTimeSynchSntp 5 }


    flWorkTimeSynchSntpBroadcastIpAddress OBJECT-TYPE
        SYNTAX IpAddress
        MAX-ACCESS read-write
        STATUS current
        DESCRIPTION
            "Writing to this object sets the broadcast
            IP address to locate local sntp or ntp servers
            in manycast mode and choose the best one."
        ::= { flWorkTimeSynchSntp 6 }
        

    flWorkTimeSynchSntpStratum OBJECT-TYPE
        SYNTAX INTEGER (0..15)
        MAX-ACCESS read-only
        STATUS current
        DESCRIPTION
            "Read out the current stratum value."       
        ::= { flWorkTimeSynchSntp 7 }
        
    flWorkTimeSynchSntpTime OBJECT-TYPE
        SYNTAX OCTET STRING
        MAX-ACCESS read-only
        STATUS current
        DESCRIPTION
            "Read out the current system time."       
        ::= { flWorkTimeSynchSntp 8 }
        
    flWorkTimeSynchSntpDate OBJECT-TYPE
        SYNTAX OCTET STRING
        MAX-ACCESS read-only
        STATUS current
        DESCRIPTION
            "Read out the current system date."       
        ::= { flWorkTimeSynchSntp 9 }
        
    flWorkTimeSynchSntpSeconds OBJECT-TYPE
        SYNTAX Unsigned32
        MAX-ACCESS read-only
        STATUS current
        DESCRIPTION
            "Read out the current NTP seconds."       
        ::= { flWorkTimeSynchSntp 10 }
        
    flWorkTimeSynchSntpFractionalSeconds OBJECT-TYPE
        SYNTAX Unsigned32
        MAX-ACCESS read-only
        STATUS current
        DESCRIPTION
            "Read out the current NTP fractional seconds."       
        ::= { flWorkTimeSynchSntp 11 }
        
    flWorkTimeSynchSntpUtcOffset OBJECT-TYPE
        SYNTAX Integer32 (-12..12)
        MAX-ACCESS read-write
        STATUS current
        DESCRIPTION
            "Hours to adjust the UTC time to the local
            time zone."       
        DEFVAL  {0}
        ::= { flWorkTimeSynchSntp 12 }
                
-- OIDs 13-23 are reserved for FL SWITCH 3000 switches.

    flWorkTimeSynchSntpServerDesc OBJECT-TYPE
        SYNTAX DisplayString
        MAX-ACCESS read-write
        STATUS current
        DESCRIPTION
            "Writing to this object sets the description
             of the primary sntp server.
             The maximum size of the string is 255 characters."       
        DEFVAL  {""}
        ::= { flWorkTimeSynchSntp 24 }
        
    flWorkTimeSynchSntpBackupServerDesc OBJECT-TYPE
        SYNTAX DisplayString
        MAX-ACCESS read-write
        STATUS current
        DESCRIPTION
            "Writing to this object sets the description
            of the backup sntp server.
            The maximum size of the string is 255 characters."       
        DEFVAL  {""}
        ::= { flWorkTimeSynchSntp 25 }
        
    flWorkTimeSynchSntpServerName OBJECT-TYPE
        SYNTAX DisplayString
        MAX-ACCESS read-write
        STATUS current
        DESCRIPTION
            "Writing to this object sets the name
             of the primary sntp server.
             The maximum size of the string is 255 characters."       
        DEFVAL  {""}
        ::= { flWorkTimeSynchSntp 26 }
        
    flWorkTimeSynchSntpBackupServerName OBJECT-TYPE
        SYNTAX DisplayString
        MAX-ACCESS read-write
        STATUS current
        DESCRIPTION
            "Writing to this object sets the name
            of the backup sntp server.
            The maximum size of the string is 255 characters."       
        DEFVAL  {""}
        ::= { flWorkTimeSynchSntp 27 }
        
    --
    --                                                   
    -- flWorkTimeSynchRTC Group
    --
    
    flWorkTimeSynchRTCDateTime OBJECT-TYPE
        SYNTAX OCTET STRING
        MAX-ACCESS read-write
        STATUS current
        DESCRIPTION
            "The Date and Time stored in the Real Time Clock.
            To set Real Time Clock use Format:
            YYYY/MM/DD hh:mm:ss"
        ::= { flWorkTimeSynchRTC 1 }
        
    flWorkTimeSynchRTCSeconds OBJECT-TYPE
        SYNTAX Unsigned32
        MAX-ACCESS read-write
        STATUS current
        DESCRIPTION
            "The Seconds stored in the Real Time Clock."       
        ::= { flWorkTimeSynchRTC 2 }    
        
		flWorkTimeSynchPTP
        OBJECT IDENTIFIER ::= { flWorkTimeSynch 3 }  

	--                                                  
    -- flWorkTimeSynchPTP Group
    --
    flWorkTimeSynchPTPPortTable
        OBJECT-TYPE
            SYNTAX      SEQUENCE OF FlWorkTimeSynchPTPPortEntry
            MAX-ACCESS  not-accessible
            STATUS      current
            DESCRIPTION
                "Table of network ports with Precision time protocol informational or configuration objects."
        ::= { flWorkTimeSynchPTP 1 }

    flWorkTimeSynchPTPPortEntry
        OBJECT-TYPE
            SYNTAX      FlWorkTimeSynchPTPPortEntry
            MAX-ACCESS  not-accessible
            STATUS      current
            DESCRIPTION
                "An entry in the table, containing information
                 of one network port concerning precistion time protocol."
            INDEX       { flWorkTimeSynchPTPPortIndex }
        ::= { flWorkTimeSynchPTPPortTable 1 }

    FlWorkTimeSynchPTPPortEntry
        ::= SEQUENCE {
            flWorkTimeSynchPTPPortIndex
                Integer32,
            flWorkTimeSynchPTPPortAdminStatus
                INTEGER
        }

    flWorkTimeSynchPTPPortIndex
        OBJECT-TYPE
            SYNTAX      Integer32 (1..1024)
            MAX-ACCESS  read-only
            STATUS      current
            DESCRIPTION
                "This object identifies the port. This value
                 is never greater then flWorkNetPortCapacity."
        ::= { flWorkTimeSynchPTPPortEntry 1 }

    flWorkTimeSynchPTPPortAdminStatus
        OBJECT-TYPE
            SYNTAX      INTEGER {
                            rxAndTx(1),
                            rxOnly(2)
                            }
            MAX-ACCESS  read-write
            STATUS      current
            DESCRIPTION
                "Determines if the precision time protocol
                 is fully enabled on this port or not.
                 rxAndTx means that the protocol is operational
                 on this port. rxOnly means that no PTCP frames are
                 transmitted any more.
                 Setting this object only has effect on the network
                 traffic if PTCP is globally enabled."
        ::= { flWorkTimeSynchPTPPortEntry 2 }

    --
    -- END OF flWorkTimeSynchPTP Group
    --

	
    --
    -- flWorkWlan Group (Level 3)
    --
	------------------------------
	------------------------------   	
	--    === (Level 4) ===    --
	------------------------------
    flWorkWlanOpMode
    	OBJECT-TYPE
    		SYNTAX INTEGER {
        		transbridge(1)
    		}
    		MAX-ACCESS  read-write
    		STATUS  current
    		DESCRIPTION
            		"Operational mode of the device. When operating as a transparent bridge, the device is acting like a layer2 bridge and is invisible to clients."
    	::= { flWorkWlan 10 }  
    
    flWorkWlanSetOnlyMode 
    	OBJECT-TYPE
    		SYNTAX INTEGER {
    				disabled(0),
    				enabled(1)
    		}
    		MAX-ACCESS  read-write
    		STATUS  current
    		DESCRIPTION
            		"Enabling this variable enables the set only mode of the FL WLAN AP/EC/DAP devices. In this mode, the automatic
            		consistency check of the device configuration is switched off.
					A WLAN Device should be set to the set only mode, if several SNMP parameters are set by consecutive SNMP set commands
					in order to disable the automatic configuration check of the FL WLAN AP/EC/DAP devices until the last SNMP 
					variable is set. Otherwise consecutive SNMP set commands can lead to temporarly inconsistent configurations (like
					WLAN channel 7 is chosen, although the device is still set to 802.11a mode).
					To commit changed parametes reset this variable to disabled(0).
					When this object is triggered to commit all parameters, the automatic configuration check is
					done and enabled in the devices again and the parameters are stored if the consistency check was successfull."
    	::= { flWorkWlan 11 }
		
	flWorkWlanCountry 
    	OBJECT-TYPE
    		SYNTAX  OCTET STRING (SIZE(1..25))
    		MAX-ACCESS  read-write
    		STATUS  current
    		DESCRIPTION
            		"Country setting of the device"
    	::= { flWorkWlan 12 }
    	 
    flWorkWlanIf1
    	OBJECT IDENTIFIER ::= { flWorkWlan 20 }
    
    flWorkWlanIf2
    	OBJECT IDENTIFIER ::= { flWorkWlan 30 }   
    	
    flWorkWlanMacFilter
    	OBJECT IDENTIFIER ::= { flWorkWlan 40 }   
    	
	------------------------------	
	--    === (Level 5) ===    --
	------------------------------
    -- Interface1
    flWorkWlanIf1Parameter
    	OBJECT IDENTIFIER ::= { flWorkWlanIf1 1 }

    flWorkWlanIf1Security
    	OBJECT IDENTIFIER ::= { flWorkWlanIf1 2 }

    flWorkWlanIf1FastRoaming		
    	OBJECT IDENTIFIER ::= { flWorkWlanIf1 3 } 

	flWorkWlanIf1Mcast
		OBJECT IDENTIFIER ::= { flWorkWlanIf1 4 }
		
	-- Interface2
	flWorkWlanIf2Parameter
    	OBJECT IDENTIFIER ::= { flWorkWlanIf2 1 }

    flWorkWlanIf2Security
    	OBJECT IDENTIFIER ::= { flWorkWlanIf2 2 }

    	
	------------------------------  	
	--    === (Level 6) ===    --
	------------------------------
	
	--
   	-- flWorkWlanIf1Parameter Group
   	--
   
   flWorkWlanIf1ParamState
		OBJECT-TYPE
			SYNTAX  EnabledDisabledStatus
			MAX-ACCESS  read-write
			STATUS  current
			DESCRIPTION
					"State of this interface. It may be enabled or disabled."
		::= { flWorkWlanIf1Parameter 1 }

   flWorkWlanIf1ParamOpMode
		OBJECT-TYPE
			SYNTAX  OpModeType
			MAX-ACCESS  read-write
			STATUS  current
			DESCRIPTION
			"This textual convention is used to distinguish the WIFI operation mode of a device.
			 station: 0
			 access point (master): 1
			 single client bridge (scb): 2
			 multi client bridge (mcb): 3
			 fully transparent bridge (ftb): 4
			 repeater : 5
			 machine admin : 6"
		::= { flWorkWlanIf1Parameter 2 }

   flWorkWlanIf1ParamSSID
		OBJECT-TYPE
			SYNTAX  OCTET STRING (SIZE(1..32))
			MAX-ACCESS  read-write
			STATUS  current
			DESCRIPTION
					"SSID (Service Set Identifier) for this interface. An SSID can be up to 32 characters long. Only letters, digits and the special characters: '@!$%&/()=?{}[]+*~#-_.:,;<>' are allowed."
		::= { flWorkWlanIf1Parameter 3 }

   flWorkWlanIf1ParamMode
		OBJECT-TYPE
			SYNTAX  INTEGER { abg(0), a(1), b(2), bg(3), an(4), gn(5) }
			MAX-ACCESS  read-write
			STATUS  current
			DESCRIPTION
					"Operation mode of this interface. 1=802.11a, 2=802.11b. 3=802.11b/g,  4=802.11a/n and 5=802.11g/n for master only."
		::= { flWorkWlanIf1Parameter 4 }

   flWorkWlanIf1ParamChannel
		OBJECT-TYPE
			SYNTAX  INTEGER(0..255)
			MAX-ACCESS  read-write
			STATUS  current
			DESCRIPTION
					"Channel of this interface. This depends on your regional limitations and selected wlanMode.
					-2.4GHz Band ------
					Auto            (0)
					Channel-1       (1)
					Channel-2       (2)
					Channel-3       (3)
					Channel-4       (4)
					Channel-5       (5)
					Channel-6       (6)
					Channel-7       (7)
					Channel-8       (8)
					Channel-9       (9)
					Channel-10     (10)
					Channel-11     (11)
					Channel-12     (12)
					Channel-13     (13)
					Channel-14     (14)
					--------------------
					====================
					-5GHz Band --------
					Channel-36     (36)
					Channel-40     (40)
					Channel-44     (44)
					Channel-48     (48)
					Channel-52     (52)
					Channel-56     (56)
					Channel-60     (60)
					Channel-64     (64)
					Channel-132   (132)
					Channel-136   (136)
					Channel-140   (140)
					Channel-149   (149)
					Channel-153   (153)
					Channel-157   (157)
					Channel-161   (161)
					Channel-165   (165)
					Indoor8-Auto  (200)
					Indoor16-Auto (201)
					Outdoor       (202)
					Auto          (203)
					--------------------"
		::= { flWorkWlanIf1Parameter 5 }

   flWorkWlanIf1ParamOutdoor
		OBJECT-TYPE
			SYNTAX  EnabledDisabledStatus
			MAX-ACCESS  read-write
			STATUS  current
			DESCRIPTION
					"If this interface is operating in 802.11a mode it must be distinguished between outdoor or indoor operation."
		::= { flWorkWlanIf1Parameter 6 }

   flWorkWlanIf1AntennaOutput
		OBJECT-TYPE
			SYNTAX  INTEGER(1..7)
			MAX-ACCESS  read-write
			STATUS  current
			DESCRIPTION
					"Mask for rx/tx-Antenna X5(1),X6(2),X7(4). e.g. Set (6) to enable x6 and x7 for rx and tx."
		::= { flWorkWlanIf1Parameter 7 }

   flWorkWlanIf1OutputPower
		OBJECT-TYPE
			SYNTAX  INTEGER(3..23)
			MAX-ACCESS  read-write
			STATUS  current
			DESCRIPTION
					"Set output power of WLAN interface. Current output power can be lower as defined due to regulatory limitations."
		::= { flWorkWlanIf1Parameter 8 }

   flWorkWlanIf1STBC
		OBJECT-TYPE
			SYNTAX  INTEGER { disable(1), enable(2)}
			MAX-ACCESS  read-write
			STATUS  current
			DESCRIPTION
					"Set output power of WLAN interface. Current output power can be lower as defined due to regulatory limitations."
		::= { flWorkWlanIf1Parameter 9 }

   flWorkWlanIf1Fragmentation
		OBJECT-TYPE
			SYNTAX  INTEGER(0..2600)
			MAX-ACCESS  read-write
			STATUS  current
			DESCRIPTION
					"Set fragmentation thresholds."
		::= { flWorkWlanIf1Parameter 10 }

   flWorkWlanIf1RtsCts
		OBJECT-TYPE
			SYNTAX  INTEGER(0..2600)
			MAX-ACCESS  read-write
			STATUS  current
			DESCRIPTION
					"Set RTS/CTS values."
		::= { flWorkWlanIf1Parameter 11 }

   flWorkWlanIf1LongDistance
		OBJECT-TYPE
			SYNTAX  INTEGER(3000..50000)
			MAX-ACCESS  read-write
			STATUS  current
			DESCRIPTION
					"Set Parameters for long distance link (meter). This Parameter must be equal at 
					master and station. Normal mode: 3000 meters.
						"
		::= { flWorkWlanIf1Parameter 12 }
    		
    		
   flWorkWlanIf1ScbMacAddress
		OBJECT-TYPE
			SYNTAX		MacAddress
			MAX-ACCESS	read-write
			STATUS		current
			DESCRIPTION
				"Mac address of the Device in SCB Mode."
		::= { flWorkWlanIf1Parameter 13 }
    		
   flWorkWlanIf1ScbManMacMode
		OBJECT-TYPE
			SYNTAX      INTEGER {
										disable(0),
										enable(1)
								 }
			MAX-ACCESS	read-write
			STATUS		current
			DESCRIPTION
				"Mac-Address assignment method in SCB Mode 
						   disable(0) = Automatic mode. The device adopts the Mac-Address from the connected ethernet device.
						   enable(1)  = Manual mode. Mac-Address is configured by flWorkWlanIf1ScbManMacMode "
		::= { flWorkWlanIf1Parameter 14 }
			
	flWorkWlanIf1IAPP
		OBJECT-TYPE
			SYNTAX      INTEGER {
										disable(0),
										enable(1)
								 }
			MAX-ACCESS	read-write
			STATUS		current
			DESCRIPTION
				"802.11f Inter Accesspoint Protocol (IAPP)
							 disable(0) = IAPP disabled
							 enable(1)  = IAPP enabled"
		::= { flWorkWlanIf1Parameter 15 }
	
	
    flWorkWlanIf1MachineAdmin
        OBJECT IDENTIFIER ::= {  flWorkWlanIf1Parameter 16 }


	--
   	-- flWorkWlanIf2Parameter Group
   	--
   
   flWorkWlanIf2ParamState
		OBJECT-TYPE
			SYNTAX  EnabledDisabledStatus
			MAX-ACCESS  read-write
			STATUS  current
			DESCRIPTION
					"State of this interface. It may be enabled or disabled."
		::= { flWorkWlanIf2Parameter 1 }

   flWorkWlanIf2ParamOpMode
		OBJECT-TYPE
			SYNTAX  OpModeType
			MAX-ACCESS  read-write
			STATUS  current
			DESCRIPTION
			"This textual convention is used to distinguish the WIFI operation mode of a device.
			 station: 0
			 access point (master): 1
			 single client bridge (scb): 2
			 multi client bridge (mcb): 3
			 fully transparent bridge (ftb): 4
			 repeater : 5
			 machine admin : 6"
		::= { flWorkWlanIf2Parameter 2 }

   flWorkWlanIf2ParamSSID
		OBJECT-TYPE
			SYNTAX  OCTET STRING (SIZE(1..32))
			MAX-ACCESS  read-write
			STATUS  current
			DESCRIPTION
					"SSID (Service Set Identifier) for this interface. An SSID can be up to 32 characters long. Only letters, digits and the special characters: '@!$%&/()=?{}[]+*~#-_.:,;<>' are allowed."
		::= { flWorkWlanIf2Parameter 3 }

   flWorkWlanIf2ParamMode
		OBJECT-TYPE
			SYNTAX  INTEGER { abg(0), a(1), b(2), bg(3), an(4), gn(5) }
			MAX-ACCESS  read-write
			STATUS  current
			DESCRIPTION
					"Operation mode of this interface. 1=802.11a, 2=802.11b. 3=802.11b/g,  4=802.11a/n and 5=802.11g/n for master only."
		::= { flWorkWlanIf2Parameter 4 }

   flWorkWlanIf2ParamChannel
		OBJECT-TYPE
			SYNTAX  INTEGER(0..255)
			MAX-ACCESS  read-write
			STATUS  current
			DESCRIPTION
					"Channel of this interface. This depends on your regional limitations and selected wlanMode.
					-2.4GHz Band ------
					Auto            (0)
					Channel-1       (1)
					Channel-2       (2)
					Channel-3       (3)
					Channel-4       (4)
					Channel-5       (5)
					Channel-6       (6)
					Channel-7       (7)
					Channel-8       (8)
					Channel-9       (9)
					Channel-10     (10)
					Channel-11     (11)
					Channel-12     (12)
					Channel-13     (13)
					Channel-14     (14)
					--------------------
					====================
					-5GHz Band --------
					Channel-36     (36)
					Channel-40     (40)
					Channel-44     (44)
					Channel-48     (48)
					Channel-52     (52)
					Channel-56     (56)
					Channel-60     (60)
					Channel-64     (64)
					Channel-132   (132)
					Channel-136   (136)
					Channel-140   (140)
					Channel-149   (149)
					Channel-153   (153)
					Channel-157   (157)
					Channel-161   (161)
					Channel-165   (165)
					Indoor8-Auto  (200)
					Indoor16-Auto (201)
					Outdoor       (202)
					Auto          (203)
					--------------------"
		::= { flWorkWlanIf2Parameter 5 }

   flWorkWlanIf2ParamOutdoor
		OBJECT-TYPE
			SYNTAX  EnabledDisabledStatus
			MAX-ACCESS  read-write
			STATUS  current
			DESCRIPTION
					"If this interface is operating in 802.11a mode it must be distinguished between outdoor or indoor operation."
		::= { flWorkWlanIf2Parameter 6 }

   flWorkWlanIf2AntennaOutput
		OBJECT-TYPE
			SYNTAX  INTEGER(1..7)
			MAX-ACCESS  read-write
			STATUS  current
			DESCRIPTION
					"Mask for rx/tx-Antenna X5(1),X6(2),X7(4). e.g. Set (6) to enable x6 and x7 for rx and tx."
		::= { flWorkWlanIf2Parameter 7 }

   flWorkWlanIf2OutputPower
		OBJECT-TYPE
			SYNTAX  INTEGER(3..23)
			MAX-ACCESS  read-write
			STATUS  current
			DESCRIPTION
					"Set output power of WLAN interface. Current output power can be lower as defined due to regulatory limitations."
		::= { flWorkWlanIf2Parameter 8 }

   flWorkWlanIf2STBC
		OBJECT-TYPE
			SYNTAX  INTEGER { disable(1), enable(2)}
			MAX-ACCESS  read-write
			STATUS  current
			DESCRIPTION
					"Set output power of WLAN interface. Current output power can be lower as defined due to regulatory limitations."
		::= { flWorkWlanIf2Parameter 9 }

   flWorkWlanIf2Fragmentation
		OBJECT-TYPE
			SYNTAX  INTEGER(0..2600)
			MAX-ACCESS  read-write
			STATUS  current
			DESCRIPTION
					"Set fragmentation thresholds."
		::= { flWorkWlanIf2Parameter 10 }

   flWorkWlanIf2RtsCts
		OBJECT-TYPE
			SYNTAX  INTEGER(0..2600)
			MAX-ACCESS  read-write
			STATUS  current
			DESCRIPTION
					"Set RTS/CTS values."
		::= { flWorkWlanIf2Parameter 11 }

   flWorkWlanIf2LongDistance
		OBJECT-TYPE
			SYNTAX  INTEGER(3000..50000)
			MAX-ACCESS  read-write
			STATUS  current
			DESCRIPTION
					"Set Parameters for long distance link (meter). This Parameter must be equal at 
					master and station. Normal mode: 3000 meters.
						"
		::= { flWorkWlanIf2Parameter 12 }
    		
    		
   flWorkWlanIf2ScbMacAddress
		OBJECT-TYPE
			SYNTAX		MacAddress
			MAX-ACCESS	read-write
			STATUS		current
			DESCRIPTION
				"Mac address of the Device in SCB Mode."
		::= { flWorkWlanIf2Parameter 13 }
    		
   flWorkWlanIf2ScbManMacMode
		OBJECT-TYPE
			SYNTAX      INTEGER {
										disable(0),
										enable(1)
								 }
			MAX-ACCESS	read-write
			STATUS		current
			DESCRIPTION
				"Mac-Address assignment method in SCB Mode 
						   disable(0) = Automatic mode. The device adopts the Mac-Address from the connected ethernet device.
						   enable(1)  = Manual mode. Mac-Address is configured by flWorkWlanIf2ScbManMacMode "
		::= { flWorkWlanIf2Parameter 14 }
			
	flWorkWlanIf2IAPP
		OBJECT-TYPE
			SYNTAX      INTEGER {
										disable(0),
										enable(1)
								 }
			MAX-ACCESS	read-write
			STATUS		current
			DESCRIPTION
				"802.11f Inter Accesspoint Protocol (IAPP)
							 disable(0) = IAPP disabled
							 enable(1)  = IAPP enabled"
		::= { flWorkWlanIf2Parameter 15 }
	
	
    flWorkWlanIf2MachineAdmin
        OBJECT IDENTIFIER ::= {  flWorkWlanIf2Parameter 16 }
   
	------------------------------
	--    === (Level 7) ===    --
	------------------------------
	--
	-- flWorkWlanIf1MachineAdmin Group
	--
	               
	flWorkWlanIf1MachineAdminSSID
		OBJECT-TYPE
			SYNTAX  OCTET STRING (SIZE(1..32))
			MAX-ACCESS  read-write
			STATUS  current
			DESCRIPTION
					"SSID (Service Set Identifier) for the Machine Admin WLAN. An SSID can be up to 32 characters long. Only letters, digits and the special characters: '@!$%&/()=?{}[]+*~#-_.:,;<>' are allowed."
		::= { flWorkWlanIf1MachineAdmin 1 }
						
	flWorkWlanIf1MachineAdminPsk
		OBJECT-TYPE
			SYNTAX  OCTET STRING (SIZE(8..63))
			MAX-ACCESS  read-write
			STATUS  current
			DESCRIPTION
					"Passphrase for the Machine Admin SSID. NOTE: You should use a randomly generated
					 alphanumeric sequence (up to 63 at least 8 characters) for maximum security."
		::= { flWorkWlanIf1MachineAdmin 2 }
				 
	flWorkWlanIf1MachineAdminIp
		OBJECT-TYPE
			SYNTAX      IpAddress
			MAX-ACCESS  read-write
			STATUS      current
			DESCRIPTION
			   "The IPv4 address of the device which should be accessible vie the Machine Admin SSID"
		::= { flWorkWlanIf1MachineAdmin 3 }
		
		
	--
	-- flWorkWlanIf2MachineAdmin Group
	--
	               
	flWorkWlanIf2MachineAdminSSID
		OBJECT-TYPE
			SYNTAX  OCTET STRING (SIZE(1..32))
			MAX-ACCESS  read-write
			STATUS  current
			DESCRIPTION
					"SSID (Service Set Identifier) for the Machine Admin WLAN. An SSID can be up to 32 characters long. Only letters, digits and the special characters: '@!$%&/()=?{}[]+*~#-_.:,;<>' are allowed."
		::= { flWorkWlanIf2MachineAdmin 1 }
						
	flWorkWlanIf2MachineAdminPsk
		OBJECT-TYPE
			SYNTAX  OCTET STRING (SIZE(8..63))
			MAX-ACCESS  read-write
			STATUS  current
			DESCRIPTION
					"Passphrase for the Machine Admin SSID. NOTE: You should use a randomly generated
					 alphanumeric sequence (up to 63 at least 8 characters) for maximum security."
		::= { flWorkWlanIf2MachineAdmin 2 }
				 
	flWorkWlanIf2MachineAdminIp
		OBJECT-TYPE
			SYNTAX      IpAddress
			MAX-ACCESS  read-write
			STATUS      current
			DESCRIPTION
			   "The IPv4 address of the device which should be accessible vie the Machine Admin SSID"
		::= { flWorkWlanIf2MachineAdmin 3 }	
	        
   --
   --
   -- flWorkWlanIf1FastRoaming Group
   --
   
   flWorkWlanIf1FastRoamingTable 
		OBJECT-TYPE
			SYNTAX     SEQUENCE OF FlWorkWlanIf1FastRoamingEntry
			MAX-ACCESS     not-accessible
			STATUS     current
			DESCRIPTION
					"Fast roaming table for all wlan interfaces."
		::= { flWorkWlanIf1FastRoaming 1 }

   flWorkWlanIf1FastRoamingEntry 
		OBJECT-TYPE
			SYNTAX     FlWorkWlanIf1FastRoamingEntry
			MAX-ACCESS     not-accessible
			STATUS     current
			DESCRIPTION
					"An entry (conceptual row) in the wlanFastRoamingFilterTable."
			INDEX      { flWorkWlanIf1FastRoamingEntryIdx }
		::= { flWorkWlanIf1FastRoamingTable 1 }

   FlWorkWlanIf1FastRoamingEntry ::= SEQUENCE {
			flWorkWlanIf1FastRoamingEntryIdx	     	INTEGER,
			flWorkWlanIf1FastRoamingEntryThreshold	INTEGER,
			flWorkWlanIf1FastRoamingEntryChannel		INTEGER,
			flWorkWlanIf1FastRoamingEntryAddress	     	MacAddress
		}

   flWorkWlanIf1FastRoamingEntryIdx 
		OBJECT-TYPE
			SYNTAX     INTEGER (0..49)
			MAX-ACCESS     not-accessible
			STATUS     current
			DESCRIPTION
					"Index in the wlanFastRoamingFilterTable."
		::= { flWorkWlanIf1FastRoamingEntry 1 }

   flWorkWlanIf1FastRoamingEntryThreshold 
		OBJECT-TYPE
			SYNTAX     INTEGER (10..60)
			MAX-ACCESS     read-write
			STATUS     current
			DESCRIPTION
					"SNR threshold when to this access point should be roamed."
		::= { flWorkWlanIf1FastRoamingEntry 2 }

   flWorkWlanIf1FastRoamingEntryChannel 
		OBJECT-TYPE
			SYNTAX     INTEGER (0..255)
			MAX-ACCESS     read-write
			STATUS     current
			DESCRIPTION
					"Channel for this entry. 0 for any."
		::= { flWorkWlanIf1FastRoamingEntry 3 }

   flWorkWlanIf1FastRoamingEntryAddress 
		OBJECT-TYPE
			SYNTAX     MacAddress
			MAX-ACCESS     read-write
			STATUS     current
			DESCRIPTION
					"MAC address of this entry."
		::= { flWorkWlanIf1FastRoamingEntry 4 }

   flWorkWlanIf1FastRoamingEnabled 
		OBJECT-TYPE
			SYNTAX     EnabledDisabledStatus
			MAX-ACCESS     read-write
			STATUS     current
			DESCRIPTION
					"Enables the client its Modbus/TCP API. A PLC may then query the current position in the list or explicitly trigger fast roaming to any position."
		::= { flWorkWlanIf1FastRoaming 2 }

   flWorkWlanIf1FastRoamToAP 
		OBJECT-TYPE
			SYNTAX     INTEGER (0..49)
			MAX-ACCESS     read-write
			STATUS     current
			DESCRIPTION
					"Triggers immedeately fast roaming to the access point with the specified index."
		::= { flWorkWlanIf1FastRoaming 3 }	        
	        
   --
   --
   -- flWorkWlanIf1Mcast Group
   --
   flWorkWlanIf1McastEnhance
		OBJECT-TYPE
			SYNTAX		INTEGER { disable (0), tunneling (1), translating (2), adv-tunnel (3) }
			MAX-ACCESS		read-write
			STATUS		current
			DESCRIPTION
					"Sets the multicast enhancement mode to either tunneling, translating or adv_tunnel."
		::= { flWorkWlanIf1Mcast 1 }
			
   flWorkWlanIf1McastDrop
		OBJECT-TYPE
			SYNTAX		INTEGER { disable (0), learned (1), all (2) }
			MAX-ACCESS		read-write
			STATUS		current
			DESCRIPTION
					"Allows different levels of dropping unknown or unneeded IP multicast traffic."
		::= { flWorkWlanIf1Mcast 2 }
			
   flWorkWlanIf1McastAutoAdd
		OBJECT-TYPE
			SYNTAX		EnabledDisabledStatus
			MAX-ACCESS		read-write
			STATUS		current
			DESCRIPTION
					"Enabling this function leads to an automatic adding of newly connected WLAN clients to all already learned multicast groups."
		::= { flWorkWlanIf1Mcast 3 }
			
   flWorkWlanIf1McastAdvSnooping
		OBJECT-TYPE
			SYNTAX		EnabledDisabledStatus
			MAX-ACCESS		read-write
			STATUS		current
			DESCRIPTION
					"By enabling this option also snooping of normal ongoing multicast traffic on the Ethernet interface is done to learn multicast groups."
		::= { flWorkWlanIf1Mcast 4}
	
   flWorkWlanIf1McastTable
		OBJECT-TYPE
			SYNTAX		SEQUENCE OF FlWorkWlanIf1McastEntry
			MAX-ACCESS		not-accessible
			STATUS		current
			DESCRIPTION
					"Table of all multicast groups learned for the WLAN interface via IGMP snooping."
		::= { flWorkWlanIf1Mcast 10 }
			
   flWorkWlanIf1McastEntry
		OBJECT-TYPE
			SYNTAX		FlWorkWlanIf1McastEntry
			MAX-ACCESS		not-accessible
			STATUS		current
			DESCRIPTION
					"An entry (conceptual row) in the flWorkWlanIf1McastTable."
			INDEX		{ flWorkWlanIf1McastTableEntryIdx }
		::= { flWorkWlanIf1McastTable 1 }
			
   FlWorkWlanIf1McastEntry ::= SEQUENCE {
				flWorkWlanIf1McastTableEntryIdx		INTEGER,
				flWorkWlanIf1McastTableEntryGroup	MacAddress,
				flWorkWlanIf1McastTableEntryMember	MacAddress,
				flWorkWlanIf1McastTableEntrySta		MacAddress
			}
			
   flWorkWlanIf1McastTableEntryIdx
		OBJECT-TYPE
			SYNTAX		INTEGER (0..31)
			MAX-ACCESS		not-accessible
			STATUS		current
			DESCRIPTION
				"Index of the flWorkWlanIf1McastTable."
		::= { flWorkWlanIf1McastEntry 1 }
	
   flWorkWlanIf1McastTableEntryGroup 
		OBJECT-TYPE
			SYNTAX     MacAddress
			MAX-ACCESS     read-only
			STATUS     current
			DESCRIPTION
					"Group MAC address learned via snooping."
		::= { flWorkWlanIf1McastEntry 2 }
	
	flWorkWlanIf1McastTableEntryMember 
		OBJECT-TYPE
			SYNTAX     MacAddress
			MAX-ACCESS     read-only
			STATUS     current
			DESCRIPTION
					"MAC address of a member of the learned multicast group."
		::= { flWorkWlanIf1McastEntry 3 }

	flWorkWlanIf1McastTableEntrySta 
		OBJECT-TYPE
			SYNTAX     MacAddress
			MAX-ACCESS     read-only
			STATUS     current
			DESCRIPTION
					"MAC address of the wlan station/client the member is connected to."
		::= { flWorkWlanIf1McastEntry 4 }

	flWorkWlanIf1McastDenyConfig
			OBJECT IDENTIFIER ::= { flWorkWlanIf1Mcast 20 }
	
	flWorkWlanIf1McastDenyCreate
		OBJECT-TYPE
			SYNTAX		IpAddress
			MAX-ACCESS		read-write
			STATUS		current
			DESCRIPTION
					"Add an IP Multicast Group to the Denylist. This multicast group is then exempted form
					special multicast handling. Get operation is meaningless, as this object is only meant 
					to be used for adding IP Multicast Groups to the list."
		::= { flWorkWlanIf1McastDenyConfig 1 }
	
   flWorkWlanIf1McastDenyTable
		OBJECT-TYPE
			SYNTAX		SEQUENCE OF FlWorkWlanIf1McastDenyEntry
			MAX-ACCESS		not-accessible
			STATUS		current
			DESCRIPTION
					"Table of IP multicast groups which are exempted from the special multicast enhancements."
		::= { flWorkWlanIf1McastDenyConfig 2 }
			
   flWorkWlanIf1McastDenyEntry
		OBJECT-TYPE
			SYNTAX		FlWorkWlanIf1McastDenyEntry
			MAX-ACCESS		not-accessible
			STATUS		current
			DESCRIPTION
					"An entry (conceptual row) in the flWorkWlanIf1McastDenyTable."
			INDEX		{ flWorkWlanIf1McastDenyTableEntryIdx }
		::= { flWorkWlanIf1McastDenyTable 1 }
			
   FlWorkWlanIf1McastDenyEntry ::= SEQUENCE {
				flWorkWlanIf1McastDenyTableEntryIdx		INTEGER,
				flWorkWlanIf1McastDenyTableEntryGroup	IpAddress,
				flWorkWlanIf1McastDenyTableEntryStatus	RowStatus
			}
			
   flWorkWlanIf1McastDenyTableEntryIdx
		OBJECT-TYPE
			SYNTAX		INTEGER (0..31)
			MAX-ACCESS		not-accessible
			STATUS		current
			DESCRIPTION
				"Index of the flWorkWlanIf1McastTable."
		::= { flWorkWlanIf1McastDenyEntry 1 }
	
   flWorkWlanIf1McastDenyTableEntryGroup 
		OBJECT-TYPE
			SYNTAX     IpAddress
			MAX-ACCESS     read-only
			STATUS     current
			DESCRIPTION
					"IP group address which is exempted from special wlan multicast treatment."
		::= { flWorkWlanIf1McastDenyEntry 2 }
	
	flWorkWlanIf1McastDenyTableEntryStatus
		OBJECT-TYPE
			SYNTAX		RowStatus
			MAX-ACCESS		read-write
			STATUS		current
			DESCRIPTION
					"active(1)  - This multicast group is active.
					 destroy(6) - Set to this value to remove the multicast group from the list."
		::= { flWorkWlanIf1McastDenyEntry 3 }	        
	       
	       
   --
   --
   -- flWorkWlanIf1Stations Table
   --
   
   flWorkWlanIf1StationsTable 
		OBJECT-TYPE
			SYNTAX     SEQUENCE OF FlWorkWlanIf1StationsEntry
			MAX-ACCESS     not-accessible
			STATUS     current
			DESCRIPTION
					"Table of all associated stations to this interface."
		::= { flWorkWlanIf1 10 }

   flWorkWlanIf1StationsEntry 
		OBJECT-TYPE
			SYNTAX     FlWorkWlanIf1StationsEntry
			MAX-ACCESS     not-accessible
			STATUS     current
			DESCRIPTION
					"An entry (conceptual row) in the wlanStationTable."
			INDEX      { flWorkWlanIf1StationEntryIdx }
		::= { flWorkWlanIf1StationsTable 1 }

   FlWorkWlanIf1StationsEntry ::= SEQUENCE {
    			flWorkWlanIf1StationEntryIdx	     	INTEGER,
    			flWorkWlanIf1StationEntrySNR	        INTEGER,
    			flWorkWlanIf1StationEntryRate		INTEGER,
    			flWorkWlanIf1StationEntryPower		INTEGER,    
    			flWorkWlanIf1StationEntryAddress	     	MacAddress
			}

   flWorkWlanIf1StationEntryIdx 
		OBJECT-TYPE
			SYNTAX     INTEGER (0..49)
			MAX-ACCESS     not-accessible
			STATUS     current
			DESCRIPTION
					"Index in the wlanStationTableIf1."
		::= { flWorkWlanIf1StationsEntry 1 }

   flWorkWlanIf1StationEntrySNR 
		OBJECT-TYPE
			SYNTAX     INTEGER (10..60)
			MAX-ACCESS     read-only
			STATUS     current
			DESCRIPTION
					"SNR of this station."
		::= { flWorkWlanIf1StationsEntry 2 }

   flWorkWlanIf1StationEntryRate 
		OBJECT-TYPE
			SYNTAX     INTEGER (0..255)
			MAX-ACCESS     read-only
			STATUS     current
			DESCRIPTION
					"TX-Rate of this station."
		::= { flWorkWlanIf1StationsEntry 3 }

   flWorkWlanIf1StationEntryPower 
		OBJECT-TYPE
			SYNTAX     INTEGER (0..255)
			MAX-ACCESS     read-only
			STATUS     current
			DESCRIPTION
					"TX-Power of this station."
		::= { flWorkWlanIf1StationsEntry 4 }

   flWorkWlanIf1StationEntryAddress 
		OBJECT-TYPE
			SYNTAX     MacAddress
			MAX-ACCESS     read-only
			STATUS     current
			DESCRIPTION
					"MAC address of this station."
		::= { flWorkWlanIf1StationsEntry 5 }	       
	       

   --
   --
   -- flWorkWlanIf1VisibleAccessPoints Table
   --
   flWorkWlanIf1VisibleAccessPointTable 
   			OBJECT-TYPE
    			SYNTAX     SEQUENCE OF FlWorkWlanIf1VisibleAccessPointEntry
    			MAX-ACCESS     not-accessible
    			STATUS     current
    			DESCRIPTION
            			"Table of all VisibleAccessPoints to this interface."
    		::= { flWorkWlanIf1 20 }

   flWorkWlanIf1VisibleAccessPointEntry 
   			OBJECT-TYPE
    			SYNTAX     FlWorkWlanIf1VisibleAccessPointEntry
    			MAX-ACCESS     not-accessible
    			STATUS     current
    			DESCRIPTION
            			"An entry (conceptual row) in the wlanVisibleAccessPointTable."
    			INDEX      { flWorkWlanIf1VisibleAccessPointEntryIdx }
    		::= { flWorkWlanIf1VisibleAccessPointTable 1 }

   FlWorkWlanIf1VisibleAccessPointEntry ::= SEQUENCE {
   			 	flWorkWlanIf1VisibleAccessPointEntryIdx	     	INTEGER,
    			flWorkWlanIf1VisibleAccessPointEntrySNR	        INTEGER,
    			flWorkWlanIf1VisibleAccessPointEntryChannel	INTEGER,
    			flWorkWlanIf1VisibleAccessPointEntryPower		INTEGER,  
    			flWorkWlanIf1VisibleAccessPointEntrySSID		OCTET STRING,
    			flWorkWlanIf1VisibleAccessPointEntrySecurity	OCTET STRING,    
    			flWorkWlanIf1VisibleAccessPointEntryAddress	MacAddress,
    			flWorkWlanIf1VisibleAccessPointEntryConnected	INTEGER,
    			flWorkWlanIf1VisibleAccessPointEntryRSSI		INTEGER,
    			flWorkWlanIf1VisibleAccessPointEntryNoise	INTEGER    
			}

   flWorkWlanIf1VisibleAccessPointEntryIdx 
   			OBJECT-TYPE
    			SYNTAX     INTEGER (0..49)
    			MAX-ACCESS     not-accessible
    			STATUS     current
    			DESCRIPTION
            			"Index in the wlanVisibleAccessPointTableIf1."
   			::= { flWorkWlanIf1VisibleAccessPointEntry 1 }
			
   flWorkWlanIf1VisibleAccessPointEntrySNR 
   			OBJECT-TYPE
    			SYNTAX     INTEGER (10..60)
    			MAX-ACCESS     read-only
    			STATUS     current
    			DESCRIPTION
            			"SNR of this visible access point."
    		::= { flWorkWlanIf1VisibleAccessPointEntry 2 }

   flWorkWlanIf1VisibleAccessPointEntryChannel 
   			OBJECT-TYPE
    			SYNTAX     INTEGER (0..255)
    			MAX-ACCESS     read-only
    			STATUS     current
    			DESCRIPTION
            			"TX-Rate of this visible access point."
    		::= { flWorkWlanIf1VisibleAccessPointEntry 3 }

   flWorkWlanIf1VisibleAccessPointEntryPower 
   			OBJECT-TYPE
    			SYNTAX     INTEGER (0..255)
    			MAX-ACCESS     read-only
    			STATUS     current
    			DESCRIPTION
            			"TX-Power of this visible access point."
    		::= { flWorkWlanIf1VisibleAccessPointEntry 4 }

   flWorkWlanIf1VisibleAccessPointEntrySSID 
   			OBJECT-TYPE
    			SYNTAX     OCTET STRING
    			MAX-ACCESS     read-only
    			STATUS     current
    			DESCRIPTION
            			"SSID of this visible access point."
    		::= { flWorkWlanIf1VisibleAccessPointEntry 5 }

   flWorkWlanIf1VisibleAccessPointEntrySecurity 
   			OBJECT-TYPE
    			SYNTAX     OCTET STRING
    			MAX-ACCESS     read-only
    			STATUS     current
    			DESCRIPTION
            			"Security of this visible access point."
    		::= { flWorkWlanIf1VisibleAccessPointEntry 6 }

   flWorkWlanIf1VisibleAccessPointEntryAddress 
   			OBJECT-TYPE
    			SYNTAX     MacAddress
    			MAX-ACCESS     read-only
    			STATUS     current
    			DESCRIPTION
            			"MAC address of this visible access point."
    		::= { flWorkWlanIf1VisibleAccessPointEntry 7 }
    
   flWorkWlanIf1VisibleAccessPointEntryConnected 
   			OBJECT-TYPE
    			SYNTAX     INTEGER { not-connected(0), connected(1) }
    			MAX-ACCESS     read-only
    			STATUS     current
    			DESCRIPTION
            		"This object shows, if the client is connected to this visible access point."
    		::= { flWorkWlanIf1VisibleAccessPointEntry 8 }  
   
   flWorkWlanIf1VisibleAccessPointEntryRSSI
   			OBJECT-TYPE
   				SYNTAX		INTEGER { not-connected(0), connected(1) }
   				MAX-ACCESS		read-only
   				STATUS		current
   				DESCRIPTION
   					"This object gives back the RSSI value, i.e. the signal strength of the visible AP. "
   			::= { flWorkWlanIf1VisibleAccessPointEntry 9 }
   	
   	flWorkWlanIf1VisibleAccessPointEntryNoise
   			OBJECT-TYPE
   				SYNTAX		INTEGER
   				MAX-ACCESS 		read-only
   				STATUS		current
   				DESCRIPTION
   					"This value shows the noise floor for the connection to the visible AP."
   			::= { flWorkWlanIf1VisibleAccessPointEntry 10 }
            
	       
	          
        
   --
   --
   -- flWorkWlanIf1Security Group
   --
   
   flWorkWlanIf1SecMode
   			OBJECT-TYPE
    			SYNTAX  INTEGER { none(0), wpa-psk(1), wep64(2), wep128(3), wpa2-psk(4), wpa2-eap(5) }
    			MAX-ACCESS  read-write
    			STATUS  current
    			DESCRIPTION
            			"Type of encryption of the wireless link. One of 'none', 'wpa-psk', 'wep64', 'wep128','wpa2-psk', 'wpa2-eap'."
    		::= { flWorkWlanIf1Security 1 }

   flWorkWlanIf1SecWpaEncryptionAlgorithm
   			OBJECT-TYPE
    			SYNTAX  INTEGER { tkip(1), aes(2), both(3) }
    			MAX-ACCESS  read-write
    			STATUS  current
    			DESCRIPTION
            			"Encryption algorithm. 1=TKIP is used on old hardware not supporting AES.
                                   			2=AES is more secure and faster on station roaming.
                                   			3=both."
    		::= { flWorkWlanIf1Security 2 }

  flWorkWlanIf1SecWpaPsk 
  			OBJECT-TYPE
    			SYNTAX  OCTET STRING (SIZE(8..63))
    			MAX-ACCESS  read-write
    			STATUS  current
    			DESCRIPTION
            			"Initial key for WPA encryption. NOTE: You should use a randomly generated 
             			alphanumeric sequence (up to 63 at least 8 characters) for maximum security."
    		::= { flWorkWlanIf1Security 3 }

   flWorkWlanIf1SecWepAuthType 
   			OBJECT-TYPE
    			SYNTAX  INTEGER {open-system(1), shared-key(2), automatic(3) }
    			MAX-ACCESS  read-write
    			STATUS  current
    			DESCRIPTION
            			"1=Open-System, 2=Shared-Key and 3=Automatic, the default."
    		::= { flWorkWlanIf1Security 4 }

   flWorkWlanIf1SecWepKeyEncoding 
   			OBJECT-TYPE
    			SYNTAX  INTEGER {hex(0), ascii(1) }
    			MAX-ACCESS  read-write
    			STATUS  current
    			DESCRIPTION
            			"If this WEP passphrase is 'hex' or 'ascii'."
    		::= { flWorkWlanIf1Security 5 }

   flWorkWlanIf1SecWepKey 
   			OBJECT-TYPE
   	 			SYNTAX  OCTET STRING (SIZE(5..26))
    			MAX-ACCESS  read-write
    			STATUS  current
    			DESCRIPTION
            			"The WEP passphrase."
    		::= { flWorkWlanIf1Security 6 }

   --
   --
   -- flWorkWlanIf2Security Group
   --
   
   flWorkWlanIf2SecMode 
   			OBJECT-TYPE
    			SYNTAX  INTEGER { none(0), wpa-psk(1), wpa2-psk(4), wpa2-eap(5) }
    			MAX-ACCESS  read-write
    			STATUS  current
    			DESCRIPTION
            			"Type of encryption of the wireless link. One of 'none', 'wpa-psk', 'wep64' or 'wep128'."
    		::= { flWorkWlanIf2Security 1 }

   flWorkWlanIf2SecWpaEncryptionAlgorithm 
   			OBJECT-TYPE
    			SYNTAX  INTEGER { tkip(1), aes(2), both(3) }
    			MAX-ACCESS  read-write
    			STATUS  current
    			DESCRIPTION
            			"Encryption algorithm. 1=TKIP is used on old hardware not supporting AES.
                                   			2=AES is more secure and faster on station roaming.
                                   			3=both."
    		::= { flWorkWlanIf2Security 2 }

   flWorkWlanIf2SecWpaPsk 
   			OBJECT-TYPE
    			SYNTAX  OCTET STRING (SIZE(8..63))
    			MAX-ACCESS  read-write
    			STATUS  current
    			DESCRIPTION
            			"Initial key for WPA encryption. NOTE: You should use a randomly generated 
             			alphanumeric sequence (up to 63 at least 8 characters) for maximum security."
    		::= { flWorkWlanIf2Security 3 }

   flWorkWlanIf2SecWepAuthType 
   			OBJECT-TYPE
    			SYNTAX  INTEGER {open-system(1), shared-key(2), automatic(3) }
    			MAX-ACCESS  read-write
    			STATUS  current
    			DESCRIPTION
            			"1=Open-System, 2=Shared-Key and 3=Automatic, the default."
    		::= { flWorkWlanIf2Security 4 }

   flWorkWlanIf2SecWepKeyEncoding
   			OBJECT-TYPE
    			SYNTAX  INTEGER {hex(0), ascii(1) }
    			MAX-ACCESS  read-write
    			STATUS  current
    			DESCRIPTION
            			"If this WEP passphrase is 'hex' or 'ascii'."
    		::= { flWorkWlanIf2Security 5 }

   flWorkWlanIf2SecWepKey 
   			OBJECT-TYPE
    			SYNTAX  OCTET STRING (SIZE(5..26))
    			MAX-ACCESS  read-write
    			STATUS  current
    			DESCRIPTION
            			"The WEP passphrase."
    		::= { flWorkWlanIf2Security 6 }

   --
   --
   -- flWorkWlanMacFilter Group
   --
   
   flWorkWlanMacPolicyIf1 
   			OBJECT-TYPE
    			SYNTAX     INTEGER {block(0), allow(1) }
    			MAX-ACCESS     read-write
    			STATUS     current
    			DESCRIPTION
            			"Mac filter table policy for this interface.
						Block any not specified clients or allow all not specified clients on WLAN-1"
    		::= { flWorkWlanMacFilter 2 }

   flWorkWlanMacPolicyIf2 
   			OBJECT-TYPE
    			SYNTAX     INTEGER {block(0), allow(1) }
    			MAX-ACCESS     read-write
    			STATUS     current
    			DESCRIPTION
            			"Mac filter table policy for this interface.
						Block any not specified clients or allow all not specified clients on WLAN-2"
    		::= { flWorkWlanMacFilter 3 }

   flWorkWlanMacFilterSyslog 
   			OBJECT-TYPE
    			SYNTAX     EnabledDisabledStatus
    			MAX-ACCESS     read-write
    			STATUS     current
    			DESCRIPTION
            			"Enable syslog warnings for default policy of Mac filter table."
    		::= { flWorkWlanMacFilter 4 }

   flWorkWlanMacFilterTable 
   			OBJECT-TYPE
    			SYNTAX     SEQUENCE OF FlWorkWlanMacFilterEntry
    			MAX-ACCESS     not-accessible
    			STATUS     current
    			DESCRIPTION
            			"Mac filter table for all wlan interfaces."
  			::= { flWorkWlanMacFilter 1 }

   flWorkWlanMacFilterEntry 
   			OBJECT-TYPE
    			SYNTAX     FlWorkWlanMacFilterEntry
    			MAX-ACCESS     not-accessible
    			STATUS     current
    			DESCRIPTION
            			"An entry (conceptual row) in the wlanMacFilterTable."
    			INDEX      { flWorkWlanMacEntryIdx }
    		::= { flWorkWlanMacFilterTable 1 }

   FlWorkWlanMacFilterEntry ::= SEQUENCE {
   				flWorkWlanMacEntryIdx	     	INTEGER,
    			flWorkWlanMacEntryInterfaceName	INTEGER,
    			flWorkWlanMacEntryAction		INTEGER,
    			flWorkWlanMacEntryAddress	     	MacAddress
			}

   flWorkWlanMacEntryIdx 
   			OBJECT-TYPE
    			SYNTAX     INTEGER (0..499)
    			MAX-ACCESS     not-accessible
    			STATUS     current
    			DESCRIPTION
            			"Index in the wlanMacFilterTable."
    		::= { flWorkWlanMacFilterEntry 1 }

   flWorkWlanMacEntryInterfaceName 
   			OBJECT-TYPE
    			SYNTAX     INTEGER { any(0), wlan-1(1), wlan-2(2) }
    			MAX-ACCESS     read-write
    			STATUS     current
    			DESCRIPTION
            			"Interface on which this entry should be applied."
    		::= { flWorkWlanMacFilterEntry 2 }

   flWorkWlanMacEntryAction 
   			OBJECT-TYPE
    			SYNTAX     INTEGER { active(0), inactive(1), disabled(2) }
    			MAX-ACCESS     read-write
    			STATUS     current
    			DESCRIPTION
            			"If this entry is 'active' or 'inactive'."
    		::= { flWorkWlanMacFilterEntry 3 }

   flWorkWlanMacEntryAddress 
   			OBJECT-TYPE
    			SYNTAX     MacAddress
    			MAX-ACCESS     read-write
    			STATUS     current
    			DESCRIPTION
            			"MAC address of this entry."
    		::= { flWorkWlanMacFilterEntry 4 }


    --
    --
    -- END OF flWorkWlan Group
    --

    --    
    --    
    --MIB-Module for Ethernet/IP DLR (Device-Level-Ring) protocol
    --
 
    flWorkFWCtrlDLRDomainTable 
    		OBJECT-TYPE
            SYNTAX          SEQUENCE OF FlWorkFWCtrlDLRDomainEntry
            MAX-ACCESS          not-accessible
            STATUS          current
            DESCRIPTION     "Every entry into the table contains information about
                             a DLR domain."
            ::= { flWorkFWCtrlDLR 1 }

    flWorkFWCtrlDLRDomainEntry     
    		OBJECT-TYPE
            SYNTAX          FlWorkFWCtrlDLRDomainEntry
            MAX-ACCESS          not-accessible
            STATUS          current
            DESCRIPTION     "An entry in the flWorkFWCtrlDLRDomainTable."
            INDEX           { flWorkFWCtrlDLRDomainIdx }
            ::= { flWorkFWCtrlDLRDomainTable 1 }
   
    FlWorkFWCtrlDLRDomainEntry 
    		::= SEQUENCE {
                flWorkFWCtrlDLRDomainIdx	                
                	INTEGER,
                flWorkFWCtrlDLRMode
                	INTEGER,
                flWorkFWCtrlDLRPort1
                	INTEGER,
                flWorkFWCtrlDLRPort2
                	INTEGER,
                flWorkFWCtrlDLRBeaconInterval
                	INTEGER,
                flWorkFWCtrlDLRBeaconTimeout
                	INTEGER,
                flWorkFWCtrlDLRSupervisorPrecedence
                	INTEGER, 
                flWorkFWCtrlDLRVlanId
                	INTEGER,
                flWorkFWCtrlDLRRingStatus
                	INTEGER,
                flWorkFWCtrlDLRDeviceStatus
                	INTEGER,
                flWorkFWCtrlDLRRingFaultCounter
                	INTEGER,
                flWorkFWCtrlDLRRingFaultCntClear
                	INTEGER,
                flWorkFWCtrlDLRActiveSupervisorIP
                	IpAddress,
                flWorkFWCtrlDLRActiveSupervisorMAC
                	MacAddress,
                flWorkFWCtrlDLRLastNodePort1IP
                	IpAddress,
                flWorkFWCtrlDLRLastNodePort1MAC
                	MacAddress,
                flWorkFWCtrlDLRLastNodePort2IP
                	IpAddress,
                flWorkFWCtrlDLRLastNodePort2MAC
                	MacAddress,
                flWorkFWCtrlDLRRapidFaultClear 
                        INTEGER,
                flWorkFWCtrlDLRActivePrecedence
                        INTEGER,
                flWorkFWCtrlDLRVerifyFaultLocation
                        INTEGER,
                flWorkFWCtrlDLRRestartSignOn
                        INTEGER
                }       
     flWorkFWCtrlDLRDomainIdx 
        OBJECT-TYPE
        SYNTAX INTEGER (1..255)
        MAX-ACCESS read-only
        STATUS current
        DESCRIPTION
        "Index number of the DLR-Domain."
        ::={ flWorkFWCtrlDLRDomainEntry 1 }   
                 
     flWorkFWCtrlDLRMode 
        OBJECT-TYPE
        SYNTAX INTEGER {
                                disable(1),
                                node(2),
                                supervisor(3)
                                }
        MAX-ACCESS read-write
        STATUS current
        DESCRIPTION
        "Configured DLR role of this device."
        ::={ flWorkFWCtrlDLRDomainEntry 2 } 
        
     flWorkFWCtrlDLRPort1 
        OBJECT-TYPE
        SYNTAX INTEGER
        MAX-ACCESS read-write
        STATUS current
        DESCRIPTION
        "First ring port of DLR."
        ::={ flWorkFWCtrlDLRDomainEntry 3 }
        
    flWorkFWCtrlDLRPort2 
        OBJECT-TYPE
        SYNTAX INTEGER
        MAX-ACCESS read-write
        STATUS current
        DESCRIPTION
        "Second ring port of DLR."
        ::={ flWorkFWCtrlDLRDomainEntry 4 }   

     flWorkFWCtrlDLRBeaconInterval 
        OBJECT-TYPE
        SYNTAX INTEGER (200..100000)
        MAX-ACCESS read-write
        STATUS current
        DESCRIPTION
        "Beacon Interval in microseconds if device acts as supervisor."
        ::={ flWorkFWCtrlDLRDomainEntry 5 } 

     flWorkFWCtrlDLRBeaconTimeout 
        OBJECT-TYPE
        SYNTAX INTEGER (200..500000)
        MAX-ACCESS read-write
        STATUS current
        DESCRIPTION
        "Beacon Timeout value in microseconds if device acts as supervisor."
        ::={ flWorkFWCtrlDLRDomainEntry 6 } 

     flWorkFWCtrlDLRSupervisorPrecedence 
        OBJECT-TYPE
        SYNTAX INTEGER (0..255)
        MAX-ACCESS read-write
        STATUS current
        DESCRIPTION
        "Configured Supervisor precedence value for this device."
        ::={ flWorkFWCtrlDLRDomainEntry 7 } 

     flWorkFWCtrlDLRVlanId 
        OBJECT-TYPE
        SYNTAX INTEGER (1..4095)
        MAX-ACCESS read-write
        STATUS current
        DESCRIPTION
        "Configured VLAN ID which is used for DLR messages."
        ::={ flWorkFWCtrlDLRDomainEntry 8 } 

    
     flWorkFWCtrlDLRRingStatus 
        OBJECT-TYPE
        SYNTAX INTEGER {
                            normal(0),
                            ringFault(1),
                            loopDetect(2),
                            partialFault(3),
                            rapidFault(4)
                            }
        MAX-ACCESS read-only
        STATUS current
        DESCRIPTION
        "Current status of the DLR ring."
        ::={ flWorkFWCtrlDLRDomainEntry 9 } 

     flWorkFWCtrlDLRDeviceStatus 
        OBJECT-TYPE
        SYNTAX INTEGER {
                            backupSupervisor(0),
                            activeSupervisor(1),
                            node(2),
                            noRing(3),
                            fault(4)
                            }
        MAX-ACCESS read-only
        STATUS current
        DESCRIPTION
        "Current status of the DLR device."
        ::={ flWorkFWCtrlDLRDomainEntry 10 } 

     flWorkFWCtrlDLRRingFaultCounter 
        OBJECT-TYPE
        SYNTAX INTEGER
        MAX-ACCESS read-only
        STATUS current
        DESCRIPTION
        "Number of ring faults since last startup of the device."
        ::={ flWorkFWCtrlDLRDomainEntry 11 } 

     flWorkFWCtrlDLRRingFaultCntClear 
        OBJECT-TYPE
        SYNTAX INTEGER {
                            noClear(1),
                            clear(2)
                            }
        MAX-ACCESS read-write
        STATUS current
        DESCRIPTION
        "Sets the Ring fault counter to zero."
        ::={ flWorkFWCtrlDLRDomainEntry 12 } 

     flWorkFWCtrlDLRActiveSupervisorIP 
        OBJECT-TYPE
        SYNTAX IpAddress
        MAX-ACCESS read-only
        STATUS current
        DESCRIPTION
        "IP address of the active supervisor in the ring."
        ::={ flWorkFWCtrlDLRDomainEntry 13 } 

     flWorkFWCtrlDLRActiveSupervisorMAC 
        OBJECT-TYPE
        SYNTAX MacAddress
        MAX-ACCESS read-only
        STATUS current
        DESCRIPTION
        "MAC address of the active supervisor in the ring."
        ::={ flWorkFWCtrlDLRDomainEntry 14 } 

     flWorkFWCtrlDLRLastNodePort1IP 
        OBJECT-TYPE
        SYNTAX IpAddress
        MAX-ACCESS read-only
        STATUS current
        DESCRIPTION
        "IP address of the last node reachable from first ring port."
        ::={ flWorkFWCtrlDLRDomainEntry 15 } 

     flWorkFWCtrlDLRLastNodePort1MAC 
        OBJECT-TYPE
        SYNTAX MacAddress
        MAX-ACCESS read-only
        STATUS current
        DESCRIPTION
        "MAC address of the last node reachable from first ring port."
        ::={ flWorkFWCtrlDLRDomainEntry 16 } 

    flWorkFWCtrlDLRLastNodePort2IP 
        OBJECT-TYPE
        SYNTAX IpAddress
        MAX-ACCESS read-only
        STATUS current
        DESCRIPTION
        "IP address of the last node reachable from second ring port."
        ::={ flWorkFWCtrlDLRDomainEntry 17 } 

     flWorkFWCtrlDLRLastNodePort2MAC 
        OBJECT-TYPE
        SYNTAX MacAddress
        MAX-ACCESS read-only
        STATUS current
        DESCRIPTION
        "MAC address of the last node reachable from second ring port."
        ::={ flWorkFWCtrlDLRDomainEntry 18 } 

     flWorkFWCtrlDLRRapidFaultClear 
        OBJECT-TYPE
        SYNTAX INTEGER {
                            noClear(1),
                            clear(2)
                            }
        MAX-ACCESS read-write
        STATUS current
        DESCRIPTION
        "If device is in Rapid Fault State, it can be set back into normal state by using this object."
        ::={ flWorkFWCtrlDLRDomainEntry 19 }

     flWorkFWCtrlDLRActivePrecedence
        OBJECT-TYPE
        SYNTAX INTEGER
        MAX-ACCESS read-only
        STATUS current
        DESCRIPTION
        "Precedenc value of the active supervisor in the ring."
        ::={ flWorkFWCtrlDLRDomainEntry 20 }

     flWorkFWCtrlDLRVerifyFaultLocation
        OBJECT-TYPE
        SYNTAX INTEGER {
                            doNothing(1),
                            start(2)
                            }
        MAX-ACCESS read-write
        STATUS current
        DESCRIPTION
        "Discover the last active nodes of the ring in case of ring failure."
        ::={ flWorkFWCtrlDLRDomainEntry 21 }

     flWorkFWCtrlDLRRestartSignOn
        OBJECT-TYPE
        SYNTAX INTEGER {
                            doNothing(1),
                            start(2)
                            }
        MAX-ACCESS read-write
        STATUS current
        DESCRIPTION
        "Update the node table."
        ::={ flWorkFWCtrlDLRDomainEntry 22 }
	
     flWorkFWCtrlDLRNodeTable 
                OBJECT-TYPE
            SYNTAX          SEQUENCE OF FlWorkFWCtrlDLRNodeEntry
            MAX-ACCESS          not-accessible
            STATUS          current
            DESCRIPTION     "Every entry into the table contains information about
                             a node within the DLR ring."
            ::= { flWorkFWCtrlDLR 2 }

    flWorkFWCtrlDLRNodeEntry     
    		OBJECT-TYPE
            SYNTAX          FlWorkFWCtrlDLRNodeEntry
            MAX-ACCESS          not-accessible
            STATUS          current
            DESCRIPTION     "An entry in the flWorkFWCtrlDLRNodeTable."
            INDEX           { 
                               flWorkFWCtrlDLRDomainIdx,
                               flWorkFWCtrlDLRNodeIdx }
            ::= { flWorkFWCtrlDLRNodeTable 1 }
   
     FlWorkFWCtrlDLRNodeEntry 
    		::= SEQUENCE {
                flWorkFWCtrlDLRNodeIdx	                
                	INTEGER,
                flWorkFWCtrlDLRNodeIP
                	IpAddress,
                flWorkFWCtrlDLRNodeMAC
                	MacAddress
                }         

     flWorkFWCtrlDLRNodeIdx 
        OBJECT-TYPE
        SYNTAX INTEGER (1..1024)
        MAX-ACCESS read-only
        STATUS current
        DESCRIPTION
        "Index number of the DLR-Node in the ring."
        ::={ flWorkFWCtrlDLRNodeEntry 2 }      

     flWorkFWCtrlDLRNodeIP 
        OBJECT-TYPE
        SYNTAX IpAddress
        MAX-ACCESS read-only
        STATUS current
        DESCRIPTION
        "IP address of the node in the ring."
        ::={ flWorkFWCtrlDLRNodeEntry 3 } 

     flWorkFWCtrlDLRNodeMAC 
        OBJECT-TYPE
        SYNTAX MacAddress
        MAX-ACCESS read-only
        STATUS current
        DESCRIPTION
        "MAC address of the node in the ring."
        ::={ flWorkFWCtrlDLRNodeEntry 4 }     
		
		
	--**********************************************************************
	-- flWorkFWCtrlFileTransfer
	--**********************************************************************		

	flWorkFWCtrlFileTransferTftpIPAddr
        OBJECT-TYPE
            SYNTAX      IpAddress
            MAX-ACCESS  read-write
            STATUS      current
            DESCRIPTION
                "Write to this object sets the IP address for
                 the TFTP server needed by the file transfer process."
        ::= { flWorkFWCtrlFileTransfer 1 }

    flWorkFWCtrlFileTransferTftpVapID
        OBJECT-TYPE
            SYNTAX      INTEGER 
            MAX-ACCESS  read-write
            STATUS      current
            DESCRIPTION
                "Sets the virtual access point to which the file will be transferred.(write-only object)"
        ::= { flWorkFWCtrlFileTransfer 2 }
	
	flWorkFWCtrlFileTransferTftpProfileID
        OBJECT-TYPE
            SYNTAX      INTEGER 
            MAX-ACCESS  read-write
            STATUS      current
            DESCRIPTION
                "Sets the profile for which the file should be used.
				Only profile 1 is currently supported."
            DEFVAL  {1}
        ::= { flWorkFWCtrlFileTransfer 3 }
	
    flWorkFWCtrlFileTransferTftpFileType
        OBJECT-TYPE
            SYNTAX      INTEGER {
						configuration (2),
						sec-context (3),
						radius-rootcert (4),
						radius-clientcert (5),
						snapshot (6)						
			}
            MAX-ACCESS  read-write
            STATUS      current
            DESCRIPTION
                "Sets the file type which should be transferred. (write only object)"
        ::= { flWorkFWCtrlFileTransfer 4 }		
		
    flWorkFWCtrlFileTransferTftpFile
        OBJECT-TYPE
            SYNTAX      OCTET STRING (SIZE(0..64))
            MAX-ACCESS  read-write
            STATUS      current
            DESCRIPTION
                "Writing to this object sets the file name
                 for the file transfer process."
            DEFVAL  {""}
        ::= { flWorkFWCtrlFileTransfer 5 }

    flWorkFWCtrlFileTransferStatus
        OBJECT-TYPE
            SYNTAX      INTEGER {
                                transferOk(1),
                                transferFault(2),
                                noTransfer(3),
                                unknown(4),
								inProgress(5)
                        }
            MAX-ACCESS  read-only
            STATUS      current
            DESCRIPTION
                "Information about the last file transfer process."
        ::= { flWorkFWCtrlFileTransfer 6 }

    flWorkFWCtrlFileTransferExecute
        OBJECT-TYPE
            SYNTAX      INTEGER {
                            noTransfer(1),
                            hostToDevice(2),
                            deviceToHost(3)
                        }
            MAX-ACCESS  read-write
            STATUS      current
            DESCRIPTION
                "Setting this object to hostToDevice(2) causes a
                 download of the configuration file from a 
                 TFTP server (host) to this device.
                 
                 Setting this object to deviceToHost(3) sends the 
                 configuration file to the tftp server named by the
                 object flWorkFWConfigTftpIPAddr.
                 This object always return the value 
                 noTransfer(1) when this object is reading."
            DEFVAL  {noTransfer}
        ::= { flWorkFWCtrlFileTransfer 7 }
		
	--**********************************************************************
    -- flWorkFWCtrlDiag
    --**********************************************************************

    --**********************************************************************
    -- flWorkFWCtrlDiagSurveillance
    --**********************************************************************
    
	flWorkFWCtrlDiagSurveillanceCrcMonitoringTable
        OBJECT-TYPE
            SYNTAX      SEQUENCE OF FlWorkFWCtrlDiagSurveillanceCrcMonitoringEntry
            MAX-ACCESS  not-accessible
            STATUS      current
            DESCRIPTION
                "Table of surveillance information."
        ::= { flWorkFWCtrlDiagSurveillance 1 }

    flWorkFWCtrlDiagSurveillanceCrcMonitoringEntry
        OBJECT-TYPE
            SYNTAX      FlWorkFWCtrlDiagSurveillanceCrcMonitoringEntry
            MAX-ACCESS  not-accessible
            STATUS      current
            DESCRIPTION
                "An entry in the flWorkFWCtrlDiagSurveillanceCrcMonitoringTable, containing surveillance information."
            INDEX       { flWorkFWCtrlDiagSurveillanceCrcMonitoringPortIndex}
        ::= { flWorkFWCtrlDiagSurveillanceCrcMonitoringTable 1 }

    FlWorkFWCtrlDiagSurveillanceCrcMonitoringEntry
        ::= SEQUENCE {
            flWorkFWCtrlDiagSurveillanceCrcMonitoringPortIndex
                Integer32,
            flWorkFWCtrlDiagSurveillanceCrcMonitoringProportionPeak
                Integer32,
            flWorkFWCtrlDiagSurveillanceCrcMonitoringPortStatus
                INTEGER,
            flWorkFWCtrlDiagSurveillanceCrcMonitoringWarningThreshold
                Integer32,
            flWorkFWCtrlDiagSurveillanceCrcMonitoringCriticalThreshold
                Integer32       
            }

    flWorkFWCtrlDiagSurveillanceCrcMonitoringPortIndex
        OBJECT-TYPE
            SYNTAX      Integer32 (1..1024)
            MAX-ACCESS  read-only
            STATUS      current
            DESCRIPTION
                "This object identifies the port. This value is never greater than flWorkNetPortCapacity."
        ::= { flWorkFWCtrlDiagSurveillanceCrcMonitoringEntry 1 }

    flWorkFWCtrlDiagSurveillanceCrcMonitoringProportionPeak
        OBJECT-TYPE
            SYNTAX      Integer32
            MAX-ACCESS  read-only
            STATUS      current
            DESCRIPTION
                "This is the highest proportion of crc errors in parts per million for a sample interval."
        ::= { flWorkFWCtrlDiagSurveillanceCrcMonitoringEntry 2 }
        
    flWorkFWCtrlDiagSurveillanceCrcMonitoringPortStatus
        OBJECT-TYPE
            SYNTAX      INTEGER {
				ok (1),
				warning (2),
				critical (3)
			}
            MAX-ACCESS  read-only
            STATUS      current
            DESCRIPTION
                "The current status of the port."
        ::= { flWorkFWCtrlDiagSurveillanceCrcMonitoringEntry 3 }
        
    flWorkFWCtrlDiagSurveillanceCrcMonitoringWarningThreshold
        OBJECT-TYPE
            SYNTAX      Integer32
            MAX-ACCESS  read-only
            STATUS      current
            DESCRIPTION
                "The warning threshold of the port in parts per million."
        ::= { flWorkFWCtrlDiagSurveillanceCrcMonitoringEntry 4 }

    flWorkFWCtrlDiagSurveillanceCrcMonitoringCriticalThreshold
        OBJECT-TYPE
            SYNTAX      Integer32
            MAX-ACCESS  read-write
            STATUS      current
            DESCRIPTION
                "The critical threshold of the port in parts per million. A value between 1000 ppm (0,1%) and 1000000 ppm (100%) can be assignd."
        ::= { flWorkFWCtrlDiagSurveillanceCrcMonitoringEntry 5 }
				
    flWorkFWCtrlDiagSurveillanceResetCrcValues
        OBJECT-TYPE
            SYNTAX      INTEGER {
                            noClear(1),
                            clear(2)
                        }
            MAX-ACCESS  read-write
            STATUS      current
            DESCRIPTION
                "When set this object to clear(2), the crc proportion peak and crc
				port status of all ports will be cleared.

                Setting this object to noClear(1) has no effect. 
                Reading this object you get always
                the value noClear(1)."
        ::= { flWorkFWCtrlDiagSurveillance 2 }
		
	--**********************************************************************
    -- flWorkFWCtrlDiagSnapshot
    --**********************************************************************
				
    flWorkFWCtrlDiagSnapshotTrigger
        OBJECT-TYPE
            SYNTAX      INTEGER {
                            noSnap(1),
                            snap(2)
                        }
            MAX-ACCESS  read-write
            STATUS      current
            DESCRIPTION
                "When set this object to snap(2), a snapshot of the current runtime parameters will be taken.

                Setting this object to noSnap(1) has no effect. 
                Reading this object you get always
                the value noSnap(1)."
        ::= { flWorkFWCtrlDiagSnapshot 1 }

    flWorkFWCtrlDiagSnapshotStatus
        OBJECT-TYPE
            SYNTAX      INTEGER {
                                notPresent(0),
                                busy(1),
                                present(2),
                                error(3)
                        }
            MAX-ACCESS  read-only
            STATUS      current
            DESCRIPTION
                "Reading this object you get the status of the snapshot file."
        ::= { flWorkFWCtrlDiagSnapshot 2 }

    flWorkFWCtrlDiagSnapshotTimeStamp
        OBJECT-TYPE
            SYNTAX      OCTET STRING
            MAX-ACCESS  read-only
            STATUS      current
            DESCRIPTION
                "Reading this object you get the timestamp of the last snapshot. The value may be 'invalid' if no snapshot have been executed."
        ::= { flWorkFWCtrlDiagSnapshot 3 }
		
	--**********************************************************************
    -- flWorkFWCtrlDiagSyslog
    --**********************************************************************

	flWorkFWCtrlDiagSyslogEnable
        OBJECT-TYPE
			SYNTAX     INTEGER {
                            disable(1),
                            enable(2)
                        }  
			MAX-ACCESS     read-write
			STATUS     current
			DESCRIPTION
					"Determines whether this device will sent messages to configured syslog servers.
					If this object is set to disable(1) no message will be sent."
			DEFVAL  {disable}
		::= { flWorkFWCtrlDiagSyslog 1 }
		
	--**********************************************************************
	-- flWorkFWCtrlDiagSyslogServTable
	--**********************************************************************	
	flWorkFWCtrlDiagSyslogServTable OBJECT-TYPE
		SYNTAX    	SEQUENCE OF FlWorkFWCtrlDiagSyslogServEntry
		MAX-ACCESS 	not-accessible
		STATUS     	current
		DESCRIPTION
			"Display available syslog servers."
		::= { flWorkFWCtrlDiagSyslog 2 }
	   
	flWorkFWCtrlDiagSyslogServEntry OBJECT-TYPE
		SYNTAX		FlWorkFWCtrlDiagSyslogServEntry
		MAX-ACCESS 	not-accessible 
		STATUS     	current
		DESCRIPTION 
			"Each entry in this table represents an syslog server."
		INDEX		{ flWorkFWCtrlDiagSyslogServIndex }
		::= { flWorkFWCtrlDiagSyslogServTable 1 }
	   
	FlWorkFWCtrlDiagSyslogServEntry ::=
		SEQUENCE {
			flWorkFWCtrlDiagSyslogServIndex  
				INTEGER,
			flWorkFWCtrlDiagSyslogServIP
				IpAddress,
			flWorkFWCtrlDiagSyslogServPort 
				INTEGER,
		    flWorkFWCtrlDiagSyslogServName
		        DisplayString				
          }
		  
	flWorkFWCtrlDiagSyslogServIndex OBJECT-TYPE
		SYNTAX     	INTEGER (1..255)
		MAX-ACCESS 	read-only
		STATUS     	current
		DESCRIPTION
			"Each index is the identification number of a syslog server."
		::= { flWorkFWCtrlDiagSyslogServEntry 1 }
	
	flWorkFWCtrlDiagSyslogServIP OBJECT-TYPE
		SYNTAX     	IpAddress
		MAX-ACCESS 	read-write
		STATUS     	current
		DESCRIPTION
			"IP address of the syslog server."
		::= { flWorkFWCtrlDiagSyslogServEntry 2 }
		
	flWorkFWCtrlDiagSyslogServPort OBJECT-TYPE
		SYNTAX     	INTEGER
		MAX-ACCESS 	read-write
		STATUS     	current
		DESCRIPTION
			"Port number of the syslog server."
		::= { flWorkFWCtrlDiagSyslogServEntry 3 }

    flWorkFWCtrlDiagSyslogServName OBJECT-TYPE
        SYNTAX DisplayString
        MAX-ACCESS read-write
        STATUS current
        DESCRIPTION
            "Name of the syslog server.
             The maximum size of the string is 255 characters."       
        DEFVAL  {""}
        ::= { flWorkFWCtrlDiagSyslogServEntry 4 }
        		
	--**********************************************************************

	flWorkFWCtrlDiagSyslogTestMsg
        OBJECT-TYPE
            SYNTAX      INTEGER {
                            noTestMsg(1),
                            sendTestMsg(2)
                        }    
            MAX-ACCESS  read-write
            STATUS      current
            DESCRIPTION
                "Setting this object to sendTestMsg(2) a syslog test message
				 will be sent to the configured syslog servers.
                 Setting this object to noTestMsg(1) has no effect. (write only object)"            
        ::= { flWorkFWCtrlDiagSyslog 3 }
		
	--**********************************************************************
	-- flWorkFWCtrlDiagSyslogMsgGroupTable
	--**********************************************************************	
	flWorkFWCtrlDiagSyslogMsgGroupTable OBJECT-TYPE
		SYNTAX    	SEQUENCE OF FlWorkFWCtrlDiagSyslogMsgGroupEntry
		MAX-ACCESS 	not-accessible
		STATUS     	current
		DESCRIPTION
			"Display available syslog message groups."
		::= { flWorkFWCtrlDiagSyslog 4 }
	   
	flWorkFWCtrlDiagSyslogMsgGroupEntry OBJECT-TYPE
		SYNTAX		FlWorkFWCtrlDiagSyslogMsgGroupEntry
		MAX-ACCESS 	not-accessible 
		STATUS     	current
		DESCRIPTION 
			"Each entry in this table represents a group of syslog messages."
		INDEX		{ flWorkFWCtrlDiagSyslogMsgGroupIndex }
		::= { flWorkFWCtrlDiagSyslogMsgGroupTable 1 }
	   
	FlWorkFWCtrlDiagSyslogMsgGroupEntry ::=
		SEQUENCE {
			flWorkFWCtrlDiagSyslogMsgGroupIndex  
				INTEGER,
			flWorkFWCtrlDiagSyslogMsgGroupName
				DisplayString,
			flWorkFWCtrlDiagSyslogMsgGroupState 
				INTEGER
          }
		  
	flWorkFWCtrlDiagSyslogMsgGroupIndex OBJECT-TYPE
		SYNTAX     	INTEGER (1..255)
		MAX-ACCESS 	read-only
		STATUS     	current
		DESCRIPTION
			"Each index is the identification number of a syslog message group."
		::= { flWorkFWCtrlDiagSyslogMsgGroupEntry 1 }
	
	flWorkFWCtrlDiagSyslogMsgGroupName OBJECT-TYPE
		SYNTAX     	DisplayString
		MAX-ACCESS 	read-only
		STATUS     	current
		DESCRIPTION
			"Name of the message group."
		::= { flWorkFWCtrlDiagSyslogMsgGroupEntry 2 }
		
	flWorkFWCtrlDiagSyslogMsgGroupState OBJECT-TYPE
		SYNTAX     INTEGER {
                            disable(1),
                            enable(2)
                        }  
			MAX-ACCESS     read-write
			STATUS     current
			DESCRIPTION
					"Determines whether this device will sent a message from this message group to the syslog servers.
					If this object is set to disable(1) no message from this group will be sent."
			DEFVAL  {enable}
		::= { flWorkFWCtrlDiagSyslogMsgGroupEntry 3 }
		
	--**********************************************************************
	
--
--
-- The Phoenix Contact private SNMP MIB objects level 4 (device specific):
--
--

    flSwitch
        OBJECT IDENTIFIER ::= { flWorkDevice 15 }


    flSwitchCtrl
        OBJECT IDENTIFIER ::= { flSwitch 1 }

    flSwitchPortMirr
        OBJECT IDENTIFIER ::= { flSwitch 2 }

    flSwitchIgmp
        OBJECT IDENTIFIER ::= { flSwitch 3 }
        
    flSwitchRedundancy
        OBJECT IDENTIFIER ::= { flSwitch 4 }

    flSwitchRelayAgentDhcp
        OBJECT IDENTIFIER ::= { flSwitch 5 }
        
    flSwitchRateCtrl
        OBJECT IDENTIFIER ::= { flSwitch 6 }

    flSwitchTrafficShaping                      
        OBJECT IDENTIFIER ::= { flSwitch 7 }    
        
    flSwitchLagConfig                 
        OBJECT IDENTIFIER ::= { flSwitch 8 }
		
	flSwitchDhcpServerConfig                 
        OBJECT IDENTIFIER ::= { flSwitch 9 }


    flSwitchCtrlSpanTree OBJECT-TYPE
        SYNTAX INTEGER {
               disable(1),
               enable(2)
        }
        MAX-ACCESS read-write
        STATUS current
        DESCRIPTION
            "Enable/ disable the (Rapid) Spanning Tree Protocol for the bridge.
             When 'disable(1)', all ports of the device are placed in the
             forwarding mode, regardless of current Spanning Tree state.
             When 'enable(2)', the normal (R)STP state transitions take place.
             Note:
             To enable (Rapid) Spanning Tree you must set the object 
             flSwitchCtrlRedundancy to spanningTree(2) first."
        DEFVAL  {disable}
        ::= { flSwitchCtrl 1 }

    flSwitchCtrlRedundancy OBJECT-TYPE
        SYNTAX INTEGER {
               noRedundancy(1),
               spanningTree(2)
        }
        MAX-ACCESS read-write
        STATUS current
        DESCRIPTION
            "This object shows the chosen redundancy mechanism.
             The value of 'noRedunduncy(1)' disables all redundancy
             mechanism, sets all redundancy parameters to default values
             and hides the related web pages.
             The value spanningTree(2) shows the (Rapid) Spanning Tree
             web pages and allows to enable the (Rapid) Spanning Tree Protocol."
        DEFVAL  {noRedundancy}
        ::= { flSwitchCtrl 2 }

    flSwitchCtrlMulticast OBJECT-TYPE
        SYNTAX INTEGER {
               disable(1),
               enable(2)
        }
        MAX-ACCESS read-write
        STATUS current
        DESCRIPTION
            "Enable/ disable the web pages for the multicast configuration.
             When 'disable(1)', all multicast web pages for the multicast
             support are hidden. When 'enable(2)', you get 
             additional web pages to configure multicast adjustments."
        DEFVAL  {disable}
        ::= { flSwitchCtrl 3 }

    flSwitchCtrlVlan OBJECT-TYPE
        SYNTAX INTEGER {
               disable(1),
               enable(2)
        }
        MAX-ACCESS read-write
        STATUS current
        DESCRIPTION
            "Enable/ disable the web pages for the vlan configuration.
             When 'disable(1)', all vlan web pages for the vlan support
             are hidden. When 'enable(2)', the you get 
             additional web pages to configure vlan adjustments."
        DEFVAL  {disable}
        ::= { flSwitchCtrl 4 }
        
    flSwitchCtrlVlanTagMode OBJECT-TYPE
        SYNTAX INTEGER {
               vlanTransparent(1),
               vlanTagging(2)
        }
        MAX-ACCESS read-write
        STATUS current
        DESCRIPTION
            "In the mode vlanTransparent(1) the switch ignores the vlan id
             of incomming ethernet packets and uses only the priority
             information out of receiving frames. The vlan id of packets
             passing through will not be changed.
             In the mode vlanTagging(2) the switch takes notice of vlan
             information inside the incoming packets and handles the packets
             like the vlan rules given by the user or management.
             The modified adjustments become effective after
             a restart of the device."             
        DEFVAL  {vlanTransparent}
        ::= { flSwitchCtrl 5 }

    flSwitchCtrlVlanTagStatus OBJECT-TYPE
        SYNTAX INTEGER {
               vlanTransparent(1),
               vlanTagging(2)
        }
        MAX-ACCESS read-only
        STATUS current
        DESCRIPTION
            "Information about the VLAN mode the switch is using.
             In the mode vlanTransparent(1) the switch ignores the vlan id
             of incomming ethernet packets and uses only the priority
             information out of receiving frames. The vlan id of packets
             passing through will not be changed.
             In the mode vlanTagging(2) the switch takes notice of vlan
             information inside the incoming packets and handles the packets
             like the vlan rules given by the user or management."        
        ::= { flSwitchCtrl 6 }

    flSwitchCtrlLldp OBJECT-TYPE
        SYNTAX INTEGER {
               disable(1),
               enable(2),
               transmit(3),
               receive(4)
        }
        MAX-ACCESS read-write
        STATUS current
        DESCRIPTION
            "Enable/ disable the link layer discovery protocol
             for the bridge."
        DEFVAL  {disable}
        ::= { flSwitchCtrl 7 }

    flSwitchCtrlRSTPLargeTreeSupport OBJECT-TYPE
        SYNTAX INTEGER {
               disable(1),
               enable(2)
        }
        MAX-ACCESS read-write
        STATUS current
        DESCRIPTION
            "Enable/ disable the Large Tree enhancement of the Rapid-Spanning-Tree-
             Protocol. When 'disable(1)', only 7 Switches under the root can be placed.
             When 'enable(2)', it is enhanced to 28 Switches."             
        DEFVAL  {disable}
        ::= { flSwitchCtrl 8 }   

     flSwitchCtrlMacHashMode OBJECT-TYPE
        SYNTAX INTEGER {
               randomMacAddresses(1),
               successiveMacAddresses(2)
               }
        MAX-ACCESS read-write
        STATUS current
        DESCRIPTION
            "This object enables the user to optimize the
             hash mode used for mac address table lookup
             in the switch controllers. 
             One algorithm is optimized for random mac addresses(1).
             The other is optimized for successive mac addresses(2).
             The modified adjustments become effective after
             saving the configuration with the next restart
             of the device."
        DEFVAL  {randomMacAddresses}
        ::= { flSwitchCtrl 9 }
        
     flSwitchCtrlDhcpRelayAgentUi OBJECT-TYPE
        SYNTAX INTEGER {
               disable(1),
               enable(2)
        }
        MAX-ACCESS read-write
        STATUS current
        DESCRIPTION
            "Enable/ disable web based user interface for the DHCP relay agent.
             You may configure the DHCP relay agent at any time using SNMP. If
             you want to configure the relay agent using web based management 
             you have to set this object to 'enabled'"             
        DEFVAL  {disable}
        ::= { flSwitchCtrl 10 }
        

     flSwitchCtrlMacTableErase OBJECT-TYPE
        SYNTAX INTEGER {
               doNothing(1),
               eraseMacTable(2)
               }
        MAX-ACCESS read-write
        STATUS current
        DESCRIPTION
            "This object will request the device, to delete all his entries
             in the mac-address-table."        
        ::= { flSwitchCtrl 11 }
        
     flSwitchCtrlRmonHistory OBJECT-TYPE
        SYNTAX INTEGER {
               disable(1),
               enable(2)
               }
        MAX-ACCESS read-write
        STATUS current
        DESCRIPTION
            "Enable or disable the rmon history for the device."        
        ::= { flSwitchCtrl 14 } 

     flSwitchCtrlLldpFlooding OBJECT-TYPE
        SYNTAX INTEGER {
               disable(1),
               enable(2)
        }
        MAX-ACCESS read-write
        STATUS current
        DESCRIPTION
            "Enable/ disable flooding of LLDP BPDUs on all ports if 
             LLDP is not enabled or not supported."
        DEFVAL  {enable}
        ::= { flSwitchCtrl 15 }

    flSwitchCtrlQosProfile OBJECT-TYPE
        SYNTAX INTEGER {
                        universal(1),
                        profinet(2),
                        ethernetIP(3)
        }
        MAX-ACCESS read-write
        STATUS current
        DESCRIPTION
            "For several traffic classes, predefined QoS scheme can be used, which will reconfigure priority
             mapping and queue usage to optimize the switch performance and buffering for the selected type of traffic.
             The following schemes are available:
           
             Universal:
             
             Uses the vlan priority. Each priority level is mapped to one queue (1 to 1 an so on).
           
             Profinet:
             
             The priority mapping and queue usage is optimized for traffic in a profinet environment.
             
           
            EthernetIP:
            
            The priority mapping and queue usage is optimized for traffic in an ethernet-ip (CIP) environment."
        DEFVAL  {universal}
        ::= { flSwitchCtrl 18 }

    --
    --
    --  flSwitchIgmpSnoop - IGMP Snooping Parameters
    --  This group is used to instrument the Layer 2 IGMP Snooping support.
    --
    flSwitchIgmpSnoop
        OBJECT IDENTIFIER ::= { flSwitchIgmp 1 }

    flSwitchIgmpQuery
        OBJECT IDENTIFIER ::= { flSwitchIgmp 2 }

    flSwitchIgmpSnoopEnable  OBJECT-TYPE
        SYNTAX INTEGER {
               disable(1),
               enable(2)
        }
        MAX-ACCESS read-write
        STATUS current
        DESCRIPTION
            "Setting this object to enable(2) enables IGMP Snooping.  Setting
             it to disable(1) disables IGMP Snooping."
        DEFVAL  {disable}
        ::= { flSwitchIgmpSnoop 1 }

    flSwitchIgmpSnoopAging  OBJECT-TYPE
        SYNTAX Integer32 (30..3600)
        MAX-ACCESS read-write
        STATUS current
        DESCRIPTION
            "The timeout period in seconds for aging out Multicast Groups
             dynamically learned with IGMP Snooping.  Note that aging operates
             on a per interface per VLAN per multicast group basis."
        DEFVAL  {300}
        ::= { flSwitchIgmpSnoop 3 }

    flSwitchIgmpSnoopTable OBJECT-TYPE
        SYNTAX SEQUENCE OF FlSwitchIgmpSnoopEntry
        MAX-ACCESS not-accessible
        STATUS current
        DESCRIPTION
            "This table, which provides IGMP Snooping information, augments
             the 'dot1qStaticMulticastTable' in the Q-MIB (RFC2674)."
        ::= { flSwitchIgmpSnoop 4 }

    flSwitchIgmpSnoopEntry OBJECT-TYPE
        SYNTAX FlSwitchIgmpSnoopEntry
        MAX-ACCESS not-accessible
        STATUS current
        DESCRIPTION
            "Displays by VLAN ID and Multicast Group the set of ports
             enabled to forward Multicast Group traffic as determined 
             by the IGMP Snooping task."
        AUGMENTS { dot1qStaticMulticastEntry }
        ::= { flSwitchIgmpSnoopTable 1 }

    FlSwitchIgmpSnoopEntry ::= SEQUENCE {
        flSwitchIgmpSnoopEgressPorts   PortList
    }

    flSwitchIgmpSnoopEgressPorts  OBJECT-TYPE
        SYNTAX PortList
        MAX-ACCESS read-only
        STATUS current
        DESCRIPTION
            "This read-only object displays the set of ports enabled to
             forward specific Multicast Group traffic as determined by the
             IGMP Snooping task.
            
             It should be noted that the IGMP Snooping task generates a pseudo-
             static (i.e., not saved in NVM) port list similar to the RFC2674
             Q-MIB 'dot1qStaticMulticastStaticEgressPorts' object. Consequently,
             a port will not be a member of 'flSwitchIgmpSnoopEgressPorts' if
             it is a member of 'dot1qStaticMulticastForbiddenEgressPorts'."
        ::= { flSwitchIgmpSnoopEntry 1 }

    flSwitchIgmpSnoopExtended
        OBJECT IDENTIFIER ::= { flSwitchIgmpSnoop 5 }

    flSwitchBlockUnknownMulticastAtQuerier  OBJECT-TYPE
        SYNTAX INTEGER {
               disable(1),
               enable(2)
        }
        MAX-ACCESS read-write
        STATUS current
        DESCRIPTION
            "When this object is set to enable(2) the
             switch doesn't forward multicast packets 
             of groups he received no igmp membership 
             report before.
             Setting this object to disable(1) causes the 
             switch to forward ethernet packets of
             unknown groups at all switch ports.
             
             Blocking multicast packets of unknown multicast
             groups will only work if IGMP Snooping is enabled
             and the switch is the active querier in the subnet.
             (see object flSwitchIgmpSnoopEnable)."
        DEFVAL  {enable}
        ::= { flSwitchIgmpSnoopExtended 1 }

    flSwitchForwardUnknownMulticastToQuerier  OBJECT-TYPE
        SYNTAX INTEGER {
               disable(1),
               enable(2)
        }
        MAX-ACCESS read-write
        STATUS current
        DESCRIPTION
            "Setting this object to enable(2) causes the
             switch to forward multicast packets of groups
             he saw no membership reports before only at
             ports receiving queries.
             Setting this object to disable(1) causes the 
             switch to forward ethernet packets of
             unknown groups at all switch ports.
             
             Forwarding multicast packets of unknown multicast
             groups to the querier will only work if IGMP Snooping
             is enabled (see object flSwitchIgmpSnoopEnable)."
        DEFVAL  {enable}
        ::= { flSwitchIgmpSnoopExtended 2 }

    flSwitchIGMPAutoQueryPort OBJECT-TYPE
        SYNTAX INTEGER {
               disable(1),
               enable(2)
        }
        MAX-ACCESS read-write
        STATUS current
        DESCRIPTION
            "Setting this object to enable(2) causes the
              switch to use autodetection of additional
              query ports by other protocols like 
              RSTP-Fast-Ring-Detection or 
              Media Redundancy Protocol. Every redundant port
              is treated like a query port and is added to every
              dynamically learned MCAST group.
             Setting this object to disable(1) causes the 
              switch to flush the dynamic learned MCAST groups on
              every topology changed indicated by redundanc mechanism, 
              instead of adding all redundant ports to the MCAST groups."
        DEFVAL  {enable}
        ::= { flSwitchIgmpSnoopExtended 3 }

    flSwitchIGMPAutoQueryPortsClear OBJECT-TYPE
        SYNTAX INTEGER {
               doNothing(1),               
               clear(2)
        }
        MAX-ACCESS read-write
        STATUS current
        DESCRIPTION
            "Setting this object to cleanr(2) causes the
              switch to remove all ports from the 
              Auto Query Port list. After the IGMP Aging
              time has expired, the ports may be removed from
              the existing MCAST groups."        
        ::= { flSwitchIgmpSnoopExtended 4 }

    flSwitchIGMPStaticQueryPorts OBJECT-TYPE
        SYNTAX PortList
        MAX-ACCESS read-write
        STATUS current
        DESCRIPTION
            "This object reflects the configuration of static Query Ports, where
             each bit of the value represents the state of one port. If a port
             is configured as query port, it will automatically be included in every 
             dynamically learned MCAST group."
        ::= { flSwitchIgmpSnoopExtended 5 }


    flSwitchIgmpQueryTable OBJECT-TYPE
        SYNTAX SEQUENCE OF FlSwitchIgmpQueryEntry
        MAX-ACCESS not-accessible
        STATUS current
        DESCRIPTION
            "A table displaying the IGMP Router Query PDU ports."
        ::= { flSwitchIgmpQuery 1 }

    flSwitchIgmpQueryEntry OBJECT-TYPE
        SYNTAX FlSwitchIgmpQueryEntry
        MAX-ACCESS not-accessible
        STATUS current
        DESCRIPTION
            "A table displaying the IGMP Router Query PDU ports.
             These are maintained on a per VLAN basis."
        INDEX { dot1qVlanIndex }
        ::= { flSwitchIgmpQueryTable 1 }

    FlSwitchIgmpQueryEntry ::= SEQUENCE {
        flSwitchIgmpQueryPorts   PortList
    }

    flSwitchIgmpQueryPorts  OBJECT-TYPE
        SYNTAX PortList
        MAX-ACCESS read-only
        STATUS current
        DESCRIPTION
            "This read-only object displays the set of ports that have received
             IGMP Router Query PDUs for this VLAN as determined by the IGMP
             Snooping task."
        ::= { flSwitchIgmpQueryEntry 1 }

    flSwitchIgmpQueryEnable  OBJECT-TYPE
        SYNTAX INTEGER {
               disable(1),
               version1(2),
               version2(3)
        }
        MAX-ACCESS read-write
        STATUS current
        DESCRIPTION
            "Setting this object to version1(2) or version2(3) the device sends
             igmp queries depending of the selected protocol version.
             IGMP Snooping must be enabled too (see object 
             flSwitchIgmpSnoopEnable).
             The value disable(1) causes the device to send no igmp queries."
        DEFVAL  {disable}
        ::= { flSwitchIgmpQuery 2 }

    flSwitchIgmpQueryInterval OBJECT-TYPE
        SYNTAX Integer32 (10..3600)
        MAX-ACCESS read-write
        STATUS current
        DESCRIPTION
            "The query interval is the interval between
             General Queries sent by the querier.
             The granularity of this timer is 1 second."
        DEFVAL  {125}
        ::= { flSwitchIgmpQuery 3 }

     flSwitchIgmpQueryActiveIP OBJECT-TYPE
        SYNTAX IpAddress
        MAX-ACCESS read-only
        STATUS current
        DESCRIPTION
            "The device ip address of the last query which has been
            received on this device and selected as active querier. 
            If the device itself is active querier, 0 is returned. If no
            query has been received, 255.255.255.255 is returned."
        ::= { flSwitchIgmpQuery 4 }

     flSwitchIgmpTablesErase OBJECT-TYPE
        SYNTAX INTEGER {
               doNothing(1),
               eraseIgmpTables(2)
               }
        MAX-ACCESS read-write
        STATUS current
        DESCRIPTION
               "When set this object to eraseIgmpTables(2), all learned
                igmp information will be erased.

                Setting this object to doNothing(1) has no effect. 
                Reading this object you get always the value doNothing(1)."
        ::= { flSwitchIgmp 3 }


    --
    --
    -- flSwitchPortMirr Group
    --
    flSwitchPortMirrDestinationPort OBJECT-TYPE
        SYNTAX Integer32
        MAX-ACCESS read-write
        STATUS current
        DESCRIPTION
            "Switch port that acts as mirror (destination).
            Don't set the same port as mirror and mirrored."
        DEFVAL  {0}    
        ::= { flSwitchPortMirr 1 }
        
    flSwitchPortMirrSourcePort OBJECT-TYPE
        SYNTAX Integer32
        MAX-ACCESS read-write
        STATUS current
        DESCRIPTION
            "Switch port that is mirrored (source).
            Value of 0 means not set. The object flSwitchPortMirrStatus
            becomes then the value disable(1) automatically."
        DEFVAL  {0}    
        ::= { flSwitchPortMirr 2 }
        
    flSwitchPortMirrStatus OBJECT-TYPE
        SYNTAX INTEGER {
               disable(1),
               enable(2)
        }
        MAX-ACCESS read-write
        STATUS current
        DESCRIPTION
            "The status of the port mirroring.
            The value enable(2)activates port mirroing
            for the ports given by the objects 
            flSwitchPortMirrDestination and 
            flSwitchPortMirrSource. 
            When the port numbers are not valid
            port mirroring will be disabled."       
        DEFVAL  {disable}    
        ::= { flSwitchPortMirr 3 }
        
    flSwitchPortMirrIngressSourcePort OBJECT-TYPE
        SYNTAX OCTET STRING
        MAX-ACCESS read-write
        STATUS current
        DESCRIPTION
            "All switch ports the ingress traffic should
             be mirrored (source). Setup a mask where 1/0 means enabled/disabled for each port.
             The mask beginns with the first port number.
             E.g. 00100000 means mirror traffic only on port 3."
        ::= { flSwitchPortMirr 4 }
    
    flSwitchPortMirrEgressSourcePort OBJECT-TYPE
        SYNTAX OCTET STRING
        MAX-ACCESS read-write
        STATUS current
        DESCRIPTION
            "Switch ports which egress traffic should
             be mirrored (source). Setup a mask where 1/0 means enabled/disabled for each port.
             The mask beginns with the first port number.
             E.g. 00100000 means mirror traffic only on port 3."
        ::= { flSwitchPortMirr 5 }



 
   

    --
    --
    -- flSwitchRedundancy Group
    --
    
    flSwitchCtrlRSTPFastRingDetection OBJECT-TYPE
        SYNTAX INTEGER {
               disable(1),
               enable(2)
        }
        MAX-ACCESS read-write
        STATUS current
        DESCRIPTION
            "Enable/ disable the Fast Ring Detection enhancement
             of the Rapid-Spanning-Tree-Protocol.
             When 'disable(1)', the normal RSTP will be used.
             When 'enable(2)', it starts a ring detection algorithm
             which cause to faster fault_recovery_times."
        DEFVAL  {enable}
        ::= { flSwitchRedundancy 1 }
   
    flSwitchRSTPRingTable
        OBJECT-TYPE
            SYNTAX      SEQUENCE OF FlSwitchRSTPRingEntry
            MAX-ACCESS  not-accessible
            STATUS      current
            DESCRIPTION
                "Table of information about the identified rings in 
                 the RSTP tree."
        ::= { flSwitchRedundancy 2 }

    flSwitchRSTPRingEntry
        OBJECT-TYPE
            SYNTAX      FlSwitchRSTPRingEntry
            MAX-ACCESS  not-accessible
            STATUS      current
            DESCRIPTION
                "An entry in the table, containing information about
                 the identified rings in the RSTP tree."
            INDEX       { flSwitchRSTPRingIndex }
        ::= { flSwitchRSTPRingTable 1 }

    FlSwitchRSTPRingEntry
        ::= SEQUENCE {
            flSwitchRSTPRingIndex
                Integer32,
            flSwitchRSTPRingMAC
                MacAddress,
            flSwitchRSTPRingBlockPort
                Integer32,
            flSwitchRSTPRingRootPort
                Integer32,
            flSwitchRSTPRingDesPort
                Integer32,    
            flSwitchRSTPRingStatus
                INTEGER       
            }

    flSwitchRSTPRingIndex
        OBJECT-TYPE
            SYNTAX      Integer32 (1..1024)
            MAX-ACCESS  read-only
            STATUS      current
            DESCRIPTION
                "This object identifies the ring identifier
                 for which this entry contains information."
        ::= { flSwitchRSTPRingEntry 1 }

    flSwitchRSTPRingMAC
        OBJECT-TYPE
            SYNTAX      MacAddress
            MAX-ACCESS  read-only
            STATUS      current
            DESCRIPTION
                "This is the Macaddress of the Switch with the Alternate
                Port of this ring."
        ::= { flSwitchRSTPRingEntry 2 }

    flSwitchRSTPRingBlockPort
        OBJECT-TYPE
            SYNTAX      Integer32
            MAX-ACCESS  read-only
            STATUS      current
            DESCRIPTION
                "This is the number of the Alternate Port of this ring."
        ::= { flSwitchRSTPRingEntry 3 }
        
   flSwitchRSTPRingRootPort
        OBJECT-TYPE
            SYNTAX      Integer32
            MAX-ACCESS  read-only
            STATUS      current
            DESCRIPTION
                "The Portnumber of the Root Port which belongs to the Ring"
        ::= { flSwitchRSTPRingEntry 4 }
        
   flSwitchRSTPRingDesPort
        OBJECT-TYPE
            SYNTAX      Integer32
            MAX-ACCESS  read-only
            STATUS      current
            DESCRIPTION
                "The Portnumber of the Designated Port which belongs to the Ring"
        ::= { flSwitchRSTPRingEntry 5 }

    flSwitchRSTPRingStatus
        OBJECT-TYPE
            SYNTAX INTEGER {
               closed(3),
               breaked(6),
               failed(7)
            }
            MAX-ACCESS  read-only
            STATUS      current
            DESCRIPTION
                "This reports the current status of the ring detection."
        ::= { flSwitchRSTPRingEntry 6}
   
   flSwitchRSTPRingFailedPort
        OBJECT-TYPE
            SYNTAX      Integer32
            MAX-ACCESS  read-only
            STATUS      current
            DESCRIPTION
                "This reports the port number of a failed link. If no error
                 have occured, it contains '0'"
        ::= { flSwitchRedundancy 3 } 

   flSwitchRSTPextPortTable
        OBJECT-TYPE
            SYNTAX      SEQUENCE OF FlSwitchRSTPextPortEntry
            MAX-ACCESS  not-accessible
            STATUS      current
            DESCRIPTION
                "Table of extended RSTP port objects."
        ::= { flSwitchRedundancy 4 }

    flSwitchRSTPextPortEntry
        OBJECT-TYPE
            SYNTAX      FlSwitchRSTPextPortEntry
            MAX-ACCESS  not-accessible
            STATUS      current
            DESCRIPTION
                "An entry in the table, containing extended information
                 and configuration objects about Spanning-Tree."
            INDEX       { flSwitchRSTPextPortNum }
        ::= { flSwitchRSTPextPortTable 1 }

    FlSwitchRSTPextPortEntry
        ::= SEQUENCE {
            flSwitchRSTPextPortNum
                Integer32,
            flSwitchRSTPextAutoEdge
                INTEGER,
            flSwitchRSTPextBPDUFlood
                INTEGER
            }

    flSwitchRSTPextPortNum
        OBJECT-TYPE
            SYNTAX      Integer32 (1..1024)
            MAX-ACCESS  read-only
            STATUS      current
            DESCRIPTION
                "This object identifies the port number."
        ::= { flSwitchRSTPextPortEntry 1 }

    flSwitchRSTPextAutoEdge
        OBJECT-TYPE
            SYNTAX      INTEGER {
                            disable(1),
                            enable(2)                            
                            }
            MAX-ACCESS  read-write
            STATUS      current
            DESCRIPTION
                "This object does reflect the Auto-Edge Parameter of Spanning-Tree. 
                  When this object is set to disable, the attribute of dot1dStpPortAdminEdgePort 
                  becomes active. Otherwise the Port is automatically detected."
            DEFVAL  {enable} 
        ::= { flSwitchRSTPextPortEntry 2 }
          
    flSwitchRSTPextBPDUFlood
        OBJECT-TYPE
            SYNTAX      INTEGER {
                            disable(1),
                            enable(2)                            
                            }
            MAX-ACCESS  read-write
            STATUS      current
            DESCRIPTION
                "This object does reflect the BPDU Flood mode on the port.
                If enabled the BPDU traffic arriving on this port when STP is disabled is flooded.
                If disabled the BPDU traffic arriving on this port when STP is disabled is blocked."
            DEFVAL  {enable} 
        ::= { flSwitchRSTPextPortEntry 3 }              
        
   
    --
    --
    -- flSwitchRelayAgentDhcp Group
    --
    

     flSwitchRelayAgentDhcpCtrl
        OBJECT-TYPE
           SYNTAX INTEGER {
               disable(1),
               enable(2)
               }
           MAX-ACCESS read-write
           STATUS current
           DESCRIPTION
              "Status of the DHCP Relay Agent given by the user.
               This object will be stored in the configuration file.
               Please note that the dhcp relay agent is not active
               if the ip address assignment is set to dhcp."
        ::= { flSwitchRelayAgentDhcp 1 }
        
    flSwitchRelayAgentDhcpIpAddress
        OBJECT-TYPE
            SYNTAX      IpAddress
            MAX-ACCESS  read-write
            STATUS      current
            DESCRIPTION
               "DHCP Server IP Address for the DHCP Relay Agent."
        ::= { flSwitchRelayAgentDhcp 2 }

    flSwitchRelayAgentDhcpStatus
        OBJECT-TYPE
            SYNTAX      OCTET STRING (SIZE(1..255))
            MAX-ACCESS  read-only
            STATUS current
            DESCRIPTION
                "The verbal current status of the DHCP Relay Agent.
                 This status is influenced by flSwitchRelayAgentDhcpCtrl
                 and the IP address assignment in this system. If the IP
                 address assignment is set to DHCP, this will overrule
                 the setting of flSwitchRelayAgentDhcpCtrl to 'disabled' "            
        ::= { flSwitchRelayAgentDhcp 3 }
        
    flSwitchRelayAgentDhcpRIdType
        OBJECT-TYPE
            SYNTAX  INTEGER {
               ipAddress(1),
               macAddress(2)
               }
            MAX-ACCESS  read-write
            STATUS current
            DESCRIPTION
                "This object indicates if the DHCP relay agent uses
                 its own mac address or its own ip address as Remote ID
                 value when inserting DHCP option 82 fields into the
                 relayed DHCP messages." 
            DEFVAL  { ipAddress }           
        ::= { flSwitchRelayAgentDhcp 4 }
        

    flSwitchRelayAgentDhcpPortTable 
        OBJECT-TYPE
            SYNTAX      SEQUENCE OF FlSwitchRelayAgentDhcpPortEntry
            MAX-ACCESS  not-accessible
            STATUS      current
            DESCRIPTION
                "Table with port based control information and settings
                 concerning the DHCP relay agent."
        ::= { flSwitchRelayAgentDhcp 5 }

    flSwitchRelayAgentDhcpPortEntry
        OBJECT-TYPE
            SYNTAX      FlSwitchRelayAgentDhcpPortEntry
            MAX-ACCESS  not-accessible
            STATUS      current
            DESCRIPTION
                "An entry in the table, containing information and settings
                 concerning port based configuration of the DHCP relay agent."
            INDEX       { flSwitchRelayAgentDhcpPortCtrlIndex }
        ::= { flSwitchRelayAgentDhcpPortTable 1 }

    FlSwitchRelayAgentDhcpPortEntry
        ::= SEQUENCE {
            flSwitchRelayAgentDhcpPortCtrlIndex
                Integer32,
            flSwitchRelayAgentDhcpPortCtrlOperation
                INTEGER
            }
                
    flSwitchRelayAgentDhcpPortCtrlIndex
        OBJECT-TYPE
            SYNTAX      Integer32 (1..1024)
            MAX-ACCESS  read-only
            STATUS      current
            DESCRIPTION
                "The port number referenced by this table line."
        ::= { flSwitchRelayAgentDhcpPortEntry 1 }
        
    flSwitchRelayAgentDhcpPortCtrlOperation
        OBJECT-TYPE
            SYNTAX      INTEGER{
                          disable(1),
                          enable(2)
                          }
            MAX-ACCESS  read-write
            STATUS      current
            DESCRIPTION
                "The operational status of the DHCP relay agent for this port.
                 The relay agent will only care about DHCP messages received on 
                 this port if the operational status is 'enable'.
                 NOTE: If the global control status of the relay agent 
                       (flSwitchRelayAgentDhcpCtrl) is set to 'disable' this 
                       will overrule any settings done in this table!"
        ::= { flSwitchRelayAgentDhcpPortEntry 2 }
        
    --
    --
    -- flSwitchRatectrl Group
    -- 
    
    flSwitchRateCtrlBroadcast 
    		OBJECT-TYPE
        	SYNTAX INTEGER {
               		disable(1),
               		enable(2)
        			}
        	MAX-ACCESS read-write
        	STATUS current
        	DESCRIPTION
            		"Enable/ disable the Broadcast limitation of
             		rate control."
        	DEFVAL  {disable}
        	::= { flSwitchRateCtrl 1 }
        
   flSwitchRateCtrlMulticast 
   			OBJECT-TYPE
        	SYNTAX INTEGER {
            	   	disable(1),
               		enable(2)
        			}
        	MAX-ACCESS read-write
        	STATUS current
        	DESCRIPTION
            		"Enable/ disable the Multicast limitation of
             		rate control."
        	DEFVAL  {disable}
        	::= { flSwitchRateCtrl 2 } 
        
   flSwitchRateCtrlBitrate 
   			OBJECT-TYPE
        	SYNTAX INTEGER
        	MAX-ACCESS read-write
        	STATUS current
        	DESCRIPTION
            		"Bit rate configuration for all the ports.
             		Value ranges in kbps. It will be rounded
             		to the last valid value."
        	DEFVAL  {0}
        	::= { flSwitchRateCtrl 3 }

    flSwitchDot3FlowControlMode OBJECT-TYPE
         SYNTAX      INTEGER {
                     enable(1),
                     disable(2)
                  }
         MAX-ACCESS  read-write
         STATUS      current
         DESCRIPTION
                     "Config switchconfig flowcontrol allows you to enable or disable
                     802.3x flow control for the switch. This value
                     applies to only full-duplex mode ports. "
         DEFVAL { disable }
         ::= { flSwitchRateCtrl 4 }

    flSwitchBroadcastControlMode OBJECT-TYPE
         SYNTAX      INTEGER {
                     enable(1),
                     disable(2)
                  }
         MAX-ACCESS  read-write
         STATUS      current
         DESCRIPTION
                     "The switch config broadcast allows you to enable or disable
                     broadcast storm recovery mode. When you specify Enable for Broadcast
                     Storm Recovery and the broadcast traffic on any Ethernet port exceeds
                     the configured threshold, the switch blocks (discards) the broadcast
                     traffic."
         DEFVAL { disable }
         ::= { flSwitchRateCtrl 5 }

    flSwitchBroadcastControlThreshold OBJECT-TYPE
         SYNTAX      Unsigned32(0..14880000)
         MAX-ACCESS  read-write
         STATUS      current
         DESCRIPTION
                     "Configures the broadcast storm recovery threshold for this port
                     in packets-per-second."
         DEFVAL { 1220 }
         ::= { flSwitchRateCtrl 6 }

    flSwitchMulticastControlMode OBJECT-TYPE
         SYNTAX      INTEGER {
                     enable(1),
                     disable(2)
                  }
         MAX-ACCESS  read-write
         STATUS      current
         DESCRIPTION
                     "The switch config multicast allows you to enable or disable
                     multicast storm recovery mode. When you specify Enable for multicast
                     Storm Recovery and the multicast traffic on any Ethernet port exceeds
                     the configured threshold, the switch blocks (discards) the multicast
                     traffic."
         DEFVAL { disable }
         ::= { flSwitchRateCtrl 7 }

    flSwitchMulticastControlThreshold OBJECT-TYPE
         SYNTAX      Unsigned32(0..14880000)
         MAX-ACCESS  read-write
         STATUS      current
         DESCRIPTION
                     "Configures the multicast storm recovery threshold for this port
                     in packets-per-second."
         DEFVAL { 1220 }
         ::= { flSwitchRateCtrl 8 }

    flSwitchUnicastControlMode OBJECT-TYPE
         SYNTAX      INTEGER {
                     enable(1),
                     disable(2)
                  }
         MAX-ACCESS  read-write
         STATUS      current
         DESCRIPTION
                     "The switch config unicast allows you to enable or disable
                     unicast storm recovery mode. When you specify Enable for unicast
                     Storm Recovery and the unknown unicast traffic on any Ethernet port exceeds
                     the configured threshold, the switch blocks (discards) the unknown unicast
                     traffic."
         DEFVAL { disable }
         ::= { flSwitchRateCtrl 9 }

    flSwitchUnicastControlThreshold OBJECT-TYPE
         SYNTAX      Unsigned32(0..14880000)
         MAX-ACCESS  read-write
         STATUS      current
         DESCRIPTION
                     "Configures the unicast storm recovery threshold for this port
                     in packets-per-second."
         DEFVAL { 1220 }
         ::= { flSwitchRateCtrl 10 }

     flSwitchStormCtrlTable
        OBJECT-TYPE
            SYNTAX      SEQUENCE OF FlSwitchStormCtrlEntry
            MAX-ACCESS  not-accessible
            STATUS      current
            DESCRIPTION
                "Table of information about the Storm control for each port."
        ::= { flSwitchRateCtrl 11 }

    flSwitchStormCtrlEntry
        OBJECT-TYPE
            SYNTAX      FlSwitchStormCtrlEntry
            MAX-ACCESS  not-accessible
            STATUS      current
            DESCRIPTION
                "An entry in the table, containing information about
                 the storm control for each port."
            INDEX       { flSwitchStormCtrlPortNum }
        ::= { flSwitchStormCtrlTable 1 }

    FlSwitchStormCtrlEntry
        ::= SEQUENCE {
            flSwitchStormCtrlPortNum
                Integer32,
            flSwitchStormCtrlBroadcast
                INTEGER,
            flSwitchStormCtrlMulticast
                INTEGER,
            flSwitchStormCtrlUnicast
                INTEGER,
            flSwitchStormCtrlThreshold
                DisplayString,
            flSwitchStormCtrlThresholdUnicast
                DisplayString,
            flSwitchStormCtrlThresholdBroadcast
                DisplayString,
            flSwitchStormCtrlThresholdMulticast
                DisplayString, 
            flSwitchStormCtrlBandwidthUnicast
                Gauge32,
            flSwitchStormCtrlBandwidthBroadcast
                Gauge32,
            flSwitchStormCtrlBandwidthMulticast
                Gauge32,
            flSwitchStormCtrlFrameLimitUnicast
                Gauge32,
            flSwitchStormCtrlFrameLimitBroadcast
                Gauge32,
            flSwitchStormCtrlFrameLimitMulticast
                Gauge32                   
                
            }

    flSwitchStormCtrlPortNum
        OBJECT-TYPE
            SYNTAX      Integer32 (1..255)
            MAX-ACCESS  read-only
            STATUS      current
            DESCRIPTION
                "This object identifies the port number."
        ::= { flSwitchStormCtrlEntry 1 }

    flSwitchStormCtrlBroadcast
        OBJECT-TYPE
        SYNTAX INTEGER {
               disable(1),
               enable(2)
        }
        MAX-ACCESS read-write
        STATUS current
        DESCRIPTION
            "Enable/ disable the broadcast storm control function for the port.
	     When 'disable(1)', the broadcast storm control disabled.
	     When 'enable(2)', the broadcast storm control enabled."
        DEFVAL  {disable}
        ::= { flSwitchStormCtrlEntry 2 }

    flSwitchStormCtrlMulticast
        OBJECT-TYPE
        SYNTAX INTEGER {
               disable(1),
               enable(2)
        }
        MAX-ACCESS read-write
        STATUS current
        DESCRIPTION
            "Enable/ disable the multicast storm control function for the port.
	     When 'disable(1)', the multicast storm control disabled.
	     When 'enable(2)', the multicast storm control enabled."
        DEFVAL  {disable}
        ::= { flSwitchStormCtrlEntry 3 }

    flSwitchStormCtrlUnicast
        OBJECT-TYPE
        SYNTAX INTEGER {
               disable(1),
               enable(2)
        }
        MAX-ACCESS read-write
        STATUS current
        DESCRIPTION
            "Enable/ disable the unknown unicast storm control function for the port.
	     When 'disable(1)', the unknown unicast storm control disabled.
	     When 'enable(2)', the unknown unicast storm control enabled."
        DEFVAL  {disable}
        ::= { flSwitchStormCtrlEntry 4 }

    flSwitchStormCtrlThreshold
        OBJECT-TYPE
        SYNTAX DisplayString (SIZE(0..7))
        MAX-ACCESS read-write
        STATUS current
        DESCRIPTION
            "Set the storm control threshold percentage for broadcast, multicast and
	     unknown unicast. The storm control take place whenever the specific packet
	     rate over the threshold. Acceptable percentage value from 0.1 to 100."
        ::= { flSwitchStormCtrlEntry 5 }

       flSwitchStormCtrlThresholdUnicast
        OBJECT-TYPE
        SYNTAX DisplayString (SIZE(0..7))
        MAX-ACCESS read-write
        STATUS current
        DESCRIPTION
            "Set the storm control threshold percentage for  unknown unicast. 
            The storm control take place whenever the specific packet
	     rate over the threshold. Acceptable percentage value from 0.1 to 100."
        ::= { flSwitchStormCtrlEntry 6 }

        flSwitchStormCtrlThresholdBroadcast
        OBJECT-TYPE
        SYNTAX DisplayString (SIZE(0..7))
        MAX-ACCESS read-write
        STATUS current
        DESCRIPTION
            "Set the storm control threshold percentage broadcast
	      The storm control take place whenever the specific packet
	     rate over the threshold. Acceptable percentage value from 0.1 to 100."
        ::= { flSwitchStormCtrlEntry 7 }

        flSwitchStormCtrlThresholdMulticast
        OBJECT-TYPE
        SYNTAX DisplayString (SIZE(0..7))
        MAX-ACCESS read-write
        STATUS current
        DESCRIPTION
            "Set the storm control threshold percentage for multicast.
             The storm control take place whenever the specific packet
	     rate over the threshold. Acceptable percentage value from 0.1 to 100."
        ::= { flSwitchStormCtrlEntry 8 }
        
        flSwitchStormCtrlBandwidthUnicast OBJECT-TYPE
        SYNTAX      Gauge32(1..4294967295)
        MAX-ACCESS  read-write
        STATUS      current
        DESCRIPTION
                     "Configures the unicast storm recovery threshold for this port
                     in kilobits-per-second."
        DEFVAL { 5000 }
        ::= { flSwitchStormCtrlEntry 9 }
        
        
        flSwitchStormCtrlBandwidthBroadcast OBJECT-TYPE
        SYNTAX      Gauge32(1..4294967295)
        MAX-ACCESS  read-write
        STATUS      current
        DESCRIPTION
                     "Configures the broadcast storm recovery threshold for this port
                     in kilobits-per-second."
        DEFVAL { 5000 }
        ::= { flSwitchStormCtrlEntry 10 }
        
        
        flSwitchStormCtrlBandwidthMulticast OBJECT-TYPE
        SYNTAX      Gauge32(1..4294967295)
        MAX-ACCESS  read-write
        STATUS      current
        DESCRIPTION
                     "Configures the multicast storm recovery threshold for this port
                     in kilobits-per-second."
        DEFVAL { 5000 }
        ::= { flSwitchStormCtrlEntry 11 }
        
        flSwitchStormCtrlFrameLimitUnicast OBJECT-TYPE
        SYNTAX      Gauge32(1..4294967295)
        MAX-ACCESS  read-write
        STATUS      current
        DESCRIPTION
                     "Configures the unicast storm recovery threshold for this port
                     in packets-per-second."
        DEFVAL { 1220 }
        ::= { flSwitchStormCtrlEntry 12}
        
        
        flSwitchStormCtrlFrameLimitBroadcast OBJECT-TYPE
        SYNTAX      Gauge32(1..4294967295)
        MAX-ACCESS  read-write
        STATUS      current
        DESCRIPTION
                     "Configures the broadcast storm recovery threshold for this port
                     in packets-per-second."
        DEFVAL { 1220 }
        ::= { flSwitchStormCtrlEntry 13 }
        
        
        flSwitchStormCtrlFrameLimitMulticast OBJECT-TYPE
        SYNTAX      Gauge32(1..4294967295)
        MAX-ACCESS  read-write
        STATUS      current
        DESCRIPTION
                     "Configures the multicast storm recovery threshold for this port
                     in packets-per-second."
        DEFVAL { 1220 }
        ::= { flSwitchStormCtrlEntry 14}
        
        


 --
 --
 -- flSwitchTrafficShaping Group
 -- 
  flSwitchTrafficShapingTable OBJECT-TYPE
         SYNTAX      SEQUENCE OF FlSwitchTrafficShapingEntry
         MAX-ACCESS  not-accessible
         STATUS      current
         DESCRIPTION 
                     "Table of class-of-service queue configuration 
                     controls for the specified interface."
         ::= { flSwitchTrafficShaping 1 }

    flSwitchTrafficShapingEntry OBJECT-TYPE
         SYNTAX      FlSwitchTrafficShapingEntry
         MAX-ACCESS  not-accessible
         STATUS      current
         DESCRIPTION 
                     "Provides a general control mechanism that affects 
                     all queues on a given interface."
         INDEX       { flSwitchTrafficShapingIntfIndex }
         ::= { flSwitchTrafficShapingTable 1 }
         
    FlSwitchTrafficShapingEntry ::= SEQUENCE {         
           flSwitchTrafficShapingIntfIndex
               InterfaceIndexOrZero,
           flSwitchTrafficShapingIntfRate
               Unsigned32
           }
    
    flSwitchTrafficShapingIntfIndex OBJECT-TYPE
         SYNTAX      InterfaceIndexOrZero
         MAX-ACCESS  not-accessible
         STATUS      current
         DESCRIPTION
                     "A non-zero value indicates  
                     the ifIndex for the corresponding interface entry  
                     in the ifTable.  A value of zero represents global
                     configuration, which in turn causes all interface
		     		 entries to be updated for a set operation, or 
		     		 reflects the most recent global setting for a get
		     		 operation."
                    
         ::= { flSwitchTrafficShapingEntry 1 }

    flSwitchTrafficShapingIntfRate OBJECT-TYPE
         SYNTAX      Unsigned32 (0..100)
         MAX-ACCESS  read-create
         STATUS      current
         DESCRIPTION 
                     "Maximum bandwidth allowed for this interface as a 
                     whole, typically used to shape the outbound 
                     transmission rate. The value is specified in terms 
                     of percentage of overall link speed for the port in 
                     1% increments.  A value of 0 means there is no 
                     maximum bandwidth limit in effect and that the 
                     interface is allowed to transmit up to its maximum 
                     line rate (i.e., work conserving method).  
                     The default value is 0.
                     
                     When set to a non-zero value, the interface is 
                     restricted to using at most the bandwidth specified 
                     in this object for the outbound transmission rate 
                     (i.e., non-work-conserving method).  This bandwidth 
                     value is independent of any per-queue maximum 
                     bandwidth value(s) in effect for the interface 
                     and should be considered as a second-level 
                     transmission rate control mechanism that regulates 
                     the output of the entire interface regardless of 
                     which queues originate the outbound traffic."
         DEFVAL { 0 }
         ::= { flSwitchTrafficShapingEntry 2 }   
    
   --
   --
   -- flSwitchLagConfig Group
   --     
   flSwitchLagCreate OBJECT-TYPE
         SYNTAX      DisplayString (SIZE(0|1..15))
         MAX-ACCESS  read-write
         STATUS      current
         DESCRIPTION
                     "When this object is set with a non-empty string, a new LAG
                     will be created if possible, with the entered string as its
                     name. 
                     Get operation on this MIB object returns a null-value, as
                     for the purpose of viewing the LAG name, the user should
                     perform the traversal of agentLagSummaryConfigTable. For
                     this reason the get operation on this object
                     agentLagConfigCreate becomes insignificant."
         ::= { flSwitchLagConfig 1 }

    flSwitchLagSummaryTable OBJECT-TYPE
         SYNTAX      SEQUENCE OF FlSwitchLagSummaryEntry
         MAX-ACCESS  not-accessible
         STATUS      current
         DESCRIPTION
                     "A summary table of the switch's LAG config entries"
         ::= { flSwitchLagConfig 2 }

    flSwitchLagSummaryEntry OBJECT-TYPE
         SYNTAX      FlSwitchLagSummaryEntry
         MAX-ACCESS  not-accessible
         STATUS      current
         DESCRIPTION
                     "Switch's LAG config entry"
         INDEX       { flSwitchLagIndex }
         ::= { flSwitchLagSummaryTable 1 }

    FlSwitchLagSummaryEntry ::= SEQUENCE {
             flSwitchLagIndex
                 Integer32,
             flSwitchLagName
                 DisplayString,
             flSwitchLagLinkTrap
                 INTEGER,
             flSwitchLagAdminMode
                 INTEGER,
             flSwitchLagStpMode
                 INTEGER,
             flSwitchLagAddPort
                 Integer32,
             flSwitchLagDeletePort
                 Integer32,
             flSwitchLagStatus
                 RowStatus,
             flSwitchLagType
                 INTEGER,
             flSwitchLagStaticCapability
                 INTEGER,
             flSwitchLagHashOption  
                 Integer32,
             flSwitchLagMaxFrameSize
                 INTEGER,
             flSwitchLagJumboFrame
                 INTEGER,
             flSwitchLagLinkStatus
                 INTEGER,
            flSwitchLagMode
                 INTEGER
             }

     flSwitchLagIndex OBJECT-TYPE
         SYNTAX      Integer32 (1..255)
         MAX-ACCESS  read-only
         STATUS      current
         DESCRIPTION
                     "This value corresponds with the LAG interface in the ifTable."
         ::= { flSwitchLagSummaryEntry 1 }

    flSwitchLagName OBJECT-TYPE
         SYNTAX      DisplayString (SIZE(1..15))
         MAX-ACCESS  read-write
         STATUS      current
         DESCRIPTION
                     "The associated name of the LAG used during creation."
         ::= { flSwitchLagSummaryEntry 2 }

    flSwitchLagLinkTrap OBJECT-TYPE
         SYNTAX      INTEGER {
                      enable(1),
                      disable(2)
                     }
         MAX-ACCESS  read-write
         STATUS      current
         DESCRIPTION
                     "Configures sending Link Up/Down traps when the LAG interface goes Up or Down."
         ::= { flSwitchLagSummaryEntry 4 }

    flSwitchLagAdminMode OBJECT-TYPE
         SYNTAX      INTEGER {
                      enable(1),
                      disable(2)
                     }
         MAX-ACCESS  read-write
         STATUS      current
         DESCRIPTION
                     "Administratively enables or disables this LAG interface."
         ::= { flSwitchLagSummaryEntry 5 }

    flSwitchLagStpMode OBJECT-TYPE
         SYNTAX      INTEGER {
                      dot1d(1),
                      fast(2),
                      off(3),
                      dot1s(4)
                     }
         MAX-ACCESS  read-write
         STATUS      current
         DESCRIPTION
                     "If Dot1d is enabled, the valid values are:
                     dot1d(1), fast(2), and off(3)

                     If Dot1s is enabled, the valid values are:
                     off(3) and dot1s(4)"

         ::= { flSwitchLagSummaryEntry 6 }

    flSwitchLagAddPort OBJECT-TYPE
         SYNTAX      Integer32
         MAX-ACCESS  read-write
         STATUS      current
         DESCRIPTION
                     "Set to a non 0 value to add a port to the LAG.  Values correspond to
                     ifIndex values in the ifTable.

                     Note: The duplex type for the port to be added must be full duplex
                     and the port to be added must operate at the same speed as previously 
                     added port(s), if any."
         ::= { flSwitchLagSummaryEntry 7 }

    flSwitchLagDeletePort OBJECT-TYPE
         SYNTAX      Integer32
         MAX-ACCESS  read-write
         STATUS      current
         DESCRIPTION
                     "Set to a non 0 value to remove a port from the LAG.  Values correspond to
                     ifIndex values in the ifTable."
         ::= { flSwitchLagSummaryEntry 8 }

    flSwitchLagStatus OBJECT-TYPE
         SYNTAX      RowStatus
         MAX-ACCESS  read-write
         STATUS      current
         DESCRIPTION
                     "active(1)  - This LAG is enabled.
                     destroy(6) - Set to this value to remove the LAG."
         ::= { flSwitchLagSummaryEntry 9 }

    flSwitchLagType OBJECT-TYPE
         SYNTAX      INTEGER {
                     static(1),
                     dynamic(2)
                     }
         MAX-ACCESS  read-only
         STATUS      current
         DESCRIPTION
                      "static(1)         - This LAG is staticly maintained.
                       dynamic(2)        - This LAG is dynamicly maintained."

         ::= { flSwitchLagSummaryEntry 10 }

    flSwitchLagStaticCapability OBJECT-TYPE
         SYNTAX      INTEGER {
                      enable(1),
                      disable(2)
                     }
         MAX-ACCESS  read-write
         STATUS      current
         DESCRIPTION
                     "enable(1) - Static capability is enabled for this LAG interface
                     disable(2) - Static capability is disabled for this LAG interface"
         DEFVAL { disable }
         ::= { flSwitchLagSummaryEntry 11 }

    flSwitchLagHashOption OBJECT-TYPE
         SYNTAX      Integer32 (1..6)
         MAX-ACCESS  read-write
         STATUS      current
         DESCRIPTION
                     "Valid values correspond to

                      1 (=Source MAC, VLAN, EtherType, and incoming port
                             associated with the packet)
                      2 (=Destination MAC, VLAN, EtherType, and incoming port
                             associated with the packet)
                      3 (=Source/Destination MAC, VLAN, EtherType, and incoming
                             port associated with the packet)
                      4 (=Source IP and Source TCP/UDP fields of the packet)
                      5 (=Destination IP and Destination TCP/UDP Port fields
                             of the packet)
                      6 (=Source/Destination IP and source/destination TCP/UDP
                             Port fields of the packet)

                      Support for particular options may vary by device."
         ::= { flSwitchLagSummaryEntry 12 }

    flSwitchLagMaxFrameSize
    	OBJECT-TYPE
    	    SYNTAX 		INTEGER (1518..9216)
    	    MAX-ACCESS  read-write
    	    STATUS      current
    	    DESCRIPTION
    	       "This object configures the maximum transmission unit(MTU) or
    	        the size of the largest packet that can be sent/received on the
    	        interface."
    	::= { flSwitchLagSummaryEntry 13 }
    	
    flSwitchLagJumboFrame
    	OBJECT-TYPE
    	    SYNTAX 		INTEGER {
    	    				 disable(0),
    	    				 enable(1)
        	    				}
    	    MAX-ACCESS  read-write
    	    STATUS      current
    	    DESCRIPTION
    	       "This object enables/disables jumbo frames on an interface."
    	::= { flSwitchLagSummaryEntry 14 }

     flSwitchLagLinkStatus OBJECT-TYPE
         SYNTAX      INTEGER {
                      up(1),
                      down(2)
                     }
         MAX-ACCESS  read-only
         STATUS      current
         DESCRIPTION
                     "The current operational state of the LAG interface."
         ::= { flSwitchLagSummaryEntry 15 }

    flSwitchLagMode OBJECT-TYPE
         SYNTAX      INTEGER {
                     static(2),
                     lacp-passiv(3),
                     lacp-activ(4)
                     }
         MAX-ACCESS  read-write
         STATUS      current
         DESCRIPTION
                      "static(2)         - This LAG is staticly maintained.
                       lacp-passiv(3)    - This LAG is dynamicly maintained.Pdus are
                                           only send when the partner does.
                       lacp-activ(4)     - This LAG is dynamicly maintained. Pdus are
                                           send even if the partner doesn't support lacp."

         ::= { flSwitchLagSummaryEntry 16 }

    --**************************************************************************************

    flSwitchLagConfigTable OBJECT-TYPE
         SYNTAX      SEQUENCE OF FlSwitchLagConfigEntry
         MAX-ACCESS  not-accessible
         STATUS      current
         DESCRIPTION
                     "A detailed table of the switch's LAG config entries"
         ::= { flSwitchLagConfig 3 }

    flSwitchLagConfigEntry OBJECT-TYPE
         SYNTAX      FlSwitchLagConfigEntry
         MAX-ACCESS  not-accessible
         STATUS      current
         DESCRIPTION
                     "Switch's LAG config entry"
         INDEX       { flSwitchLagConfigIndex, flSwitchLagConfigIfIndex }
         ::= { flSwitchLagConfigTable 1 }

    FlSwitchLagConfigEntry ::= SEQUENCE {
             flSwitchLagConfigIndex
                 Integer32,
             flSwitchLagConfigIfIndex
                 Integer32,
             flSwitchLagConfigPortSpeed
                 OBJECT IDENTIFIER,
             flSwitchLagConfigPortStatus
                 INTEGER
             }

    flSwitchLagConfigIndex OBJECT-TYPE
         SYNTAX      Integer32 (1..255)
         MAX-ACCESS  read-only
         STATUS      current
         DESCRIPTION
                     "LAG index"
         ::= { flSwitchLagConfigEntry 1 }

    flSwitchLagConfigIfIndex OBJECT-TYPE
         SYNTAX      Integer32 (1..255)
         MAX-ACCESS  read-only
         STATUS      current
         DESCRIPTION
                     "LAG port index"
         ::= { flSwitchLagConfigEntry 2 }

    flSwitchLagConfigPortSpeed OBJECT-TYPE
         SYNTAX      OBJECT IDENTIFIER
         MAX-ACCESS  read-only
         STATUS      current
         DESCRIPTION
                     "LAG port speed.  See agentPortType for a description and list
                      of valid values."
         ::= { flSwitchLagConfigEntry 3 }

    flSwitchLagConfigPortStatus OBJECT-TYPE
         SYNTAX      INTEGER {
                     active(1),
                     inactive(2)
                     }
         MAX-ACCESS  read-only
         STATUS      current
         DESCRIPTION
                     "LAG port status.

                     active(1)   - Actively participating in the LAG.
                     inactive(2) - Not participating in the LAG."
         ::= { flSwitchLagConfigEntry 4 }

    flSwitchLagGlobalHashOption OBJECT-TYPE
         SYNTAX      Integer32 (1..7)
         MAX-ACCESS  read-write
         STATUS      current
         DESCRIPTION
                     "Valid values correspond to

                      1 (=Source MAC, VLAN, EtherType, and incoming port
                             associated with the packet)
                      2 (=Destination MAC, VLAN, EtherType, and incoming port
                             associated with the packet)
                      3 (=Source/Destination MAC, VLAN, EtherType, and incoming
                             port associated with the packet)
                      4 (=Source IP and Source TCP/UDP fields of the packet)
                      5 (=Destination IP and Destination TCP/UDP Port fields
                             of the packet)
                      6 (=Source/Destination IP and source/destination TCP/UDP
                             Port fields of the packet)
				      7 (=Source/Destination MAC, source/destination IP and
					         source/destination TCP/UDP Port fields of the packet)

                      Support for particular options may vary by device."
         ::= { flSwitchLagConfig 4 }

   --**************************************************************************************
   --  flSwitchDiffServConfig
   --
   --**************************************************************************************
     flSwitchDiffServConfig                 OBJECT IDENTIFIER ::= { flSwitch 15 }
    
    flSwitchDiffServEnable OBJECT-TYPE
	SYNTAX       INTEGER {
                      disable(1),
                      enable(2)
                     }
        MAX-ACCESS   read-write
        STATUS       current
	DESCRIPTION
         " DiffServ Admin Mode"
	DEFVAL    { disable }
        ::= { flSwitchDiffServConfig 1 }

     flSwitchDiffServConfigTable OBJECT-TYPE
         SYNTAX      SEQUENCE OF FlSwitchDiffServConfigEntry
         MAX-ACCESS  not-accessible
         STATUS      current
         DESCRIPTION
                     "A detailed table of the switch's created DiffServ Rules"
         ::= { flSwitchDiffServConfig 2 }

    flSwitchDiffServConfigEntry OBJECT-TYPE
         SYNTAX      FlSwitchDiffServConfigEntry
         MAX-ACCESS  not-accessible
         STATUS      current
         DESCRIPTION
                     "Switch's DiffServ config entry"
         INDEX       {  flSwitchDiffServCSIndex }
         ::= { flSwitchDiffServConfigTable 1 }

    FlSwitchDiffServConfigEntry ::= SEQUENCE {
             flSwitchDiffServCSIndex
                 Integer32,
             flSwitchDiffServCSName
                 DisplayString,
             flSwitchDiffServCriType
                 INTEGER,
             flSwitchDiffServCriEtypeValue
                 INTEGER,
             flSwitchDiffServCriEtypeValueCustom
                 EtypeValue,
             flSwitchDiffServCriIpTosBits
                 OCTET STRING,
             flSwitchDiffServCriIpTosMask
                 OCTET STRING,
             flSwitchDiffServCriIpPrecedence
                 Unsigned32,
             flSwitchDiffServServiceType
                 INTEGER,
             flSwitchDiffServServiceAssignQueueID
                 Unsigned32,
             flSwitchDiffServIncludedPorts
                 OCTET STRING,
             flSwitchDiffServRowStatus
                 RowStatus
             }

    flSwitchDiffServCSIndex OBJECT-TYPE
         SYNTAX      Integer32 (1..255)
         MAX-ACCESS  read-only
         STATUS      current
         DESCRIPTION
                     "DiffServ Rule Index"
         ::= { flSwitchDiffServConfigEntry 1 }


    flSwitchDiffServCSName OBJECT-TYPE
         SYNTAX      DisplayString (SIZE(1..31))
         MAX-ACCESS  read-create
         STATUS      current
         DESCRIPTION
                     "Name of the DiffServ Rule"
        ::= { flSwitchDiffServConfigEntry 2 }

     flSwitchDiffServCriType OBJECT-TYPE
         SYNTAX      INTEGER {
                     ethertype(1),
                     ipPrecedence(2),
                     ipTos(3)
                     }
         MAX-ACCESS  read-create
         STATUS      current
         DESCRIPTION
                     "This object must be created before the attributes or the match objects are created.
                     Choose one of the following criteria types: 
                        ethertype(1) Match ethertype field of mac header.
                        ipPrecedence(2) Match the precedence bits(0-2) in type of service field of IP header.
                        ipTos(3) Match Type of service field of IP header. The last 2 bits of this field are optional."
         ::= { flSwitchDiffServConfigEntry 3 }
     flSwitchDiffServCriEtypeValue OBJECT-TYPE
            SYNTAX      INTEGER {
                            user-value(0),
                            appletalk(1),                          
                            arp(2),
                            ibmsna(3),
                            ipv4(4),
                            ipv6(5),
                            ipx(6),
                            mpls-multicast(7),
                            mpls-unicast(8),
                            netbios(9),
                            novell(10),
                            pppoe(11),
                            reverse-arp(12)
                            }
            MAX-ACCESS  read-create
            STATUS      current
            DESCRIPTION
                "Ethertype keyword match value for the rule - only valid if the 
		      flSwitchDiffServCriType is set to ethertype(1).  A keyword
		      of user-value(0) requires that the flSwitchDiffServCriEtypeValueCustom
		      object also be set."
                                                                    
        ::= { flSwitchDiffServConfigEntry 4 }

--     flSwitchDiffServCriEtypeValueCustom OBJECT-TYPE
--            SYNTAX      Integer32 (1536..65535)
--            MAX-ACCESS  read-write
--            STATUS      current
--            DESCRIPTION
--                ""
--                                                                    
--        ::= { flSwitchDiffServConfigEntry 5 }

    flSwitchDiffServCriEtypeValueCustom OBJECT-TYPE
         SYNTAX      EtypeValue
         MAX-ACCESS  read-create
         STATUS      current 
         DESCRIPTION
                     "Ethertype match value for the class - only valid if the 
		      flSwitchDiffServCriType is set to ethertype(1) and
		      the flSwitchDiffServCriEtypeValue is set to user-value(0).
	              The allowed value for this object is 0x0600 to 0xFFFF." 
         ::= { flSwitchDiffServConfigEntry 5 }

     flSwitchDiffServCriIpTosBits OBJECT-TYPE
         SYNTAX      OCTET STRING (SIZE(1))
         MAX-ACCESS  read-create
         STATUS      current
         DESCRIPTION
                     "IP TOS bits match value for the rule - only valid if the 
		      flSwitchDiffServCriType is set to ipTos(8).
		      The TOS bits are defined as all eight bits of the Service 
		      Type octet in the IPv4 header."
         ::= { flSwitchDiffServConfigEntry 6 }
	 
     flSwitchDiffServCriIpTosMask OBJECT-TYPE
         SYNTAX      OCTET STRING (SIZE(1))
         MAX-ACCESS  read-create
         STATUS      current
         DESCRIPTION
                     "IP TOS bits mask match value for the rule - only valid if the 
		      flSwitchDiffServCriType is set to ipTos(8). This mask value
		      identifies the portion of flSwitchDiffServCriIpTosBits that 
		      is compared against a packet. A non-contiguous mask value is permitted." 
         ::= { flSwitchDiffServConfigEntry 7 }

     flSwitchDiffServCriIpPrecedence OBJECT-TYPE
         SYNTAX      Unsigned32 (0..7)
         MAX-ACCESS  read-create
         STATUS      current
         DESCRIPTION
                     "IP Precedence match value for the rule - only valid if the 
		      flSwitchDiffServCriType is set to ipPrecedence(7).
		      The Precedence bits are defined as the high-order three bits of
		      the Service Type octed in the IPv4 header." 
         ::= { flSwitchDiffServConfigEntry 8 }

     flSwitchDiffServServiceType OBJECT-TYPE
         SYNTAX      INTEGER {
		      assignQueue(1)
		      }

         MAX-ACCESS  read-create
         STATUS      current
         DESCRIPTION
                     "This object allows configuration of the service
                      provided to the packets that match the defined criteria."
         ::= { flSwitchDiffServConfigEntry 9 }

     flSwitchDiffServServiceAssignQueueID OBJECT-TYPE
         SYNTAX      Unsigned32
         MAX-ACCESS  read-create
         STATUS      current
         DESCRIPTION
                     "Queue identifier to which all inbound packets belonging to this 
		      class-instance are directed.  This attribute is only valid if the 
		      value of flSwitchDiffServServiceType is set to assignQueue(1)."
         ::= { flSwitchDiffServConfigEntry 10 }

     flSwitchDiffServIncludedPorts OBJECT-TYPE
        SYNTAX OCTET STRING (SIZE(1..32))
        MAX-ACCESS read-create
        STATUS current
        DESCRIPTION
            "This object allows configuration of the list of ports to which this rule and the corresponding service is applicable to.
             This is a long strings of 0 and 1 positioned in the sequence of port interface number and 1 represents that the rule
             should be applied to this port and 0 defines that the rule should not be applied to this port.
             (e.g    0100001000100000100000000000)
             This rule is applied to the port 2, 7, 11 and 17."       
        ::= { flSwitchDiffServConfigEntry 11 }
	 
   flSwitchDiffServRowStatus OBJECT-TYPE
      SYNTAX      RowStatus
      MAX-ACCESS  read-create
      STATUS       current
      DESCRIPTION 
          "The row status variable, used in accordance to installation
         and removal conventions for conceptual rows. To create a row in
         this table, a manager sets this object to either createAndGo(4)
         or createAndWait(5). The newly created row will be in active state later.
         To delete the DiffServ Rule set this object to destroy."
      ::= { flSwitchDiffServConfigEntry 12 }

    --
    --
    -- flSwitchDhcpServerConfig Group
    --
    
    flSwitchDhcpServerCtrl
        OBJECT-TYPE
           SYNTAX INTEGER {
               disable(1),
               enable(2)
               }
           MAX-ACCESS read-write
           STATUS current
           DESCRIPTION
              "Status of the DHCP server given by the user."
        ::= { flSwitchDhcpServerConfig 1 }

    flSwitchDhcpServerStartAddress
        OBJECT-TYPE
            SYNTAX      IpAddress
            MAX-ACCESS  read-write
            STATUS      current
            DESCRIPTION
               "The IPv4 address of the first address in the range.  The
              value of dhcpv4ServerRangeStartAddress MUST be less than or
              equal to the value of flSwitchDhcpServerEndAddress."
        ::= { flSwitchDhcpServerConfig 2 }

    flSwitchDhcpServerEndAddress
        OBJECT-TYPE
            SYNTAX      IpAddress
            MAX-ACCESS  read-write
            STATUS      current
            DESCRIPTION
               "The IPv4 address of the last address in the range.  The value
              of dhcpv4ServerRangeEndAddress MUST be greater than or equal
              to the value of flSwitchDhcpServerStartAddress."
        ::= { flSwitchDhcpServerConfig 3 }
    
    flSwitchDhcpServerSubnetmask
        OBJECT-TYPE
            SYNTAX      IpAddress
            MAX-ACCESS  read-write
            STATUS      current
            DESCRIPTION
               "The subnet address mask."
        ::= { flSwitchDhcpServerConfig 4 }
        
    flSwitchDhcpServerGatewayAddress
        OBJECT-TYPE
            SYNTAX      IpAddress
            MAX-ACCESS  read-write
            STATUS      current
            DESCRIPTION
               "IP address of the default gateway."
        ::= { flSwitchDhcpServerConfig 5 }

    flSwitchDhcpServerDnsAddress
        OBJECT-TYPE
            SYNTAX      IpAddress
            MAX-ACCESS  read-write
            STATUS      current
            DESCRIPTION
               "IP address of the DNS."
        ::= { flSwitchDhcpServerConfig 6 }

    flSwitchDhcpServerLeaseTime
        OBJECT-TYPE
            SYNTAX      INTEGER {
            							hour(3600),
            							day(86400),
            							week(604800),
            							month(2592000)
            							}
            MAX-ACCESS  read-write
            STATUS      current
            DESCRIPTION
               "Lease time in units of seconds. Valid values are 1 hour, 1 day, 1 week
                or 1 month."
            DEFVAL  {3600}
        ::= { flSwitchDhcpServerConfig 7 }

    flSwitchDhcpServerStatus
        OBJECT-TYPE
            SYNTAX      INTEGER {
                            notModified(1),
                            modified(2)
                            }
            MAX-ACCESS  read-only
            STATUS      current
            DESCRIPTION
                "This object is used to synchronize the modification of the DHCP
                server parameters used by the protocol stack based on the 
                flSwitchDhcpServerConfig MIB objects. 
                If flSwitchDhcpServerStatus returns notModified(1), no modifications 
                were made to flSwitchDhcpServerConfig parameters. If flSwitchDhcpServerStatus
                returns  modified(2), one or more objects were changed, but have not been 
                applied."
        ::= { flSwitchDhcpServerConfig 8 }

    flSwitchDhcpServerApply
        OBJECT-TYPE
            SYNTAX      INTEGER {
                            restore(1),
                            apply(2)
                            }
            MAX-ACCESS  read-write
            STATUS      current
            DESCRIPTION
                "This object is used to apply the modification of the DHCP server
                parameters used by the protocol stack based on the flSwitchDhcpServerConfig
                MIB objects. This allows the user to change flSwitchDhcpServerStartAddress, 
                flSwitchDhcpServerEndAddress, flSwitchDhcpServerSubnetmask,
                flSwitchDhcpServerGatewayAddress, flSwitchDhcpServerDnsAddress and
                flSwitchDhcpServerLeaseTime and then 
                apply the changes to the unit using apply(2).
                If one or more of the flSwitchDhcpServerConfig objects were modified, 
                the user can restore the parameters to a mirror of the current values 
                using restore(1)."
            DEFVAL  {restore}
        ::= { flSwitchDhcpServerConfig 9 }
		
    flSwitchDhcpServerAddressPoolSize
        OBJECT-TYPE
            SYNTAX      INTEGER
            MAX-ACCESS  read-write
            STATUS      current
            DESCRIPTION
               "This object specifies the pool size of IP addresses which will be distributed by the DHCP server"
            DEFVAL  {10}
        ::= { flSwitchDhcpServerConfig 10 }

   flSwitchDhcpServerAcceptBootp
        OBJECT-TYPE
            SYNTAX      INTEGER {
                            disable(1),
                            enable(2)
                        }
            MAX-ACCESS  read-write
            STATUS      current
            DESCRIPTION
               " This object specifies, if the DHCP Server accepts BOOTP requests (enable) or not (disable)."
            DEFVAL  {enable}
        ::= { flSwitchDhcpServerConfig 11 }

    flSwitchDhcpServerRunning
        OBJECT-TYPE
            SYNTAX      INTEGER {
                            inactive(1),
                            active(2)
                        }
            MAX-ACCESS  read-only
            STATUS      current
            DESCRIPTION
               " This object returns the current state of the DHCP server. If the pool is not configured
               correctly, the server may go into inactive state."
        ::= { flSwitchDhcpServerConfig 12 }

   -- DHCP Port local service

    flSwitchDhcpPortLocalService
        OBJECT IDENTIFIER ::= { flSwitchDhcpServerConfig 100 }    
		 
		 
    flSwitchDhcpPortLocalTable 
        OBJECT-TYPE
            SYNTAX      SEQUENCE OF FlSwitchDhcpPortLocalEntry
            MAX-ACCESS  not-accessible
            STATUS      current
            DESCRIPTION
                "Table with port based control information and settings
                 concerning the Port local DHCP service."
        ::= { flSwitchDhcpPortLocalService 1 }

    flSwitchDhcpPortLocalEntry
        OBJECT-TYPE
            SYNTAX      FlSwitchDhcpPortLocalEntry
            MAX-ACCESS  not-accessible
            STATUS      current
            DESCRIPTION
                "An entry in the table, containing information and settings
                 concerning port based configuration of Port local DHCP service."
            INDEX       { flSwitchDhcpPortLocalIndex }
        ::= { flSwitchDhcpPortLocalTable 1 }

    FlSwitchDhcpPortLocalEntry
        ::= SEQUENCE {
            flSwitchDhcpPortLocalIndex
                Integer32,
            flSwitchDhcpPortLocalOperation
                INTEGER,
            flSwitchDhcpPortLocalLeaseIP
                IpAddress,
            flSwitchDhcpPortLocalNetmask
                IpAddress,
            flSwitchDhcpPortLocalGateway
                IpAddress,
            flSwitchDhcpPortLocalDns
                IpAddress
            }
                
    flSwitchDhcpPortLocalIndex
        OBJECT-TYPE
            SYNTAX      Integer32 (1..1024)
            MAX-ACCESS  read-only
            STATUS      current
            DESCRIPTION
                "The port number referenced by this table line."
        ::= { flSwitchDhcpPortLocalEntry 1 }
        
    flSwitchDhcpPortLocalOperation
        OBJECT-TYPE
            SYNTAX      INTEGER{
                          disable(1),
                          enable(2)
                          }
            MAX-ACCESS  read-write
            STATUS      current
            DESCRIPTION
                "The operational status of the Port local DHCP service for this port.
                 NOTE: There will be no general DHCP service or Relay Agent functionality
                       on this port if enabled. "
        ::= { flSwitchDhcpPortLocalEntry 2 }

    flSwitchDhcpPortLocalLeaseIP
        OBJECT-TYPE
            SYNTAX      IpAddress
            MAX-ACCESS  read-write
            STATUS      current
            DESCRIPTION
               "The IPv4 address which will be offered to the client requesting on this port."
        ::= { flSwitchDhcpPortLocalEntry 3 }

    flSwitchDhcpPortLocalNetmask
        OBJECT-TYPE
            SYNTAX      IpAddress
            MAX-ACCESS  read-write
            STATUS      current
            DESCRIPTION
               "The netmask which will be offered to the client requesting on this port."
        ::= { flSwitchDhcpPortLocalEntry 4 }

    flSwitchDhcpPortLocalGateway
        OBJECT-TYPE
            SYNTAX      IpAddress
            MAX-ACCESS  read-write
            STATUS      current
            DESCRIPTION
               "The router address which will be offered to the client requesting on this port."
        ::= { flSwitchDhcpPortLocalEntry 5 }

    flSwitchDhcpPortLocalDns
        OBJECT-TYPE
            SYNTAX      IpAddress
            MAX-ACCESS  read-write
            STATUS      current
            DESCRIPTION
               "The dns address which will be offered to the client requesting on this port."
        ::= { flSwitchDhcpPortLocalEntry 6 }
        
    flSwitchDhcpPortLocalClear
        OBJECT-TYPE
            SYNTAX      INTEGER {
               doNothing(1),
               clear(2)
           }
            MAX-ACCESS  read-write
            STATUS      current
            DESCRIPTION
               "This object allows to delete all configured local bindings. Port local service will be disabled."
        ::= { flSwitchDhcpPortLocalService 2}	
         
   -- DHCP current leases

    flSwitchDhcpCurrentLeases
        OBJECT IDENTIFIER ::= { flSwitchDhcpServerConfig 101 }    
		 
		 
    flSwitchDhcpCurrentLeaseTable 
        OBJECT-TYPE
            SYNTAX      SEQUENCE OF FlSwitchDhcpCurrentLeaseEntry
            MAX-ACCESS  not-accessible
            STATUS      current
            DESCRIPTION
                "Table with current leases of lokal DHCP server."
        ::= { flSwitchDhcpCurrentLeases 1 }

    flSwitchDhcpCurrentLeaseEntry
        OBJECT-TYPE
            SYNTAX      FlSwitchDhcpCurrentLeaseEntry
            MAX-ACCESS  not-accessible
            STATUS      current
            DESCRIPTION
                "An entry in the table does contain information about an address-lease."
            INDEX       { flSwitchDhcpCurrentLeaseIP }
        ::= { flSwitchDhcpCurrentLeaseTable 1 }

    FlSwitchDhcpCurrentLeaseEntry
        ::= SEQUENCE {
            flSwitchDhcpCurrentLeaseIP
                IpAddress,
            flSwitchDhcpCurrentLeaseClientID
                DisplayString,
            flSwitchDhcpCurrentLeaseSystemUpTime
                TimeTicks,
            flSwitchDhcpCurrentLeaseTime
                OCTET STRING,
            flSwitchDhcpCurrentLeaseDate
                OCTET STRING,
            flSwitchDhcpCurrentLeaseSeconds
                Unsigned32,
            flSwitchDhcpCurrentLeaseStatus
                INTEGER,
            flSwitchDhcpCurrentLeaseLocalPort
                Integer32
            }
                
    flSwitchDhcpCurrentLeaseIP
        OBJECT-TYPE
            SYNTAX      IpAddress
            MAX-ACCESS  read-only
            STATUS      current
            DESCRIPTION
                "The IP address which has been leased."
        ::= { flSwitchDhcpCurrentLeaseEntry 1 }
        
    flSwitchDhcpCurrentLeaseClientID
        OBJECT-TYPE
            SYNTAX DisplayString
            MAX-ACCESS  read-only
            STATUS      current
            DESCRIPTION
                "The identifier of the client which holds the lease. "
        ::= { flSwitchDhcpCurrentLeaseEntry 2 }	 

    flSwitchDhcpCurrentLeaseSystemUpTime
        OBJECT-TYPE
            SYNTAX      TimeTicks
            MAX-ACCESS  read-only
            STATUS      current
            DESCRIPTION
                "This object contains the system up time
                at which an event occured."
        ::= { flSwitchDhcpCurrentLeaseEntry 3 }
        
    flSwitchDhcpCurrentLeaseTime
        OBJECT-TYPE
            SYNTAX      OCTET STRING
            MAX-ACCESS  read-only
            STATUS      current
            DESCRIPTION
                "This object contains the UTC time
                at which an event occured."
        ::= { flSwitchDhcpCurrentLeaseEntry 4 }
        
    flSwitchDhcpCurrentLeaseDate
        OBJECT-TYPE
            SYNTAX      OCTET STRING
            MAX-ACCESS  read-only
            STATUS      current
            DESCRIPTION
                "This object contains the UTC date
                at which an event occured."
        ::= { flSwitchDhcpCurrentLeaseEntry 5 }
        
    flSwitchDhcpCurrentLeaseSeconds
        OBJECT-TYPE
            SYNTAX      Unsigned32
            MAX-ACCESS  read-only
            STATUS      current
            DESCRIPTION
                "This object contains the UTC seconds
                used in NTP at which an event occured."
        ::= { flSwitchDhcpCurrentLeaseEntry 6 }
		 
	
    flSwitchDhcpCurrentLeaseStatus
        OBJECT-TYPE
            SYNTAX      INTEGER {
                            new(1),
                            renewed(2),
                            processing(3),
                            forever(4),
                            conflicted(5),
                            reserved(6),
                            portlocal(7),
                            static(8)
                            }
            MAX-ACCESS  read-only
            STATUS      current
            DESCRIPTION
                "The status of the current lease."
        ::= { flSwitchDhcpCurrentLeaseEntry 7 }	 

    flSwitchDhcpCurrentLeaseLocalPort
        OBJECT-TYPE
            SYNTAX      Integer32
            MAX-ACCESS  read-only
            STATUS      current
            DESCRIPTION
                "The port on which the lease has been registered. If 0 no port
                is associated to this entry."
        ::= { flSwitchDhcpCurrentLeaseEntry 8 }	 

    flSwitchDhcpCurrentLeasesRelease
        OBJECT-TYPE
            SYNTAX      INTEGER {
                            doNothing(1),
                            release(2)
                        }
            MAX-ACCESS  read-write
            STATUS      current
            DESCRIPTION
               " This object starts the release process if set to (release). The release process
                 will ping every dynamically allocated IP and frees the lease if no
                 answer is recorded."
            DEFVAL  {doNothing}
        ::= { flSwitchDhcpCurrentLeases 2 }
		 
	-- DHCP static bindings

    flSwitchDhcpStaticBinding
        OBJECT IDENTIFIER ::= { flSwitchDhcpServerConfig 102 }    
		 
		 
    flSwitchDhcpStaticBindingTable 
        OBJECT-TYPE
            SYNTAX      SEQUENCE OF FlSwitchDhcpStaticBindingEntry
            MAX-ACCESS  not-accessible
            STATUS      current
            DESCRIPTION
                "Table with configured bindings of lokal DHCP server."
        ::= { flSwitchDhcpStaticBinding 1 }

    flSwitchDhcpStaticBindingEntry
        OBJECT-TYPE
            SYNTAX      FlSwitchDhcpStaticBindingEntry
            MAX-ACCESS  not-accessible
            STATUS      current
            DESCRIPTION
                "An entry in the table does contain information about an address-lease."
            INDEX       { flSwitchDhcpStaticBindingIP }
        ::= { flSwitchDhcpStaticBindingTable 1 }

    FlSwitchDhcpStaticBindingEntry
        ::= SEQUENCE {
            flSwitchDhcpStaticBindingIP
                IpAddress,
            flSwitchDhcpStaticBindingClientID
                DisplayString
       }
		 
		 
    flSwitchDhcpStaticBindingIP
        OBJECT-TYPE
            SYNTAX      IpAddress
            MAX-ACCESS  read-write
            STATUS      current
            DESCRIPTION
                "The IP address reserved for static entry. setting this object to 0.0.0.0
                will delete the static entry."
        ::= { flSwitchDhcpStaticBindingEntry 1 }
        
    flSwitchDhcpStaticBindingClientID
        OBJECT-TYPE
            SYNTAX DisplayString
            MAX-ACCESS  read-write
            STATUS      current
            DESCRIPTION
                "The client to which the IP has been bound to. "
        ::= { flSwitchDhcpStaticBindingEntry 2 }	 		 
		 
    flSwitchDhcpStaticBindingClear
        OBJECT-TYPE
            SYNTAX      INTEGER {
              doNothing(1),
               clear(2)
           }
            MAX-ACCESS  read-write
            STATUS      current
            DESCRIPTION
               "This object allows to delete all configured static binds on this server."
        ::= { flSwitchDhcpStaticBinding 2 }		 
	
   -- DHCP Port Server service

    flSwitchDhcpPortServerService
        OBJECT IDENTIFIER ::= { flSwitchDhcpServerConfig 103 }    
		 
		 
    flSwitchDhcpPortServerTable 
        OBJECT-TYPE
            SYNTAX      SEQUENCE OF FlSwitchDhcpPortServerEntry
            MAX-ACCESS  not-accessible
            STATUS      current
            DESCRIPTION
                "Table with port based control information and settings
                 concerning the Port Server DHCP service."
        ::= { flSwitchDhcpPortServerService 1 }

    flSwitchDhcpPortServerEntry
        OBJECT-TYPE
            SYNTAX      FlSwitchDhcpPortServerEntry
            MAX-ACCESS  not-accessible
            STATUS      current
            DESCRIPTION
                "An entry in the table, containing information and settings
                 concerning port based configuration of Port Server DHCP service."
            INDEX       { flSwitchDhcpPortServerIndex }
        ::= { flSwitchDhcpPortServerTable 1 }

    FlSwitchDhcpPortServerEntry
        ::= SEQUENCE {
            flSwitchDhcpPortServerIndex
                Integer32,
            flSwitchDhcpPortServerOperation
                INTEGER,
            flSwitchDhcpPortServerStartAddress
                IpAddress,
            flSwitchDhcpPortServerAddressPoolSize
                INTEGER,
            flSwitchDhcpPortServerSubnetmask
                IpAddress,
            flSwitchDhcpPortServerGatewayAddress
                IpAddress,
            flSwitchDhcpPortServerDnsAddress
                IpAddress,
            flSwitchDhcpPortServerLeaseTime
                INTEGER
            }
                	              	
    flSwitchDhcpPortServerIndex
        OBJECT-TYPE
            SYNTAX      Integer32 (1..5096)
            MAX-ACCESS  read-only
            STATUS      current
            DESCRIPTION
                "The port number referenced by this table line."
        ::= { flSwitchDhcpPortServerEntry 1 }
        
    flSwitchDhcpPortServerOperation
        OBJECT-TYPE
            SYNTAX      INTEGER{
                          disable(1),
                          enable(2)
                          }
            MAX-ACCESS  read-write
            STATUS      current
            DESCRIPTION
                "The operational status of the Port Server DHCP service."
        ::= { flSwitchDhcpPortServerEntry 2 }

    flSwitchDhcpPortServerStartAddress
        OBJECT-TYPE
            SYNTAX      IpAddress
            MAX-ACCESS  read-write
            STATUS      current
            DESCRIPTION
               "The IPv4 address of the first address in the range.  The
              value of flSwitchDhcpPortServerStartAddress MUST be less than or
              equal to the value of flSwitchDhcpPortServerEndAddress."
        ::= { flSwitchDhcpPortServerEntry 3 }

    flSwitchDhcpPortServerAddressPoolSize
        OBJECT-TYPE
            SYNTAX      INTEGER
            MAX-ACCESS  read-write
            STATUS      current
            DESCRIPTION
               "This object specifies the pool size of IP addresses which will be distributed by the Port DHCP server"
            DEFVAL  {10}
        ::= { flSwitchDhcpPortServerEntry 4 }

    flSwitchDhcpPortServerSubnetmask
        OBJECT-TYPE
            SYNTAX      IpAddress
            MAX-ACCESS  read-write
            STATUS      current
            DESCRIPTION
               "The subnet address mask."
        ::= { flSwitchDhcpPortServerEntry 5 }

    flSwitchDhcpPortServerGatewayAddress
        OBJECT-TYPE
            SYNTAX      IpAddress
            MAX-ACCESS  read-write
            STATUS      current
            DESCRIPTION
               "IP address of the default gateway."
        ::= { flSwitchDhcpPortServerEntry 6 }

    flSwitchDhcpPortServerDnsAddress
        OBJECT-TYPE
            SYNTAX      IpAddress
            MAX-ACCESS  read-write
            STATUS      current
            DESCRIPTION
               "IP address of the DNS."
        ::= { flSwitchDhcpPortServerEntry 7 }

    flSwitchDhcpPortServerLeaseTime
        OBJECT-TYPE
            SYNTAX      INTEGER {
            							hour(3600),
            							day(86400),
            							week(604800),
            							month(2592000)
            							}
            MAX-ACCESS  read-write
            STATUS      current
            DESCRIPTION
               "Lease time in units of seconds. Valid values are 1 hour, 1 day, 1 week
                or 1 month."
            DEFVAL  {3600}
        ::= { flSwitchDhcpPortServerEntry 8 }
	
    --
    --                                                   
    -- flWorkRoutingIp
    --

    flWorkRoutingIpRoutingMode OBJECT-TYPE
         SYNTAX      INTEGER {
                      enable(1),
                      disable(2)
                     }
         MAX-ACCESS  read-write
         STATUS      current
         DESCRIPTION
                     "Administratively enables/disables routing on the switch."
         ::= { flWorkRoutingIp 1 }

    --**************************************************************************************
    -- flWorkRoutingIpInterfaceTable
    --
    --**************************************************************************************
        
    flWorkRoutingIpInterfaceTable OBJECT-TYPE
         SYNTAX      SEQUENCE OF FlWorkRoutingIpInterfaceEntry
         MAX-ACCESS  not-accessible
         STATUS      current
         DESCRIPTION 
                     ""
         ::= { flWorkRoutingIp 3 }

    flWorkRoutingIpInterfaceEntry OBJECT-TYPE
         SYNTAX      FlWorkRoutingIpInterfaceEntry
         MAX-ACCESS  not-accessible
         STATUS      current
         DESCRIPTION 
                     ""
         INDEX       { flWorkRoutingIpInterfaceIfIndex }
         ::= { flWorkRoutingIpInterfaceTable 1 }
         
    FlWorkRoutingIpInterfaceEntry ::= SEQUENCE {         
          flWorkRoutingIpInterfaceIfIndex
              Integer32,
          flWorkRoutingIpInterfaceIpAddress
              IpAddress,
          flWorkRoutingIpInterfaceNetMask
              IpAddress,
          flWorkRoutingIpInterfaceClearIp
              INTEGER,
          flWorkRoutingIpInterfaceRoutingMode
              INTEGER,
          flWorkRoutingIpInterfaceProxyARPMode
              INTEGER,
          flWorkRoutingIpInterfaceMtuValue
              Unsigned32,
          flWorkRoutingIpInterfaceBandwidth
              Unsigned32,
          flWorkRoutingIpInterfaceUnnumberedIfIndex
              InterfaceIndexOrZero,
          flWorkRoutingIpInterfaceIcmpUnreachables
              INTEGER,
          flWorkRoutingIpInterfaceIcmpRedirects
              INTEGER,
          flWorkRoutingIpInterfaceManagementAccess
              INTEGER,
          flWorkRoutingIpInterfaceAssignMode
              INTEGER,
          flWorkRoutingIpInterfaceMapIdx2IfTable
              Integer32
          }
          
    flWorkRoutingIpInterfaceIfIndex OBJECT-TYPE
         SYNTAX      Integer32 (1..255)
         MAX-ACCESS  read-only
         STATUS      current
         DESCRIPTION
                     "The IfIndex associated with this instance."
         ::= { flWorkRoutingIpInterfaceEntry 1 }
          
    flWorkRoutingIpInterfaceIpAddress OBJECT-TYPE
         SYNTAX      IpAddress
         MAX-ACCESS  read-write
         STATUS      current
         DESCRIPTION
                     "The IpAddress assigned to this interface.  When setting this value,
                     the value of flWorkRoutingIpInterfaceNetMask must be set at the same time."
         ::= { flWorkRoutingIpInterfaceEntry 2 }
          
    flWorkRoutingIpInterfaceNetMask OBJECT-TYPE
         SYNTAX      IpAddress
         MAX-ACCESS  read-write
         STATUS      current
         DESCRIPTION
                     "The NetMask assigned to this interface.  When setting this value, the 
                     value of flWorkRoutingIpInterfaceIpAddress must be set at the same time."
         ::= { flWorkRoutingIpInterfaceEntry 3 }
          
    flWorkRoutingIpInterfaceClearIp OBJECT-TYPE
         SYNTAX      INTEGER {
                      enable(1),
                      disable(2)
                     }
         MAX-ACCESS  read-write
         STATUS      current
         DESCRIPTION
                     "Sets the interfaces IpAddress and NetMask back to 0.0.0.0"
         ::= { flWorkRoutingIpInterfaceEntry 4 }
         
    flWorkRoutingIpInterfaceRoutingMode OBJECT-TYPE
         SYNTAX      INTEGER {
                      enable(1),
                      disable(2)
                     }
         MAX-ACCESS  read-write
         STATUS      current
         DESCRIPTION
                     "Enables or disables routing for this interface."
         ::= { flWorkRoutingIpInterfaceEntry 5 }

    flWorkRoutingIpInterfaceProxyARPMode OBJECT-TYPE
         SYNTAX      INTEGER {
                      enable(1),
                      disable(2)
                     }
         MAX-ACCESS  read-write
         STATUS      current
         DESCRIPTION
                     "Enables or disables Proxy ARP for this interface."
         ::= { flWorkRoutingIpInterfaceEntry 6 }
          
    flWorkRoutingIpInterfaceMtuValue OBJECT-TYPE
         SYNTAX      Unsigned32 (0|128..1500)
         MAX-ACCESS  read-write
         STATUS      current
         DESCRIPTION
                     "Configures the MTU value for this interface.  If the value returned is 0
                     this interface is not enabled for routing.  It is not valid to set this
                     value to 0 if routing is enabled."
         ::= { flWorkRoutingIpInterfaceEntry 7 }
    flWorkRoutingIpInterfaceBandwidth OBJECT-TYPE
         SYNTAX      Unsigned32 (0|1..10000000)
         MAX-ACCESS  read-write
         STATUS      current
         DESCRIPTION
                     "Configures the Bandwidth  value for this interface.  If the value returned is 0
                       bandwidth for this interface is not Configured."
                      ::= { flWorkRoutingIpInterfaceEntry 8 }  
          
    flWorkRoutingIpInterfaceUnnumberedIfIndex OBJECT-TYPE
         SYNTAX      InterfaceIndexOrZero
         MAX-ACCESS  read-only
         STATUS      current
         DESCRIPTION
                     "If this object is non-zero, it indicates that the interface is unnumbered,
                     and specifies which interface the address is borrowed from."
         ::= { flWorkRoutingIpInterfaceEntry 9 }

    flWorkRoutingIpInterfaceIcmpUnreachables OBJECT-TYPE
         SYNTAX      INTEGER {
                    enable(1),
                    disable(2)
                  }

         MAX-ACCESS  read-write
         STATUS      current
         DESCRIPTION
                     "If this object is enable, it indicates that ICMP unreachables can be sent on this
                      interface."
         ::= { flWorkRoutingIpInterfaceEntry 10 }

    flWorkRoutingIpInterfaceIcmpRedirects OBJECT-TYPE
         SYNTAX      INTEGER {
                    enable(1),
                    disable(2)
                  }
         MAX-ACCESS  read-write
         STATUS      current
         DESCRIPTION
                     "If this object is enable and flWorkRoutingIpIcmpRedirectsMode is also enable ICMP Redirects
                      can be sent on this interface."
         ::= { flWorkRoutingIpInterfaceEntry 11 }

    flWorkRoutingIpInterfaceManagementAccess OBJECT-TYPE
         SYNTAX      INTEGER {
                    enable(1),
                    disable(2)
                  }
         MAX-ACCESS  read-write
         STATUS      current
         DESCRIPTION
                     "If this object is enable, Management Interfaces can be accessed via this Interface"
         ::= { flWorkRoutingIpInterfaceEntry 12 }
          
    flWorkRoutingIpInterfaceAssignMode OBJECT-TYPE
         SYNTAX      INTEGER {
                    static(1),                            
                    bootp(2),
                    dhcp(3),
                    dcp(4)
                }
         MAX-ACCESS  read-write
         STATUS      current
         DESCRIPTION
                     "this object contains the IP Assignment Mode of this Interface"
         ::= { flWorkRoutingIpInterfaceEntry 13 }

    flWorkRoutingIpInterfaceMapIdx2IfTable OBJECT-TYPE
         SYNTAX      Integer32 (1..255)
         MAX-ACCESS  read-only
         STATUS      current
         DESCRIPTION
                     "The mapping to the Interface Index used in MIB-2 ifTable.
                      OID 1.3.6.1.2.1.2.2"
         ::= { flWorkRoutingIpInterfaceEntry 14 }
          
    --**************************************************************************************
    -- flWorkRoutingIpRouterDiscoveryTable
    --
    --**************************************************************************************
        
    flWorkRoutingIpRouterDiscoveryTable OBJECT-TYPE
         SYNTAX      SEQUENCE OF FlWorkRoutingIpRouterDiscoveryEntry
         MAX-ACCESS  not-accessible
         STATUS      current
         DESCRIPTION 
                     "There is no global administrative flag for router discovery.  The global
                     routing flag (flWorkRoutingIpRoutingMode) will be used for this purpose.  If routing
                     is disabled, router discovery is disabled as well."
         ::= { flWorkRoutingIp 4 }

    flWorkRoutingIpRouterDiscoveryEntry OBJECT-TYPE
         SYNTAX      FlWorkRoutingIpRouterDiscoveryEntry
         MAX-ACCESS  not-accessible
         STATUS      current
         DESCRIPTION 
                     ""
         INDEX       { flWorkRoutingIpRouterDiscoveryIfIndex }
         ::= { flWorkRoutingIpRouterDiscoveryTable 1 }
         
    FlWorkRoutingIpRouterDiscoveryEntry ::= SEQUENCE {         
          flWorkRoutingIpRouterDiscoveryIfIndex
              Integer32,
          flWorkRoutingIpRouterDiscoveryAdvertiseMode
              INTEGER,
          flWorkRoutingIpRouterDiscoveryMaxAdvertisementInterval
              Integer32,
          flWorkRoutingIpRouterDiscoveryMinAdvertisementInterval
              Integer32,
          flWorkRoutingIpRouterDiscoveryAdvertisementLifetime
              Integer32,
          flWorkRoutingIpRouterDiscoveryPreferenceLevel
              Integer32,
          flWorkRoutingIpRouterDiscoveryAdvertisementAddress
              IpAddress
          }
          
    flWorkRoutingIpRouterDiscoveryIfIndex OBJECT-TYPE
         SYNTAX      Integer32 (1..255)
         MAX-ACCESS  read-only
         STATUS      current
         DESCRIPTION
                     "Interface Number to configure Router Discovery on."
         ::= { flWorkRoutingIpRouterDiscoveryEntry 1 }
         
    flWorkRoutingIpRouterDiscoveryAdvertiseMode OBJECT-TYPE
         SYNTAX      INTEGER {
                      enable(1),
                      disable(2)
                     }
         MAX-ACCESS  read-write
         STATUS      current
         DESCRIPTION
                     "Enable or disable router discovery on the interface."
         DEFVAL      { enable }
         ::= { flWorkRoutingIpRouterDiscoveryEntry 2 }
         
    flWorkRoutingIpRouterDiscoveryMaxAdvertisementInterval OBJECT-TYPE
         SYNTAX      Integer32 (4..1800)
         MAX-ACCESS  read-write
         STATUS      current
         DESCRIPTION
                     "Maximum time allowed between sending router advertisements 
                     from the interface."
         DEFVAL      { 600 }
         ::= { flWorkRoutingIpRouterDiscoveryEntry 3 }
         
    flWorkRoutingIpRouterDiscoveryMinAdvertisementInterval OBJECT-TYPE
         SYNTAX      Integer32 (3..1800)
         MAX-ACCESS  read-write
         STATUS      current
         DESCRIPTION
                     "Minimum time allowed between sending router advertisements from the interface.
                     
                     This value must be less than or equal to 
                     flWorkRoutingIpRouterDiscoveryMaxAdvertisementInterval."
         DEFVAL      { 450 }
         ::= { flWorkRoutingIpRouterDiscoveryEntry 4 }
         
    flWorkRoutingIpRouterDiscoveryAdvertisementLifetime OBJECT-TYPE
         SYNTAX      Integer32 (4..9000)
         MAX-ACCESS  read-write
         STATUS      current
         DESCRIPTION
                     "Value of lifetime field of router advertsisement sent from 
                     the interface.
                     
                     This value must be greater than or equal to 
                     flWorkRoutingIpRouterDiscoveryMaxAdvertisementInterval."
         DEFVAL      { 1800 }
         ::= { flWorkRoutingIpRouterDiscoveryEntry 5 }
         
    flWorkRoutingIpRouterDiscoveryPreferenceLevel OBJECT-TYPE
         SYNTAX      Integer32
         MAX-ACCESS  read-write
         STATUS      current
         DESCRIPTION
                     "Preferability of the address as a default router address,
                     related to other addresses on the same subnet.  This is defined
                     as the larger the number, the higher the preference."
         DEFVAL      { 0 }
         ::= { flWorkRoutingIpRouterDiscoveryEntry 6 }
         
    flWorkRoutingIpRouterDiscoveryAdvertisementAddress OBJECT-TYPE
         SYNTAX      IpAddress
         MAX-ACCESS  read-write
         STATUS      current
         DESCRIPTION
                     "Address used when sending router advertisements from the interface."
         DEFVAL      { 'E0000001'H } -- 224.0.0.1
         ::= { flWorkRoutingIpRouterDiscoveryEntry 7 }
         
    --**************************************************************************************
    -- flWorkRoutingIpVlanTable
    --
    --**************************************************************************************
        
    flWorkRoutingIpVlanTable OBJECT-TYPE
         SYNTAX      SEQUENCE OF FlWorkRoutingIpVlanEntry
         MAX-ACCESS  not-accessible
         STATUS      current
         DESCRIPTION 
                     ""
         ::= { flWorkRoutingIp 5 }

    flWorkRoutingIpVlanEntry OBJECT-TYPE
         SYNTAX      FlWorkRoutingIpVlanEntry
         MAX-ACCESS  not-accessible
         STATUS      current
         DESCRIPTION 
                     "A Static VLAN for which routing can be enabled/disabled"
         INDEX       { flWorkRoutingIpVlanId }
         ::= { flWorkRoutingIpVlanTable 1 }
         
    FlWorkRoutingIpVlanEntry ::= SEQUENCE {         
          flWorkRoutingIpVlanId
              Integer32,
          flWorkRoutingIpVlanIfIndex
              Integer32,
          flWorkRoutingIpVlanRoutingStatus
              RowStatus
          }
          
    flWorkRoutingIpVlanId OBJECT-TYPE
         SYNTAX      Integer32 (1..4095)
         MAX-ACCESS  read-only
         STATUS      current
         DESCRIPTION
                     "The Vlan's Id."
         ::= { flWorkRoutingIpVlanEntry 1 }
         
    flWorkRoutingIpVlanIfIndex OBJECT-TYPE
         SYNTAX      Integer32 (1..255)
         MAX-ACCESS  read-only
         STATUS      current
         DESCRIPTION
                     "The IfIndex associated with this VLAN."
         ::= { flWorkRoutingIpVlanEntry 2 }
         
    flWorkRoutingIpVlanRoutingStatus OBJECT-TYPE
         SYNTAX      RowStatus
         MAX-ACCESS  read-create
         STATUS      current
         DESCRIPTION
                     "Status of Routing mode per Vlan.
                     active(1)       - Vlan is enabled for routing
                     createAndGo(4)  - Adds Vlan entry for routing
                     destroy(6)      - Removes Vlan from routing"
         ::= { flWorkRoutingIpVlanEntry 3 }
         
    --**************************************************************************************
    -- flWorkRoutingSecondaryAddressTable
    --
    --**************************************************************************************
        
    flWorkRoutingSecondaryAddressTable OBJECT-TYPE
         SYNTAX      SEQUENCE OF FlWorkRoutingSecondaryAddressEntry
         MAX-ACCESS  not-accessible
         STATUS      current
         DESCRIPTION 
                     "Contains a list of secondary IP Addresses associated with an interface."
         ::= { flWorkRoutingIp 6 }

    flWorkRoutingSecondaryAddressEntry OBJECT-TYPE
         SYNTAX      FlWorkRoutingSecondaryAddressEntry
         MAX-ACCESS  not-accessible
         STATUS      current
         DESCRIPTION 
                     "A secondary IP Address for a given interface.  This IP Address must not 
                     conflict with the IP Address configured in the flWorkRoutingIpInterfaceTable."
         INDEX       { flWorkRoutingIpInterfaceIfIndex, flWorkRoutingSecondaryIpAddress }
         ::= { flWorkRoutingSecondaryAddressTable 1 }
         
    FlWorkRoutingSecondaryAddressEntry ::= SEQUENCE {         
          flWorkRoutingSecondaryIpAddress
              IpAddress,
          flWorkRoutingSecondaryNetMask
              IpAddress,
          flWorkRoutingSecondaryStatus
              RowStatus
          }
          
    flWorkRoutingSecondaryIpAddress OBJECT-TYPE
         SYNTAX      IpAddress
         MAX-ACCESS  not-accessible
         STATUS      current
         DESCRIPTION
                     "The Secondary IP Address assigned to this interface."
         ::= { flWorkRoutingSecondaryAddressEntry 1 }
          
    flWorkRoutingSecondaryNetMask OBJECT-TYPE
         SYNTAX      IpAddress
         MAX-ACCESS  read-create
         STATUS      current
         DESCRIPTION
                     "The Secondary Net Mask assigned to this interface.  This value must be
                     set during creation, and can not be changed."
         ::= { flWorkRoutingSecondaryAddressEntry 2 }
          
    flWorkRoutingSecondaryStatus OBJECT-TYPE
         SYNTAX      RowStatus
         MAX-ACCESS  read-create
         STATUS      current
         DESCRIPTION
                     "Creates a new entry in the Secondary Address table.
                     Allowed values are:
                     
                     createAndGo(4)  - Creates an entry in this table, associating the address
                                       with a given interface.  The flWorkRoutingSecondaryNetMask
                                       object must be set during creation.
                                        
                     destroy(6)      - Removes the associated address from the interface."
         ::= { flWorkRoutingSecondaryAddressEntry 3 }



    --**************************************************************************************
    -- flWorkRoutingHelperAddressTable
    --
    --**************************************************************************************
    flWorkRoutingHelperAddressTable OBJECT-TYPE
         SYNTAX      SEQUENCE OF FlWorkRoutingHelperAddressEntry
         MAX-ACCESS  not-accessible
         STATUS      current
         DESCRIPTION
                     "Contains a list of Helper IP Addresses associated with an interface."
         ::= { flWorkRoutingIp  7}

    flWorkRoutingHelperAddressEntry OBJECT-TYPE
         SYNTAX      FlWorkRoutingHelperAddressEntry
         MAX-ACCESS  not-accessible
         STATUS      current
         DESCRIPTION
                     "A Helper IP Address for a given interface."
         INDEX       { flWorkRoutingIpInterfaceIfIndex, flWorkRoutingHelperIpAddress }
         ::= { flWorkRoutingHelperAddressTable 1 }

    FlWorkRoutingHelperAddressEntry ::= SEQUENCE {
          flWorkRoutingHelperIpAddress
              IpAddress,
           flWorkRoutingHelperStatus
              RowStatus
          }

    flWorkRoutingHelperIpAddress OBJECT-TYPE
         SYNTAX      IpAddress
         MAX-ACCESS  not-accessible
         STATUS      current
         DESCRIPTION
                     "The Helper IP Address assigned to this interface."
         ::= { flWorkRoutingHelperAddressEntry 1 }


    flWorkRoutingHelperStatus OBJECT-TYPE
         SYNTAX      RowStatus
         MAX-ACCESS  read-create
         STATUS      current
         DESCRIPTION
                     "Creates a new entry in the Helper Address table.
                     Allowed values are:

                     createAndGo(4)  - Creates an entry in this table, associating the address
                                       with a given interface.  The flWorkRoutingHelperNetMask
                                       object must be set during creation.

                     destroy(6)      - Removes the associated address from the interface."
         ::= { flWorkRoutingHelperAddressEntry 2 }



   --**************************************************************************************
   -- flWorkRoutingIpIcmp
   --
   --************************************************************************************** 
   flWorkRoutingIpIcmpControl                     OBJECT IDENTIFIER ::= { flWorkRoutingIp 8}
   flWorkRoutingIpIcmpEchoReplyMode OBJECT-TYPE
        SYNTAX      INTEGER {
                     enable(1),
                     disable(2)
                  }
         MAX-ACCESS  read-write
         STATUS      current
         DESCRIPTION
                     "Sets the administrative Echo Reply Mode."
         ::= { flWorkRoutingIpIcmpControl 1 }

  flWorkRoutingIpIcmpRedirectsMode OBJECT-TYPE
       SYNTAX      INTEGER {
                    enable(1),
                    disable(2)
                  }
       MAX-ACCESS  read-write
       STATUS      current
       DESCRIPTION 
                   "Sets the administrative Mode for sending Redirects. "
       ::= { flWorkRoutingIpIcmpControl 2 }

  flWorkRoutingIpIcmpRateLimitInterval OBJECT-TYPE
       SYNTAX      Integer32 (0..2147483647)
       MAX-ACCESS  read-write
       STATUS      current
       DESCRIPTION 
                   "Specifies the time interval between tokens being placed in the bucket for
                    ICMP Ratelimit."
       ::= { flWorkRoutingIpIcmpControl 3 }

  flWorkRoutingIpIcmpRateLimitBurstSize OBJECT-TYPE
       SYNTAX      Integer32 (1..200)
       MAX-ACCESS  read-write
       STATUS      current
       DESCRIPTION
                   "Specifies the number of tokens to be placed after timeout."
       ::= { flWorkRoutingIpIcmpControl 4 }

    --**************************************************************************************
    -- flWorkRoutingStaticRouteTable
    --
    
    --**************************************************************************************
    
    flWorkRoutingStaticRouteTable 
       OBJECT-TYPE
         SYNTAX      SEQUENCE OF FlWorkRoutingStaticRouteEntry
         MAX-ACCESS  not-accessible
         STATUS      current
         DESCRIPTION
                     "Contains a List of Static Routes."
         ::= { flWorkRoutingIp  9}


    flWorkRoutingStaticRouteEntry OBJECT-TYPE
         SYNTAX      FlWorkRoutingStaticRouteEntry
         MAX-ACCESS  not-accessible
         STATUS      current
         DESCRIPTION 
                     "An entry in the table does contain information about an static route entry."
         INDEX       { flWorkRoutingStaticRouteTableIndex }
         ::= { flWorkRoutingStaticRouteTable 1 }
         
    FlWorkRoutingStaticRouteEntry ::= SEQUENCE {
            flWorkRoutingStaticRouteTableIndex
                Integer32,
            flWorkRoutingStaticRouteTableDestNetwork
                IpAddress,
	    flWorkRoutingStaticRouteTableDestSubnetMask
                IpAddress,
	    flWorkRoutingStaticRouteTableNextHop
                IpAddress,
	    flWorkRoutingStaticRouteTablePreference
                Integer32,
	    flWorkRoutingStaticRouteTableActive
	        INTEGER,
            flWorkRoutingStaticRouteTableStatus
                RowStatus
        }

    flWorkRoutingStaticRouteTableIndex
        OBJECT-TYPE
            SYNTAX      Integer32 (1..10)
            MAX-ACCESS  read-only
            STATUS      current
            DESCRIPTION
                "Index of this entry.
				"
        ::= { flWorkRoutingStaticRouteEntry 1 }

    flWorkRoutingStaticRouteTableDestNetwork
        OBJECT-TYPE
            SYNTAX      IpAddress
            MAX-ACCESS  read-write
            STATUS      current
            DESCRIPTION
                "Network IP Address of the destination Network.
				"
        ::= { flWorkRoutingStaticRouteEntry 2 }

    flWorkRoutingStaticRouteTableDestSubnetMask
        OBJECT-TYPE
            SYNTAX      IpAddress
            MAX-ACCESS  read-write
            STATUS      current
            DESCRIPTION
                "Network Subnet Mask of the destination Network.
				"
        ::= { flWorkRoutingStaticRouteEntry 3 }
  
    flWorkRoutingStaticRouteTableNextHop
        OBJECT-TYPE
            SYNTAX      IpAddress
            MAX-ACCESS  read-write
            STATUS      current
            DESCRIPTION
                "IP Address of the Next Hop Router to
				the Destination network.
				"
        ::= { flWorkRoutingStaticRouteEntry 4 }
		
     flWorkRoutingStaticRouteTablePreference
        OBJECT-TYPE
            SYNTAX      Integer32 (0..10)
            MAX-ACCESS  read-write
            STATUS      current
            DESCRIPTION
                "Preference value for the Route."
        ::= { flWorkRoutingStaticRouteEntry 5 }	

     flWorkRoutingStaticRouteTableActive
        OBJECT-TYPE
            SYNTAX      INTEGER {
                            disable(1),
                            enable(2)
                        }
            MAX-ACCESS  read-write
            STATUS      current
            DESCRIPTION
                "This object shows the status of this 
				Route."
        ::= { flWorkRoutingStaticRouteEntry 6 }

    flWorkRoutingStaticRouteTableStatus OBJECT-TYPE
         SYNTAX      RowStatus
         MAX-ACCESS  read-create
         STATUS      current
         DESCRIPTION
                     "Status of Routing Table Entry.
                     active(1)       - Routing Table entry is present
                     createAndGo(4)  - Adds static routing entry
                     destroy(6)      - Removes static routing entry"
        ::= { flWorkRoutingStaticRouteEntry 7 }
		
    --**************************************************************************************
    -- flWorkRoutingArp
    --
    
    --**************************************************************************************
    
    flWorkRoutingArpAgeoutTime OBJECT-TYPE
         SYNTAX      Integer32 (15..21600)
         MAX-ACCESS  read-write
         STATUS      current
         DESCRIPTION
                     "Configures the ARP entry ageout time in seconds.
                     Allowable range: 15-21600"
         DEFVAL      { 1200 }

         ::= { flWorkRoutingArp 1 }
         
    flWorkRoutingArpResponseTime OBJECT-TYPE
         SYNTAX      Integer32 (1..10)
         MAX-ACCESS  read-write
         STATUS      current
         DESCRIPTION
                     "Configures the ARP request response timeout in seconds.
                     Allowable range: 1-10"
         ::= { flWorkRoutingArp 2 }
    
    flWorkRoutingArpMaxRetries OBJECT-TYPE
         SYNTAX      Integer32 (0..10)
         MAX-ACCESS  read-write
         STATUS      current
         DESCRIPTION
                     "Configures the ARP count of maximum request for retries.
                     Allowable range: 0-10"
         ::= { flWorkRoutingArp 3 }
    
    flWorkRoutingArpCacheSize OBJECT-TYPE
         SYNTAX      Integer32
         MAX-ACCESS  read-write
         STATUS      current
         DESCRIPTION
                     "Configures the ARP maximum number of entries in the cache.
		     Allowable range is platform-specific."
         ::= { flWorkRoutingArp 4 }
   
     flWorkRoutingArpDynamicRenew OBJECT-TYPE
         SYNTAX      INTEGER {
                      enable(1),
                      disable(2)
                     }
         MAX-ACCESS  read-write
         STATUS      current
         DESCRIPTION
                     "This indicates the current setting of ARP dynamic renew mode. "   
         DEFVAL      { enable }
         ::= { flWorkRoutingArp 5 } 
         
      flWorkRoutingArpTotalEntryCountCurrent OBJECT-TYPE
         SYNTAX      Gauge32
         MAX-ACCESS  read-only
         STATUS      current
         DESCRIPTION
                     "Current number of entries in the ARP cache."
         ::= { flWorkRoutingArp 6 }    

      flWorkRoutingArpTotalEntryCountPeak OBJECT-TYPE
         SYNTAX      Gauge32
         MAX-ACCESS  read-only
         STATUS      current
         DESCRIPTION
                     "Peak number of entries recorded in the ARP cache over
		     time.  This value is restarted whenever the ARP cache
		     size is changed."
         ::= { flWorkRoutingArp 7 }

     flWorkRoutingArpStaticEntryCountCurrent OBJECT-TYPE
         SYNTAX      Gauge32
         MAX-ACCESS  read-only
         STATUS      current
         DESCRIPTION
                     "Current number of configured static ARP entries."
         ::= { flWorkRoutingArp 8 }

     flWorkRoutingArpStaticEntryCountMax OBJECT-TYPE
         SYNTAX      Integer32
         MAX-ACCESS  read-only
         STATUS      current
         DESCRIPTION
                     "Maximum number of configurable static ARP entries."
         ::= { flWorkRoutingArp 9 }

         
--*************************************************************************

    flWorkRoutingLocalProxyArpTable OBJECT-TYPE
         SYNTAX      SEQUENCE OF FlWorkRoutingLocalProxyArpEntry
         MAX-ACCESS  not-accessible
         STATUS      current
         DESCRIPTION
                     "This table contains the per-interface configuration
                      parameters for Local Proxy Arp."
         ::= { flWorkRoutingArp 11 }

    flWorkRoutingLocalProxyArpEntry OBJECT-TYPE
         SYNTAX      FlWorkRoutingLocalProxyArpEntry
         MAX-ACCESS  not-accessible
         STATUS      current
         DESCRIPTION
                     "Represents a logical row in the
                      flWorkRoutingLocalProxyArpTable"
         INDEX       { ifIndex }
         ::= { flWorkRoutingLocalProxyArpTable 1 }

    FlWorkRoutingLocalProxyArpEntry ::= SEQUENCE {
          flWorkRoutingLocalProxyArpMode
              INTEGER
           }

     flWorkRoutingLocalProxyArpMode OBJECT-TYPE
         SYNTAX      INTEGER{
                     enable(1),
                     disable(2)
                     }
         MAX-ACCESS  read-write
         STATUS      current
         DESCRIPTION
                     "The Local Proxy Arp Mode for the interface."
         ::= { flWorkRoutingLocalProxyArpEntry 1 }

--*************************************************************************

    flWorkRoutingIntfArpTable OBJECT-TYPE
         SYNTAX      SEQUENCE OF FlWorkRoutingIntfArpEntry
         MAX-ACCESS  not-accessible
         STATUS      current
         DESCRIPTION 
                     "This table augments the MIB-II ipNetToMediaTable by providing
                     per-interface ARP entry information."
         ::= { flWorkRoutingArp 12 }

    flWorkRoutingIntfArpEntry OBJECT-TYPE
         SYNTAX      FlWorkRoutingIntfArpEntry
         MAX-ACCESS  not-accessible
         STATUS      current
         DESCRIPTION 
                     ""
         INDEX       { flWorkRoutingIntfArpIpAddress, 
                       flWorkRoutingIntfArpIfIndex}
         ::= { flWorkRoutingIntfArpTable 1 }
         
    FlWorkRoutingIntfArpEntry ::= SEQUENCE {         
           flWorkRoutingIntfArpIpAddress
               IpAddress,
           flWorkRoutingIntfArpIfIndex
               InterfaceIndex,
           flWorkRoutingIntfArpAge
               TimeTicks,        
           flWorkRoutingIntfArpMacAddress
               MacAddress,
           flWorkRoutingIntfArpType
               INTEGER,
           flWorkRoutingIntfArpStatus
               RowStatus
           }
    
    flWorkRoutingIntfArpIpAddress OBJECT-TYPE
         SYNTAX      IpAddress
         MAX-ACCESS  read-only
         STATUS      current
         DESCRIPTION
                     "The Type of Address assigned to this interface."
         ::= { flWorkRoutingIntfArpEntry 1 }
    
    flWorkRoutingIntfArpIfIndex OBJECT-TYPE
         SYNTAX      InterfaceIndex
         MAX-ACCESS  read-create
         STATUS      current
         DESCRIPTION
                     "The Associated IfIndex which identified the ARP Entry.
                     This value must be specified for static ARP entries on an
                     unnumbered interface"
         ::= { flWorkRoutingIntfArpEntry 2 }
         
    flWorkRoutingIntfArpAge OBJECT-TYPE
         SYNTAX      TimeTicks
         MAX-ACCESS  read-only
         STATUS      current 
         DESCRIPTION
                     "This defines the time (in seconds) since the ARP entry 
		     was last refreshed.  This value is 0 for ARP entries of
		     type local(1) or static(3), since these entries are 
		     not subject to aging."
         ::= { flWorkRoutingIntfArpEntry 3 }  
         
    flWorkRoutingIntfArpMacAddress OBJECT-TYPE
         SYNTAX      MacAddress
         MAX-ACCESS  read-create
         STATUS      current
         DESCRIPTION
                     "The hardware MAX Address that each interface maps to."
         ::= { flWorkRoutingIntfArpEntry 4 }
         
    flWorkRoutingIntfArpType OBJECT-TYPE
         SYNTAX      INTEGER {
                        local(1),
                        gateway(2),
                        static(3),
                        dynamic(4)
                     }
         MAX-ACCESS  read-only
         STATUS      current
         DESCRIPTION
                     "The type of ARP entry."
         ::= { flWorkRoutingIntfArpEntry 5 }
    
    flWorkRoutingIntfArpStatus OBJECT-TYPE
         SYNTAX      RowStatus
         MAX-ACCESS  read-write
         STATUS      current
         DESCRIPTION
                     "The status of this ARP entry.  Setting this object destroy will remove the entry."
         ::= { flWorkRoutingIntfArpEntry 6 }


    --**************************************************************************************
   -- flWorkRoutingVrrp
   --
   --**************************************************************************************

   flWorkRoutingVrrpAdminState OBJECT-TYPE
     SYNTAX      INTEGER {
                 enable(1),
                 disable(2)
                }
     MAX-ACCESS  read-write
     STATUS      current
     DESCRIPTION
                "Sets the administrative mode of VRRP in the router."
         ::= { flWorkRoutingVrrp 1 }
  

--**************************************************************************************
-- flWorkRoutingVrrpOperTable
--
--**************************************************************************************
   flWorkRoutingVrrpOperTable OBJECT-TYPE
       SYNTAX      SEQUENCE OF FlWorkRoutingVrrpOperEntry
       MAX-ACCESS   not-accessible
       STATUS       current
       DESCRIPTION
           "Operations table for a VRRP router which consists of a
            sequence (i.e., one or more conceptual rows) of
            `flWorkRoutingVrrpOperEntry' items."
       ::= { flWorkRoutingVrrp 2 }
   
   flWorkRoutingVrrpOperEntry OBJECT-TYPE
       SYNTAX FlWorkRoutingVrrpOperEntry
       MAX-ACCESS   not-accessible 
       STATUS       current
       DESCRIPTION 
           "An entry in the table contains operational priority that is 
            associated with a virtual router."
       INDEX    { ifIndex, vrrpOperVrId }
       ::= { flWorkRoutingVrrpOperTable 1 }

  FlWorkRoutingVrrpOperEntry ::=
      SEQUENCE {
          flWorkRoutingVrrpOperPriority 
              Integer32
          }
        
  flWorkRoutingVrrpOperPriority  OBJECT-TYPE 
     SYNTAX       Integer32 (0..255)
     MAX-ACCESS   read-only
     STATUS       current
     DESCRIPTION 
         "This object specifies the operational priority of the VRRP router.
         This value will be afftected by both the tracking process and the
         configured priority set by the vrrpOperPriority object."
     ::= {  flWorkRoutingVrrpOperEntry 1 }
 
     --**********************************************************************
     -- flWorkRoutingVrrpTrackIntfTable
     --**********************************************************************
 
   flWorkRoutingVrrpTrackIntfTable OBJECT-TYPE
       SYNTAX      SEQUENCE OF FlWorkRoutingVrrpTrackIntfEntry
       MAX-ACCESS   not-accessible
       STATUS       current
       DESCRIPTION
           "Tracking table for a VRRP router which consists of
            flWorkRoutingVrrpTrackIntfEntry items."
       ::= { flWorkRoutingVrrp 3 }
   
  flWorkRoutingVrrpTrackIntfEntry OBJECT-TYPE
       SYNTAX       FlWorkRoutingVrrpTrackIntfEntry
       MAX-ACCESS   not-accessible 
       STATUS       current
       DESCRIPTION 
           "An entry in the table contains tracked IP interfaces 
            associated with a virtual router."
       INDEX    { ifIndex, vrrpOperVrId,  flWorkRoutingVrrpTrackIntf }
       ::= { flWorkRoutingVrrpTrackIntfTable 1 }

  FlWorkRoutingVrrpTrackIntfEntry ::=
      SEQUENCE {
          flWorkRoutingVrrpTrackIntf  
              InterfaceIndex,
          flWorkRoutingVrrpTrackIfPrioDec
              Integer32,
          flWorkRoutingVrrpTrackIfState
              Integer32,
          flWorkRoutingVrrpTrackIfStatus
             RowStatus 
          }
        
  flWorkRoutingVrrpTrackIntf OBJECT-TYPE
      SYNTAX       InterfaceIndex
      MAX-ACCESS   read-create
      STATUS       current
      DESCRIPTION
          "This object specifies the interface to be tracked."
      ::= { flWorkRoutingVrrpTrackIntfEntry 1 }
       
  flWorkRoutingVrrpTrackIfPrioDec  OBJECT-TYPE 
     SYNTAX       Integer32 (1..254)
     MAX-ACCESS   read-create
     STATUS       current
     DESCRIPTION
        "This object specifies the decrement priority of the 
         VRRP router."
     DEFVAL { 10 }
     ::= { flWorkRoutingVrrpTrackIntfEntry 2 }
  
  flWorkRoutingVrrpTrackIfState OBJECT-TYPE
      SYNTAX      Integer32
      MAX-ACCESS  read-only
      STATUS       current
      DESCRIPTION
          "This object specifies the IP state of the tracked interface 
           for the virtual router. "
      ::= { flWorkRoutingVrrpTrackIntfEntry 3 }

  flWorkRoutingVrrpTrackIfStatus OBJECT-TYPE
      SYNTAX RowStatus
      MAX-ACCESS read-create
      STATUS       current
      DESCRIPTION 
          "The row status variable, used in accordance to installation
         and removal conventions for conceptual rows. To create a row in
         this table, a manager sets this object to either createAndGo(4)
         or createAndWait(5). The newly created row will be in active state later.
         To destroy the row set this object to destroy."
      ::= { flWorkRoutingVrrpTrackIntfEntry 4 }

 
     --**********************************************************************
     -- flWorkRoutingVrrpTrackRouteTable
     --**********************************************************************
 
   flWorkRoutingVrrpTrackRouteTable OBJECT-TYPE
       SYNTAX      SEQUENCE OF FlWorkRoutingVrrpTrackRouteEntry
       MAX-ACCESS   not-accessible
       STATUS       current
       DESCRIPTION
           "Tracking table for a VRRP router which consists of a
            'flWorkRoutingVrrpTrackRouteEntry' items."
       ::= { flWorkRoutingVrrp 4 }
   
  flWorkRoutingVrrpTrackRouteEntry OBJECT-TYPE
       SYNTAX FlWorkRoutingVrrpTrackRouteEntry
       MAX-ACCESS   not-accessible 
       STATUS       current
       DESCRIPTION 
           "An entry in the table contains tracked Routes
            associated with a virtual router."
       INDEX    { ifIndex, vrrpOperVrId,  flWorkRoutingVrrpTrackRtPfx, 
                  flWorkRoutingVrrpTrackRtPfxLen }
       ::= { flWorkRoutingVrrpTrackRouteTable 1 }

  FlWorkRoutingVrrpTrackRouteEntry ::=
      SEQUENCE {
          flWorkRoutingVrrpTrackRtPfx  
              IpAddress,
          flWorkRoutingVrrpTrackRtPfxLen
              Integer32,
          flWorkRoutingVrrpTrackRtPrioDec
              Integer32,
          flWorkRoutingVrrpTrackRtReachable
              Integer32,
          flWorkRoutingVrrpTrackRtStatus
             RowStatus 
          }
        
  flWorkRoutingVrrpTrackRtPfx OBJECT-TYPE
      SYNTAX       IpAddress
      MAX-ACCESS   read-create
      STATUS       current
      DESCRIPTION
          "This object specifies the prefix of the route to be tracked."
      ::= { flWorkRoutingVrrpTrackRouteEntry 1 }

  flWorkRoutingVrrpTrackRtPfxLen OBJECT-TYPE
      SYNTAX      Integer32 (1..32)
      MAX-ACCESS  read-create
      STATUS      current
      DESCRIPTION 
          "This object specifies prefix length of the route to be tracked."
      ::= { flWorkRoutingVrrpTrackRouteEntry 2 }
       
  flWorkRoutingVrrpTrackRtPrioDec  OBJECT-TYPE 
     SYNTAX       Integer32 (1..254)
     MAX-ACCESS   read-create
     STATUS       current
     DESCRIPTION
        "This object specifies the decrement priority of the 
         VRRP router."
     DEFVAL { 10 }
     ::= { flWorkRoutingVrrpTrackRouteEntry 3 }
  
  flWorkRoutingVrrpTrackRtReachable OBJECT-TYPE
      SYNTAX      Integer32
      MAX-ACCESS  read-only
      STATUS       current
      DESCRIPTION
          "This object specifies the reachability of the
           tracked route."
      ::= { flWorkRoutingVrrpTrackRouteEntry 4 }

  flWorkRoutingVrrpTrackRtStatus OBJECT-TYPE
      SYNTAX      RowStatus
      MAX-ACCESS  read-create
      STATUS       current
      DESCRIPTION 
          "The row status variable, used in accordance to installation
         and removal conventions for conceptual rows. To create a row in
         this table, a manager sets this object to either createAndGo(4)
         or createAndWait(5). The newly created row will be in active state later.
         To delete the tracked route set this object to destroy."
      ::= { flWorkRoutingVrrpTrackRouteEntry 5 }
  
     flWorkRoutingVrrpIcmpEcho OBJECT-TYPE
     SYNTAX      INTEGER  {
     			 enable(1),
     			 disable(2)
     			 }
     MAX-ACCESS  read-write
     STATUS      current
     DESCRIPTION
     			
                        "Sets and shows the ICMP ECHO state of VRRP in the router.
                         If enabled, the router will answer to ICMP Echo
                         requestes issued to a virtual router IP address if the
                         router ist the current master for this virtual router IP"
     	 ::= { flWorkRoutingVrrp 5 }

    --**************************************************************************************
    -- flWorkRoutingRip
    --
    --**************************************************************************************
    
    flWorkRoutingRipAdminState OBJECT-TYPE
         SYNTAX      INTEGER {
                     enable(1),
                     disable(2)
                  }
         MAX-ACCESS  read-write
         STATUS      current
         DESCRIPTION
                     "Sets the administrative mode of RIP in the router."
         ::= { flWorkRoutingRip 1 }
         
    flWorkRoutingRipSplitHorizonMode OBJECT-TYPE
         SYNTAX      INTEGER {
                     none(1),
                     simple(2),
                     poisonReverse(3)
                  }
         MAX-ACCESS  read-write
         STATUS      current
         DESCRIPTION
                     "Sets the RIP split horizon operating mode in the router.
		      A value of none(1) means split horizon processing is
		      disabled.  When set to simple(2), the simple split 
		      horizon technique is used.  When set to poisonReverse(3),
		      the split horizon with poison reverse technique is used.
		      The default split horizon mode is simple(2)."
         DEFVAL { simple }
         ::= { flWorkRoutingRip 2 }
         
    flWorkRoutingRipAutoSummaryMode OBJECT-TYPE
         SYNTAX      INTEGER {
                     enable(1),
                     disable(2)
                  }
         MAX-ACCESS  read-write
         STATUS      current
         DESCRIPTION
                     "Sets the RIP auto summarization mode in the router.
		      A value of enable(1) means that routes advertized by
		      this RIP router are combined, or summarized, whenever
		      possible into aggregates. When set to disable(2),
		      routes are not aggregated in RIP updates generated
		      by this router.  The default auto summary mode is 
		      enable(1)."
         DEFVAL { enable }
         ::= { flWorkRoutingRip 3 }
         
    flWorkRoutingRipHostRoutesAcceptMode OBJECT-TYPE
         SYNTAX      INTEGER {
                     enable(1),
                     disable(2)
                  }
         MAX-ACCESS  read-write
         STATUS      current
         DESCRIPTION
                     "Sets the RIP host route acceptance mode in the router.
		      A value of enable(1) means that host routes advertized
		      to this RIP router will be accepted (learned) into its
		      routing table.  When set to disable(2), host routes 
		      advertized in RIP updates from neighboring routers
		      are ignored.  The default host routes accept mode is
		      enable(1)."
         DEFVAL { enable }
         ::= { flWorkRoutingRip 4 }
         
         
    --************************************************************************************  
    flWorkRoutingRipDefaultMetric  OBJECT-TYPE
       SYNTAX      Integer32 (1..15)
       MAX-ACCESS  read-write
       STATUS      current
       DESCRIPTION
               "Default metric of redistributed routes, when RIP redistributes 
                from other protocols."
            ::= { flWorkRoutingRip 5 }

    flWorkRoutingRipDefaultMetricConfigured OBJECT-TYPE
         SYNTAX      TruthValue
         MAX-ACCESS  read-write
         STATUS      current
         DESCRIPTION
                     "Flag to determine whether RIP default-metric is configured or not."
         ::= { flWorkRoutingRip 6 } 
            
    flWorkRoutingRipDefaultInfoOriginate  OBJECT-TYPE
       SYNTAX      TruthValue
       MAX-ACCESS  read-write
       STATUS      current
       DESCRIPTION
               "Flag to determine, whether RIP can advertise a default-route learned
                from another protocol." 
       DEFVAL { false }
            ::= { flWorkRoutingRip 7 }   
                                
    flWorkRoutingRipRouteRedistTable OBJECT-TYPE
         SYNTAX      SEQUENCE OF FlWorkRoutingRipRouteRedistEntry
         MAX-ACCESS  not-accessible
         STATUS      current
         DESCRIPTION 
                     "This table contains the MIB objects required to configure 
                      route-redistribution for RIP. Here, RIP is the Destination
                      protocol and the source protocols can be any of : BGP, OSPF,
                      Static, Connected."
         ::= { flWorkRoutingRip 8 }

    flWorkRoutingRipRouteRedistEntry OBJECT-TYPE
         SYNTAX      FlWorkRoutingRipRouteRedistEntry
         MAX-ACCESS  not-accessible
         STATUS      current
         DESCRIPTION 
                     ""
         INDEX       { flWorkRoutingRipRouteRedistSource }
         ::= { flWorkRoutingRipRouteRedistTable 1 }
         
    FlWorkRoutingRipRouteRedistEntry ::= SEQUENCE {         
          flWorkRoutingRipRouteRedistSource
              INTEGER,
          flWorkRoutingRipRouteRedistMode
              INTEGER,
          flWorkRoutingRipRouteRedistMetric
              Integer32,
          flWorkRoutingRipRouteRedistMetricConfigured
              TruthValue,
          flWorkRoutingRipRouteRedistMatchInternal
              INTEGER,
          flWorkRoutingRipRouteRedistMatchExternal1
              INTEGER, 
          flWorkRoutingRipRouteRedistMatchExternal2
              INTEGER,
          flWorkRoutingRipRouteRedistMatchNSSAExternal1
              INTEGER, 
          flWorkRoutingRipRouteRedistMatchNSSAExternal2
              INTEGER,
          flWorkRoutingRipRouteRedistDistList
              Unsigned32,
          flWorkRoutingRipRouteRedistDistListConfigured
              TruthValue
          } 
         
    flWorkRoutingRipRouteRedistSource OBJECT-TYPE
         SYNTAX      INTEGER{
                     connected(1),
                     static(2),                     
                     ospf(3),
                     bgp(4)                                        
                     }
         
         MAX-ACCESS  read-only
         STATUS      current
         DESCRIPTION
                     "Source route, from which RIP can redistribute routes.
                      This object also acts as the identifier for  the 
                      RIP redistribution Table entry."
         ::= { flWorkRoutingRipRouteRedistEntry 1 }
                                                   
    flWorkRoutingRipRouteRedistMode OBJECT-TYPE
                 SYNTAX      INTEGER {
                      enable(1),
                      disable(2)
                     }
         MAX-ACCESS  read-write
         STATUS      current
         DESCRIPTION
                     "User enabels/disables route-redistribution for a particular source
                      protocol."
         DEFVAL { disable }
         ::= { flWorkRoutingRipRouteRedistEntry 2 }
     
    flWorkRoutingRipRouteRedistMetric OBJECT-TYPE
         SYNTAX      Integer32 (0..15)
         MAX-ACCESS  read-write
         STATUS      current
         DESCRIPTION
                     "Metric used for redistributing a particular source protocol route
                      into RIP."
         ::= { flWorkRoutingRipRouteRedistEntry 3 } 
         
    flWorkRoutingRipRouteRedistMetricConfigured OBJECT-TYPE
         SYNTAX      TruthValue
         MAX-ACCESS  read-write
         STATUS      current
         DESCRIPTION
                     "Flag to determine whether RIP redistribute-metric is configured or not."
         ::= { flWorkRoutingRipRouteRedistEntry 4 } 

         
    flWorkRoutingRipRouteRedistMatchInternal OBJECT-TYPE
         SYNTAX      INTEGER {
                      true(1),
                      false(2),
                      not-applicable(3)
                     }
         MAX-ACCESS  read-write
         STATUS      current
         DESCRIPTION
                     "If this flag is true, RIP redistributes OSPF internal routes.
                      It will be non-applicable, when source protocol is other than ospf."
         ::= { flWorkRoutingRipRouteRedistEntry 5 }
         
    flWorkRoutingRipRouteRedistMatchExternal1 OBJECT-TYPE
         SYNTAX      INTEGER {
                      true(1),
                      false(2),
                      not-applicable(3)
                     }
         MAX-ACCESS  read-write
         STATUS      current
         DESCRIPTION
                     "If this flag is true, RIP redistributes OSPF External1 routes.
                      It will be non-applicable, when source protocol is other than ospf."
         ::= { flWorkRoutingRipRouteRedistEntry 6 }
         
    flWorkRoutingRipRouteRedistMatchExternal2 OBJECT-TYPE
         SYNTAX      INTEGER {
                      true(1),
                      false(2),
                      not-applicable(3)
                     }
         MAX-ACCESS  read-write
         STATUS      current
         DESCRIPTION
                     "If this flag is true, RIP redistributes OSPF External2 routes.
                      It will be non-applicable, when source protocol is other than ospf."
         ::= { flWorkRoutingRipRouteRedistEntry 7 } 
         
    flWorkRoutingRipRouteRedistMatchNSSAExternal1 OBJECT-TYPE
         SYNTAX      INTEGER {
                      true(1),
                      false(2),
                      not-applicable(3)
                     }
         MAX-ACCESS  read-write
         STATUS      current
         DESCRIPTION
                     "If this flag is true, RIP redistributes OSPF NSSA-External1 routes.
                      It will be non-applicable, when source protocol is other than ospf."
         ::= { flWorkRoutingRipRouteRedistEntry 8 }
         
    flWorkRoutingRipRouteRedistMatchNSSAExternal2 OBJECT-TYPE
         SYNTAX      INTEGER {
                      true(1),
                      false(2),
                      not-applicable(3)
                     }
         MAX-ACCESS  read-write
         STATUS      current
         DESCRIPTION
                     "If this flag is true, RIP redistributes OSPF NSSA-External2 routes.
                      It will be non-applicable, when source protocol is other than ospf."
         ::= { flWorkRoutingRipRouteRedistEntry 9 } 
         
    flWorkRoutingRipRouteRedistDistList OBJECT-TYPE
         SYNTAX      Unsigned32 (1..199)
         MAX-ACCESS  read-write
         STATUS      current
         DESCRIPTION
                     "Access-list number of the access-list, which filters routes received
                      from a source-protocol."
         ::= { flWorkRoutingRipRouteRedistEntry 10 } 
         
     flWorkRoutingRipRouteRedistDistListConfigured OBJECT-TYPE
         SYNTAX      TruthValue
         MAX-ACCESS  read-write
         STATUS      current
         DESCRIPTION
                     "Flag to determine whether Access-list is configured or not."
         ::= { flWorkRoutingRipRouteRedistEntry 11 }


         

    -- The RIP Interface Configuration Table (augmented information).

    flWorkRoutingRip2IfConfTable OBJECT-TYPE
        SYNTAX   SEQUENCE OF FlWorkRoutingRip2IfConfEntry
        MAX-ACCESS   not-accessible
        STATUS   current
        DESCRIPTION
           "A list of subnets which require separate
           configuration in RIP.  Augments rip2IfConfTable
	   in the RIPv2-MIB."
       ::= { flWorkRoutingRip 9 }

    flWorkRoutingRip2IfConfEntry OBJECT-TYPE
        SYNTAX   FlWorkRoutingRip2IfConfEntry
        MAX-ACCESS   not-accessible
        STATUS   current
        DESCRIPTION
           "A Single Routing Domain in a single Subnet.
	   Augments rip2IfConfEntry in RIPv2-MIB."
       AUGMENTS { rip2IfConfEntry }
       ::= { flWorkRoutingRip2IfConfTable 1 }

    FlWorkRoutingRip2IfConfEntry ::=
        SEQUENCE {
            flWorkRoutingRip2IfConfAuthKeyId
                INTEGER
                  }

    flWorkRoutingRip2IfConfAuthKeyId OBJECT-TYPE
        SYNTAX   INTEGER (0..255)
        MAX-ACCESS   read-create
        STATUS   current
        DESCRIPTION
           "The identifier for the authentication key used
           on this interface.  This field is only meaningful 
           when the RIPv2-MIB rip2IfConfAuthType is md5(3); 
	   otherwise, the value is not used."
      ::= { flWorkRoutingRip2IfConfEntry 1 }  


    --**************************************************************************************
    -- flWorkRoutingOspf
    --
    --**************************************************************************************
    
     flWorkRoutingOspfDefaultMetric  OBJECT-TYPE
       SYNTAX      Integer32 (1..16777214)
       MAX-ACCESS  read-write
       STATUS      current
       DESCRIPTION
               "Default metric of redistributed routes, when OSPF redistributes 
                from other protocols."
            ::= { flWorkRoutingOspf 1 }

     flWorkRoutingOspfDefaultMetricConfigured OBJECT-TYPE
         SYNTAX      TruthValue
         MAX-ACCESS  read-write
         STATUS      current
         DESCRIPTION
                     "Flag to determine whether OSPF default-metric is configured or not."
         ::= { flWorkRoutingOspf 2 } 
 
            
     flWorkRoutingOspfDefaultInfoOriginate  OBJECT-TYPE
       SYNTAX      TruthValue
       MAX-ACCESS  read-write
       STATUS      current
       DESCRIPTION
               "Flag to determine, whether OSPF can advertise a default-route learned
                from another protocol."
       DEFVAL { false }
            ::= { flWorkRoutingOspf 3 }     
            
     flWorkRoutingOspfDefaultInfoOriginateAlways  OBJECT-TYPE
       SYNTAX      TruthValue
       MAX-ACCESS  read-write
       STATUS      current
       DESCRIPTION
               "When this flag is true, the router advertises 0.0.0.0/0.0.0.0 always.
                Without this option, OSPF will only advertise 0.0.0.0/0.0.0.0 if the
                router's forwarding table contains a default route."
       DEFVAL { false }
            ::= { flWorkRoutingOspf 4 } 
            
     flWorkRoutingOspfDefaultInfoOriginateMetric  OBJECT-TYPE
       SYNTAX      Integer32 (1..16777214)
       MAX-ACCESS  read-write
       STATUS      current
       DESCRIPTION
               "Metric of the default route,which OSPF advertises when learned from
                other protocol." 
       DEFVAL { 10 }
            ::= { flWorkRoutingOspf 5 } 
            
     flWorkRoutingOspfDefaultInfoOriginateMetricConfigured OBJECT-TYPE
         SYNTAX      TruthValue
         MAX-ACCESS  read-write
         STATUS      current
         DESCRIPTION
                     "Flag to determine whether OSPF default-info originate metric 
                      is configured or not."
         ::= { flWorkRoutingOspf 6 }
            
     flWorkRoutingOspfDefaultInfoOriginateMetricType  OBJECT-TYPE
       SYNTAX      INTEGER {
                   externalType1(1),
                   externalType2(2)
                   }
       MAX-ACCESS  read-write
       STATUS      current
       DESCRIPTION
               "Metric Type of the default route,which OSPF advertises when learned from
                other protocol. It can be 1(external type 1) or 2(external type 2)." 
       DEFVAL { 2 }
            ::= { flWorkRoutingOspf 7 } 
            
    flWorkRoutingOspfRouteRedistTable OBJECT-TYPE
         SYNTAX      SEQUENCE OF FlWorkRoutingOspfRouteRedistEntry
         MAX-ACCESS  not-accessible
         STATUS      current
         DESCRIPTION 
                     "This table contains the MIB objects required to configure 
                      route-redistribution for OSPF. Here, OSPF is the Destination
                      protocol and the source protocols can be any of : BGP, RIP,
                      Static, Connected."
         ::= { flWorkRoutingOspf 8 }

    flWorkRoutingOspfRouteRedistEntry OBJECT-TYPE
         SYNTAX      FlWorkRoutingOspfRouteRedistEntry
         MAX-ACCESS  not-accessible
         STATUS      current
         DESCRIPTION 
                     ""
         INDEX       { flWorkRoutingOspfRouteRedistSource }
         ::= { flWorkRoutingOspfRouteRedistTable 1 }
         
   FlWorkRoutingOspfRouteRedistEntry ::= SEQUENCE {  
          
          flWorkRoutingOspfRouteRedistSource
              INTEGER,
          flWorkRoutingOspfRouteRedistMode
              INTEGER,
          flWorkRoutingOspfRouteRedistMetric
              Integer32,
          flWorkRoutingOspfRouteRedistMetricConfigured
              TruthValue,
          flWorkRoutingOspfRouteRedistMetricType
              INTEGER,
          flWorkRoutingOspfRouteRedistTag
              Unsigned32,
          flWorkRoutingOspfRouteRedistSubnets
              TruthValue,
          flWorkRoutingOspfRouteRedistDistList
              Unsigned32,
          flWorkRoutingOspfRouteRedistDistListConfigured
              TruthValue
              }
              
    flWorkRoutingOspfRouteRedistSource OBJECT-TYPE
         SYNTAX      INTEGER{
                     connected(1),
                     static(2),                     
                     rip(3),
                     bgp(4)                                        
                     }
         MAX-ACCESS  read-only
         STATUS      current
         DESCRIPTION
                     "Source protocol, from which OSPF can redistribute routes.
                      This object also acts as the identifier for  the 
                      OSPF redistribution Table entry."
         ::= { flWorkRoutingOspfRouteRedistEntry 1 }
                                                   
    flWorkRoutingOspfRouteRedistMode OBJECT-TYPE
                 SYNTAX      INTEGER {
                      enable(1),
                      disable(2)
                     }
         MAX-ACCESS  read-write
         STATUS      current
         DESCRIPTION
                     "User enabels/disables route-redistribution for a particular source
                      protocol." 
         DEFVAL { disable }
         ::= { flWorkRoutingOspfRouteRedistEntry 2 }
     
    flWorkRoutingOspfRouteRedistMetric OBJECT-TYPE
         SYNTAX      Integer32 (0..16777214)
         MAX-ACCESS  read-write
         STATUS      current
         DESCRIPTION
                     "Metric used for redistributing a particular source protocol route
                      into OSPF."
         ::= { flWorkRoutingOspfRouteRedistEntry 3 } 

    flWorkRoutingOspfRouteRedistMetricConfigured OBJECT-TYPE
         SYNTAX      TruthValue
         MAX-ACCESS  read-write
         STATUS      current
         DESCRIPTION
                     "Flag to determine whether OSPF redistribute-metric is configured or not."
         ::= { flWorkRoutingOspfRouteRedistEntry 4 } 

         
    flWorkRoutingOspfRouteRedistMetricType OBJECT-TYPE
         SYNTAX      INTEGER {
                     externalType1(1),
                     externalType2(2)
                     }
         MAX-ACCESS  read-write
         STATUS      current
         DESCRIPTION
                     "Metric Type of routes,which OSPF redistributes from other source protocols.
                      It can be 1(external type 1) or 2(external type 2)."
         DEFVAL { externalType2 }
         ::= { flWorkRoutingOspfRouteRedistEntry 5 }
         
    flWorkRoutingOspfRouteRedistTag OBJECT-TYPE
         SYNTAX      Unsigned32(0..4294967295)
         MAX-ACCESS  read-write
         STATUS      current
         DESCRIPTION
                     "It specifies the tag field in routes redistributed by OSPF."
         ::= { flWorkRoutingOspfRouteRedistEntry 6 } 
         
    flWorkRoutingOspfRouteRedistSubnets OBJECT-TYPE
         SYNTAX      TruthValue
         MAX-ACCESS  read-write
         STATUS      current
         DESCRIPTION
                     "If this value is false, then OSPF will not redistribute subnetted routes."
         DEFVAL { false }
         ::= { flWorkRoutingOspfRouteRedistEntry 7 }
         
    flWorkRoutingOspfRouteRedistDistList OBJECT-TYPE
         SYNTAX      Unsigned32 (1..199) 
         MAX-ACCESS  read-write
         STATUS      current
         DESCRIPTION
                     "Access-list number of the access-list, which filters routes received
                      from a source-protocol."
         ::= { flWorkRoutingOspfRouteRedistEntry 8 } 
         
    flWorkRoutingOspfRouteRedistDistListConfigured OBJECT-TYPE
         SYNTAX      TruthValue
         MAX-ACCESS  read-write
         STATUS      current
         DESCRIPTION
                     "Flag to determine whether Access-list is configured or not."
         ::= { flWorkRoutingOspfRouteRedistEntry 9 }

         
    --  OSPF Interface Table (augmented information)

    flWorkRoutingOspfIfTable OBJECT-TYPE
        SYNTAX   SEQUENCE OF FlWorkRoutingOspfIfEntry
        MAX-ACCESS   not-accessible
        STATUS   current
        DESCRIPTION
           "The OSPF Interface Table describes the  inter-
           faces from the viewpoint of OSPF.  Augments 
	   ospfIfTable from the OSPF-MIB."
      ::= { flWorkRoutingOspf 9 }

    flWorkRoutingOspfIfEntry OBJECT-TYPE
        SYNTAX   FlWorkRoutingOspfIfEntry
        MAX-ACCESS   not-accessible
        STATUS   current
        DESCRIPTION
           "The OSPF Interface Entry describes one  inter-
           face from the viewpoint of OSPF.  Augments
	   ospfIfEntry in OSPF-MIB."
       AUGMENTS { ospfIfEntry }
       ::= { flWorkRoutingOspfIfTable 1 }

    FlWorkRoutingOspfIfEntry ::=
        SEQUENCE {
            flWorkRoutingOspfIfAuthKeyId
                INTEGER,
            flWorkRoutingOspfIfIpMtuIgnoreFlag
                INTEGER,
            flWorkRoutingOspfIfPassiveMode
                TruthValue
                  }

    flWorkRoutingOspfIfAuthKeyId OBJECT-TYPE
        SYNTAX   INTEGER (0..255)
        MAX-ACCESS   read-create
        STATUS   current
        DESCRIPTION
           "The identifier for the authentication key used
           on this interface.  This field is only meaningful 
           when the OSPF-MIB ospfIfAuthType is md5(2); 
	   otherwise, the value is not used."
      ::= { flWorkRoutingOspfIfEntry 1 }

    flWorkRoutingOspfIfIpMtuIgnoreFlag OBJECT-TYPE
         SYNTAX      INTEGER {
                      enable(1),
                      disable(2)
                     }
         MAX-ACCESS  read-write
         STATUS      current
         DESCRIPTION
                     "Configures the IP MTU Ignore Flag value for this OSPF interface."
         ::= { flWorkRoutingOspfIfEntry 2 }

     flWorkRoutingOspfIfPassiveMode  OBJECT-TYPE
       SYNTAX      TruthValue
       MAX-ACCESS  read-write
       STATUS      current
       DESCRIPTION
               "Flag to determine whether the interface is passive.
                A passive interface will not participate in the OSPF
                adjacency formation."
       DEFVAL { false }
            ::= { flWorkRoutingOspfIfEntry 3 }

    --  OSPF Virtual Interface Table (augmented information)

    flWorkRoutingOspfVirtIfTable OBJECT-TYPE
        SYNTAX   SEQUENCE OF FlWorkRoutingOspfVirtIfEntry
        MAX-ACCESS   not-accessible
        STATUS   current
        DESCRIPTION
           "Information about this router's virtual inter-
           faces.  Augments ospfVirtIfTable from the OSPF-MIB."
      ::= { flWorkRoutingOspf 10 }

    flWorkRoutingOspfVirtIfEntry OBJECT-TYPE
        SYNTAX   FlWorkRoutingOspfVirtIfEntry
        MAX-ACCESS   not-accessible
        STATUS   current
        DESCRIPTION
           "Information about a single Virtual Interface.
	   Augments ospfVirtIfEntry in OSPF-MIB."
       AUGMENTS { ospfVirtIfEntry }
       ::= { flWorkRoutingOspfVirtIfTable 1 }

    FlWorkRoutingOspfVirtIfEntry ::=
        SEQUENCE {
            flWorkRoutingOspfVirtIfAuthKeyId
                INTEGER
                  }

    flWorkRoutingOspfVirtIfAuthKeyId OBJECT-TYPE
        SYNTAX   INTEGER (0..255)
        MAX-ACCESS   read-create
        STATUS   current
        DESCRIPTION
           "The identifier for the authentication key used
           on this virtual interface.  This field is only meaningful 
           when the OSPF-MIB ospfVirtIfAuthType is md5(2); 
	   otherwise, the value is not used."
      ::= { flWorkRoutingOspfVirtIfEntry 1 }


    --**************************************************************************************
    
    flWorkRoutingOspfRFC1583CompatibilityMode OBJECT-TYPE
         SYNTAX      INTEGER {
                     enable(1),
                     disable(2)
                  }
         MAX-ACCESS  read-write
         STATUS      current
         DESCRIPTION
           "From RFC2328: 
            Controls the preference rules used in Section 16.4 when
            choosing among multiple AS-external-LSAs advertising the
            same destination. When set to 'enabled', the preference
            rules remain those specified by RFC 1583 ([Ref9]). When set
            to 'disabled', the preference rules are those stated in

            Section 16.4.1, which prevent routing loops when AS-
            external-LSAs for the same destination have been originated
            from different areas. Set to 'enabled' by default.

            In order to minimize the chance of routing loops, all OSPF
            routers in an OSPF routing domain should have
            RFC1583Compatibility set identically. When there are routers
            present that have not been updated with the functionality
            specified in Section 16.4.1 of this memo, all routers should
            have RFC1583Compatibility set to 'enabled'. Otherwise, all
            routers should have RFC1583Compatibility set to 'disabled',
            preventing all routing loops."
         DEFVAL { enable }
         ::= { flWorkRoutingOspf 11 }

    flWorkRoutingOspfSpfDelayTime OBJECT-TYPE
         SYNTAX      Integer32 (0..65535)
         MAX-ACCESS   read-write
         STATUS   current
         DESCRIPTION
           "Delay time (in seconds) between when OSPF
            receives a topology change and when it
            starts an SPF calculation. It can be an
            integer from 0 to 65535. The default
            time is 5 seconds. A value of 0 means
            that there is no delay; that is, the
            SPF calculation is started immediately."
         DEFVAL { 5 }
         ::= {  flWorkRoutingOspf 12 }   

    flWorkRoutingOspfSpfHoldTime OBJECT-TYPE
         SYNTAX      Integer32 (0..65535)
         MAX-ACCESS   read-write
         STATUS   current
         DESCRIPTION
           "Minimum time (in seconds) between two
            consecutive SPF calculations. It can
            be an integer from 0 to 65535. The
            default time is 10 seconds. A value
            of 0 means that there is no delay;
            that is, two SPF calculations can
            be done, one immediately after the
            other."
         DEFVAL { 10 }
         ::= { flWorkRoutingOspf  13 }   

    flWorkRoutingOspfAutoCostRefBw OBJECT-TYPE
         SYNTAX      Unsigned32 (1..4294967)
         MAX-ACCESS   read-write
         STATUS   current
         DESCRIPTION
         "Auto cost refernece bandwidth of the 
         router interfaces for ospf metric calculations.
         It can be an integer from 1 to 4294967. The
         default reference bandwidth is 100 Mbps."
         DEFVAL { 100 }
         ::= { flWorkRoutingOspf  14 }    

     --**************************************************************************************
     -- Following OSPF MIB general group objects/tables are added .
     -- These contain opaque related tables and scalars.
     --**************************************************************************************
    flWorkRoutingOspfOpaqueLsaSupport  OBJECT-TYPE 
         SYNTAX       TruthValue 
         MAX-ACCESS   read-write
         STATUS       current 
         DESCRIPTION 
           "The router's support for Opaque LSA types. 
            This object is persistent and when written 
            the entity SHOULD save the change to non-volatile
            storage." 
         REFERENCE 
           "The OSPF Opaque LSA Option" 
         ::= { flWorkRoutingOspf 15 } 


         --  OSPF Type10 (Area Opaque) Link State Database 

    flWorkRoutingOspfAreaOpaqueLsdbTable OBJECT-TYPE 
         SYNTAX       SEQUENCE OF FlWorkRoutingOspfAreaOpaqueLsdbEntry 
         MAX-ACCESS   not-accessible 
         STATUS       current 
         DESCRIPTION 
           "The OSPF Process's Area Link State Database (LSDB). 
            The LSDB contains type-10 Link State Advertisements 
            from throughout the areas that the device is attached to." 
         REFERENCE 
           "OSPF Version 2, Section 12 Link State Advertisements" 
         ::= { flWorkRoutingOspf 16 } 

    flWorkRoutingOspfAreaOpaqueLsdbEntry OBJECT-TYPE 
         SYNTAX   FlWorkRoutingOspfAreaOpaqueLsdbEntry 
         MAX-ACCESS   not-accessible 
         STATUS   current 
         DESCRIPTION 
           "A single AreaOpaque Link State Advertisement." 
         INDEX { flWorkRoutingOspfAreaOpaqueLsdbAreaId, flWorkRoutingOspfAreaOpaqueLsdbType, 
           flWorkRoutingOspfAreaOpaqueLsdbLsid, flWorkRoutingOspfAreaOpaqueLsdbRouterId } 
         ::= { flWorkRoutingOspfAreaOpaqueLsdbTable 1 } 

    FlWorkRoutingOspfAreaOpaqueLsdbEntry ::= 
         SEQUENCE { 
             flWorkRoutingOspfAreaOpaqueLsdbAreaId 
               IpAddress, 
             flWorkRoutingOspfAreaOpaqueLsdbType 
               INTEGER, 
             flWorkRoutingOspfAreaOpaqueLsdbLsid 
               IpAddress, 
             flWorkRoutingOspfAreaOpaqueLsdbRouterId 
               IpAddress, 
             flWorkRoutingOspfAreaOpaqueLsdbSequence 
               Integer32, 
             flWorkRoutingOspfAreaOpaqueLsdbAge 
               Integer32, 
             flWorkRoutingOspfAreaOpaqueLsdbChecksum 
               Integer32, 
             flWorkRoutingOspfAreaOpaqueLsdbAdvertisement 
               OCTET STRING 
           } 

    flWorkRoutingOspfAreaOpaqueLsdbAreaId OBJECT-TYPE 
         SYNTAX       IpAddress 
         MAX-ACCESS   read-only 
         STATUS       current 
         DESCRIPTION 
             "The 32 bit identifier of the Area from which 
              the LSA was received." 
         REFERENCE 
             "OSPF Version 2, Appendix C.2 Area parameters" 
         ::= { flWorkRoutingOspfAreaOpaqueLsdbEntry 1 } 

    flWorkRoutingOspfAreaOpaqueLsdbType OBJECT-TYPE 
         SYNTAX       INTEGER { 
                       areaOpaqueLink (10) 
                     } 
         MAX-ACCESS   read-only 
         STATUS       current 
         DESCRIPTION 
             "The type of the link state advertisement. 
              Each link state type has a separate advertisement 
              format." 
         REFERENCE 
             "OSPF Version 2, Appendix A.4.1 The  Link  State 
              Advertisement header" 
         ::= { flWorkRoutingOspfAreaOpaqueLsdbEntry 2 } 

    flWorkRoutingOspfAreaOpaqueLsdbLsid OBJECT-TYPE 
         SYNTAX       IpAddress 
         MAX-ACCESS   read-only 
         STATUS       current 
         DESCRIPTION 
             "The Link State ID is an LS Type Specific field 
              containing either a Router ID or an IP Address; 
              it identifies the piece of the routing domain 
              that is being described by the advertisement." 
         REFERENCE 
             "OSPF Version 2, Section 12.1.4 Link State ID" 
         ::= { flWorkRoutingOspfAreaOpaqueLsdbEntry 3 } 

    flWorkRoutingOspfAreaOpaqueLsdbRouterId OBJECT-TYPE 
         SYNTAX       IpAddress 
         MAX-ACCESS   read-only 
         STATUS       current 
         DESCRIPTION 
             "The 32 bit number that uniquely identifies the 
              originating router in the Autonomous System." 
         REFERENCE 
             "OSPF Version 2, Appendix C.1 Global parameters" 
         ::= { flWorkRoutingOspfAreaOpaqueLsdbEntry 4 } 

    flWorkRoutingOspfAreaOpaqueLsdbSequence OBJECT-TYPE 
         SYNTAX       Integer32 
         MAX-ACCESS   read-only 
         STATUS       current 
         DESCRIPTION 
             "The sequence number field is a signed 32-bit 
              integer. It starts with the value '80000001'h, 
              or -'7FFFFFFF'h, and increments until '7FFFFFFF'h. 
              Thus, a typical sequence number will be very negative. 
              It is used to detect old and duplicate link state 
              advertisements. The space of sequence numbers is linearly 
              ordered. The larger the sequence number the more recent 
              the advertisement." 
         REFERENCE 
             "OSPF Version 2, Section 12.1.6 LS sequence 
              number" 
         ::= { flWorkRoutingOspfAreaOpaqueLsdbEntry 5 } 

    flWorkRoutingOspfAreaOpaqueLsdbAge OBJECT-TYPE 
         SYNTAX       Integer32 -- Should be 0..MaxAge, except when 
        -- doNotAge bit is set 
         UNITS        "seconds" 
         MAX-ACCESS   read-only 
         STATUS       current 
         DESCRIPTION 
             "This field is the age of the link state advertisement 
              in seconds." 
         REFERENCE 
             "OSPF Version 2, Section 12.1.1 LS age" 
         ::= { flWorkRoutingOspfAreaOpaqueLsdbEntry 6 }

    flWorkRoutingOspfAreaOpaqueLsdbChecksum OBJECT-TYPE
         SYNTAX       Integer32
         MAX-ACCESS   read-only
         STATUS       current
         DESCRIPTION
             "This field is the checksum of the complete contents of
              the advertisement, excepting the age field. The age field
              is excepted so that an advertisement's age can be 
              incremented without updating the checksum. The checksum
              used is the same that is used for ISO connectionless
              datagrams; it is commonly referred to as the Fletcher 
              checksum."
         REFERENCE 
             "OSPF Version 2, Section 12.1.7 LS checksum" 
         ::= { flWorkRoutingOspfAreaOpaqueLsdbEntry 7 }

    flWorkRoutingOspfAreaOpaqueLsdbAdvertisement OBJECT-TYPE 
         SYNTAX       OCTET STRING (SIZE (1..65535)) 
         MAX-ACCESS   read-only 
         STATUS       current 
         DESCRIPTION 
             "The entire Link State Advertisement, including 
              its header. 
              Note that for variable length LSAs, SNMP agents 
              may not be able to return the largest string size" 
         REFERENCE 
             "OSPF Version 2, Section 12 Link State Advertisements" 
         ::= { flWorkRoutingOspfAreaOpaqueLsdbEntry 8 }

   --  OSPF Link State Database, Link-Local for non-virtual links 


    flWorkRoutingOspfLocalLsdbTable OBJECT-TYPE 
         SYNTAX       SEQUENCE OF FlWorkRoutingOspfLocalLsdbEntry 
         MAX-ACCESS   not-accessible 
         STATUS       current 
         DESCRIPTION 
             "The OSPF Process's Link-Local Link State Database 
              for non-virtual links. 
              This table is identical to the OSPF LSDB Table 
              in format, but contains only Link-Local Link State 
              Advertisements for non-virtual links. The purpose is 
              to allow Link-Local LSAs to be displayed for each 
              non-virtual interface. This table is implemented to 
              support type-9 LSAs which are defined 
              in 'The OSPF Opaque LSA Option'." 
         REFERENCE 
             "OSPF Version 2, Section 12 Link State 
              Advertisements and The OSPF Opaque LSA Option" 
         ::= { flWorkRoutingOspf 17 }

    flWorkRoutingOspfLocalLsdbEntry OBJECT-TYPE 
         SYNTAX       FlWorkRoutingOspfLocalLsdbEntry 
         MAX-ACCESS   not-accessible 
         STATUS       current 
         DESCRIPTION 
             "A single Link State Advertisement." 
         INDEX { flWorkRoutingOspfLocalLsdbIpAddress, flWorkRoutingOspfLocalLsdbAddressLessIf, 
         flWorkRoutingOspfLocalLsdbType, flWorkRoutingOspfLocalLsdbLsid, flWorkRoutingOspfLocalLsdbRouterId 
               }
        ::= { flWorkRoutingOspfLocalLsdbTable 1 }

   FlWorkRoutingOspfLocalLsdbEntry ::= 
        SEQUENCE {   
            flWorkRoutingOspfLocalLsdbIpAddress 
            IpAddress, 
            flWorkRoutingOspfLocalLsdbAddressLessIf 
              InterfaceIndexOrZero, 
            flWorkRoutingOspfLocalLsdbType 
              INTEGER, 
            flWorkRoutingOspfLocalLsdbLsid 
              IpAddress, 
            flWorkRoutingOspfLocalLsdbRouterId 
              RouterID, 
            flWorkRoutingOspfLocalLsdbSequence 
              Integer32, 
            flWorkRoutingOspfLocalLsdbAge 
              Integer32, 
            flWorkRoutingOspfLocalLsdbChecksum 
              Integer32, 
            flWorkRoutingOspfLocalLsdbAdvertisement 
              OCTET STRING 
            } 

    flWorkRoutingOspfLocalLsdbIpAddress OBJECT-TYPE 
         SYNTAX       IpAddress 
         MAX-ACCESS   read-only 
         STATUS       current 
         DESCRIPTION 
             "The IP Address of the interface from 
              which the LSA was received if the interface is 
              numbered." 
         REFERENCE 
             "OSPF Version 2, Appendix C.3 Interface parameters" 
         ::= { flWorkRoutingOspfLocalLsdbEntry 1 } 

    flWorkRoutingOspfLocalLsdbAddressLessIf OBJECT-TYPE 
         SYNTAX       InterfaceIndexOrZero 
         MAX-ACCESS   read-only 
         STATUS       current 
         DESCRIPTION 
             "The Interface Index of the interface from 
              which the LSA was received if the interface is 
              unnumbered." 
         REFERENCE 
             "OSPF Version 2, Appendix C.3 Interface parameters" 
         ::= { flWorkRoutingOspfLocalLsdbEntry 2 } 

    flWorkRoutingOspfLocalLsdbType OBJECT-TYPE 
         SYNTAX       INTEGER { localOpaqueLink (9) } 
         MAX-ACCESS   read-only 
         STATUS       current 
         DESCRIPTION 
             "The type of the link state advertisement. 
              Each link state type has a separate advertise- 
              ment format." 
         REFERENCE 
             "OSPF Version 2, Appendix A.4.1 The  Link  State 
              Advertisement header and " 
         ::= { flWorkRoutingOspfLocalLsdbEntry 3 } 

    flWorkRoutingOspfLocalLsdbLsid OBJECT-TYPE 
         SYNTAX       IpAddress 
         MAX-ACCESS   read-only
         STATUS       current 
         DESCRIPTION 
             "The Link State ID is an LS Type Specific field 
              containing a 32 bit identifier in IP address format; 
              it identifies the piece of the routing domain 
              that is being described by the advertisement." 
         REFERENCE 
             "OSPF Version 2, Section 12.1.4 Link State ID" 
         ::= { flWorkRoutingOspfLocalLsdbEntry 4 } 

    flWorkRoutingOspfLocalLsdbRouterId OBJECT-TYPE 
         SYNTAX       RouterID 
         MAX-ACCESS   read-only 
         STATUS       current 
         DESCRIPTION 
             "The 32 bit number that uniquely identifies the 
              originating router in the Autonomous System." 
         REFERENCE 
             "OSPF Version 2, Appendix C.1 Global parameters" 
         ::= { flWorkRoutingOspfLocalLsdbEntry 5 } 

    flWorkRoutingOspfLocalLsdbSequence OBJECT-TYPE 
         SYNTAX       Integer32 
         MAX-ACCESS   read-only 
         STATUS       current 
         DESCRIPTION 
             "The sequence number field is a signed 32-bit 
              integer. It starts with the value '80000001'h, 
              or -'7FFFFFFF'h, and increments until '7FFFFFFF'h. 
              Thus, a typical sequence number will be very negative. 
              It is used to detect old and duplicate link state 
              advertisements. The space of sequence numbers is linearly 
              ordered. The larger the sequence number the more recent 
              the advertisement." 
         REFERENCE 
             "OSPF Version 2, Section 12.1.6 LS sequence 
              number" 
         ::= { flWorkRoutingOspfLocalLsdbEntry 6 } 

    flWorkRoutingOspfLocalLsdbAge OBJECT-TYPE 
         SYNTAX       Integer32 -- Should be 0..MaxAge, except when 
         -- doNotAge bit is set 
         UNITS        "seconds" 
         MAX-ACCESS   read-only 
         STATUS       current 
         DESCRIPTION 
             "This field is the age of the link state adver- 
              tisement in seconds." 
         REFERENCE 
             "OSPF Version 2, Section 12.1.1 LS age" 
         ::= { flWorkRoutingOspfLocalLsdbEntry 7 }

    flWorkRoutingOspfLocalLsdbChecksum OBJECT-TYPE
         SYNTAX       Integer32 
         MAX-ACCESS   read-only 
         STATUS       current 
         DESCRIPTION 
             "This field is the checksum of the complete 
             contents of the advertisement, excepting the 
             age field. The age field is excepted so that 
             an advertisement's age can be incremented 
             without updating the checksum. The checksum 
             used is the same that is used for ISO connec- 
             tionless datagrams; it is commonly referred  to 
             as the Fletcher checksum." 
        REFERENCE 
            "OSPF Version 2, Section 12.1.7 LS checksum" 
        ::= { flWorkRoutingOspfLocalLsdbEntry 8 }

    flWorkRoutingOspfLocalLsdbAdvertisement OBJECT-TYPE 
         SYNTAX       OCTET STRING (SIZE (1..65535)) 
         MAX-ACCESS   read-only 
         STATUS       current 
         DESCRIPTION 
             "The entire Link State Advertisement, including 
             its header. 

             Note that for variable length LSAs, SNMP agents 
             may not be able to return the largest string size." 
         REFERENCE 
             "OSPF Version 2, Section 12 Link State Adver- 
              tisements" 
         ::= { flWorkRoutingOspfLocalLsdbEntry 9 }

         --  OSPF Link State Database, AS-scope 

    flWorkRoutingOspfAsLsdbTable OBJECT-TYPE 
         SYNTAX       SEQUENCE OF FlWorkRoutingOspfAsLsdbEntry 
         MAX-ACCESS   not-accessible 
         STATUS       current 
         DESCRIPTION 
             "The OSPF Process's AS-scope LSA Link State Database. 
             The Database contains the AS-scope Link State 
             Advertisements from throughout the areas that 
             the device is attached to. 

             This table is identical to the OSPF LSDB Table 
             in format, but contains only AS-scope Link State 
             Advertisements.  The purpose is to allow AS-scope 
             LSAs to be displayed once for the router rather 
             than once in each non-stub area." 
         REFERENCE 
             "OSPF Version 2, Section 12 Link State Adver- 
              tisements" 
         ::= { flWorkRoutingOspf 18 } 

    flWorkRoutingOspfAsLsdbEntry OBJECT-TYPE 
         SYNTAX       FlWorkRoutingOspfAsLsdbEntry 
         MAX-ACCESS   not-accessible 
         STATUS       current 
         DESCRIPTION 
             "A single Link State Advertisement." 
         INDEX { flWorkRoutingOspfAsLsdbType, flWorkRoutingOspfAsLsdbLsid, flWorkRoutingOspfAsLsdbRouterId } 
         ::= { flWorkRoutingOspfAsLsdbTable 1 } 

    FlWorkRoutingOspfAsLsdbEntry ::= 
         SEQUENCE { 
           flWorkRoutingOspfAsLsdbType 
             INTEGER, 
           flWorkRoutingOspfAsLsdbLsid 
             IpAddress, 
           flWorkRoutingOspfAsLsdbRouterId 
             RouterID, 
           flWorkRoutingOspfAsLsdbSequence 
             Integer32, 
           flWorkRoutingOspfAsLsdbAge 
             Integer32, 
           flWorkRoutingOspfAsLsdbChecksum 
             Integer32, 
           flWorkRoutingOspfAsLsdbAdvertisement 
             OCTET STRING 
         } 

    flWorkRoutingOspfAsLsdbType OBJECT-TYPE 
         SYNTAX      INTEGER { 
                         asOpaqueLink   (11) 
                       } 
         MAX-ACCESS   read-only 
         STATUS       current 
         DESCRIPTION 
             "The type of the link state advertisement. 
              Each link state type has a separate advertise- 
              ment format." 
         REFERENCE 
             "OSPF Version 2, Appendix A.4.1 The  Link  State 
              Advertisement header" 
         ::= { flWorkRoutingOspfAsLsdbEntry 1 } 

    flWorkRoutingOspfAsLsdbLsid OBJECT-TYPE 
         SYNTAX       IpAddress 
         MAX-ACCESS   read-only 
         STATUS       current 
         DESCRIPTION 
             "The Link State ID is an LS Type Specific field 
             containing either a Router ID or an IP Address; 
             it identifies the piece of the routing domain 
             that is being described by the advertisement." 
         REFERENCE 
             "OSPF Version 2, Section 12.1.4 Link State ID" 
         ::= { flWorkRoutingOspfAsLsdbEntry 2 } 

    flWorkRoutingOspfAsLsdbRouterId OBJECT-TYPE 
         SYNTAX       RouterID
         MAX-ACCESS   read-only
         STATUS       current 
         DESCRIPTION 
             "The 32 bit number that uniquely identifies the 
              originating router in the Autonomous System." 
         REFERENCE 
             "OSPF Version 2, Appendix C.1 Global parameters" 
         ::= { flWorkRoutingOspfAsLsdbEntry 3 } 

    flWorkRoutingOspfAsLsdbSequence OBJECT-TYPE 
         SYNTAX       Integer32 
         MAX-ACCESS   read-only 
         STATUS       current 
         DESCRIPTION 
             "The sequence number field is a signed 32-bit 
             integer. It starts with the value '80000001'h, 
             or -'7FFFFFFF'h, and increments until '7FFFFFFF'h. 
             Thus, a typical sequence number will be very negative. 
             It is used to detect old and duplicate link state 
             advertisements. The space of sequence numbers is linearly 
             ordered. The larger the sequence number the more recent 
             the advertisement." 
         REFERENCE 
             "OSPF Version  2,  Section  12.1.6  LS  sequence 
              number" 
         ::= { flWorkRoutingOspfAsLsdbEntry 4 } 

    flWorkRoutingOspfAsLsdbAge OBJECT-TYPE 
         SYNTAX       Integer32 -- Should be 0..MaxAge, except when 
         -- doNotAge bit is set 
         UNITS        "seconds" 
         MAX-ACCESS   read-only 
         STATUS       current 
         DESCRIPTION 
             "This field is the age of the link state adver- 
              tisement in seconds." 
         REFERENCE 
             "OSPF Version 2, Section 12.1.1 LS age" 
         ::= { flWorkRoutingOspfAsLsdbEntry 5 } 

    flWorkRoutingOspfAsLsdbChecksum OBJECT-TYPE 
         SYNTAX       Integer32 
         MAX-ACCESS   read-only 
         STATUS       current 
         DESCRIPTION 
             "This field is the checksum of the complete 
             contents of the advertisement, excepting the 
             age field. The age field is excepted so that 
             an advertisement's age can be incremented 
             without updating the checksum. The checksum 
             used is the same that is used for ISO connec- 
             tionless datagrams; it is commonly referred  to 
             as the Fletcher checksum." 
         REFERENCE 
             "OSPF Version 2, Section 12.1.7 LS checksum" 
         ::= { flWorkRoutingOspfAsLsdbEntry 6 }

    flWorkRoutingOspfAsLsdbAdvertisement OBJECT-TYPE 
         SYNTAX       OCTET STRING (SIZE (1..65535)) 
         MAX-ACCESS   read-only 
         STATUS       current 
         DESCRIPTION 
             "The entire Link State Advertisement, including 
              its header." 
         REFERENCE 
             "OSPF Version 2, Section 12  Link  State  Adver- 
              tisements. 
              Note that for variable length LSAs, SNMP agents 
              may not be able to return the largest string size." 
         ::= { flWorkRoutingOspfAsLsdbEntry 7 }

     flWorkRoutingOspfDefaultPassiveMode  OBJECT-TYPE
       SYNTAX      TruthValue
       MAX-ACCESS  read-write
       STATUS      current
       DESCRIPTION
               "Flag to determine, whether all the interfaces are passive interfaces
                by default. A passive interface will not participate in the OSPF
                adjacency formation."
       DEFVAL { false }
            ::= { flWorkRoutingOspf  19 }
         

   --**************************************************************************************
   -- flWorkRoutingLoopback
   --**************************************************************************************

    flWorkRoutingLoopbackTable OBJECT-TYPE
         SYNTAX      SEQUENCE OF FlWorkRoutingLoopbackEntry
         MAX-ACCESS  not-accessible
         STATUS      current
         DESCRIPTION
                     "A summary table of the Loopback instances"
         ::= { flWorkRoutingLoopback 1 }

    flWorkRoutingLoopbackEntry OBJECT-TYPE
         SYNTAX      FlWorkRoutingLoopbackEntry
         MAX-ACCESS  not-accessible
         STATUS      current
         DESCRIPTION
                     ""
         INDEX       { flWorkRoutingLoopbackID }
         ::= { flWorkRoutingLoopbackTable 1 }

    FlWorkRoutingLoopbackEntry ::= SEQUENCE {
                        flWorkRoutingLoopbackID
                           Integer32,
                        flWorkRoutingLoopbackIfIndex
                           Integer32,
                        flWorkRoutingLoopbackIPAddress
                           IpAddress,
                        flWorkRoutingLoopbackIPSubnet
                           IpAddress,
                        flWorkRoutingLoopbackStatus
                           RowStatus
           }

    flWorkRoutingLoopbackID      OBJECT-TYPE
         SYNTAX          Integer32 (1..255)
         MAX-ACCESS      not-accessible
         STATUS          current
         DESCRIPTION
                         "The  Loopback ID is associated with Internal Interface number
                         which will be generated when we create a loopback."
         ::= { flWorkRoutingLoopbackEntry 1 }

    flWorkRoutingLoopbackIfIndex OBJECT-TYPE
         SYNTAX          Integer32
         MAX-ACCESS      read-only
         STATUS          current
         DESCRIPTION
                         "This is external interface associated with inetrnal interface of loopback.
                          The  Loopback ID is associated with Internal Interface number
                         which will be generated when we create a loopback."
         ::= { flWorkRoutingLoopbackEntry 2 }

    flWorkRoutingLoopbackIPAddress OBJECT-TYPE
         SYNTAX            IpAddress
         MAX-ACCESS        read-write
         STATUS            current
         DESCRIPTION
                           "The IP Address configured for the respective loopback"
         ::= { flWorkRoutingLoopbackEntry 3 }

    flWorkRoutingLoopbackIPSubnet  OBJECT-TYPE
         SYNTAX            IpAddress
         MAX-ACCESS        read-write
         STATUS            current
         DESCRIPTION
                           "The Subnet mask configured for the respective loopback"
         ::= { flWorkRoutingLoopbackEntry 4 }

    flWorkRoutingLoopbackStatus OBJECT-TYPE
         SYNTAX         RowStatus
         MAX-ACCESS     read-create
         STATUS         current
         DESCRIPTION
                        "Status of this instance.  The rows can be added/deleted in the table by setting createAndGo/destroy respectively

                     active(1)      - this loopback instance is active
                     createAndGo(4) - set to this value to create an instance
                     destroy(6)     - set to this value to delete an instance"
         ::= { flWorkRoutingLoopbackEntry 5 }
 
   --**************************************************************************************
   -- flWorkRoutingNAT
   --**************************************************************************************

    flWorkRoutingNATIntfCtrl
        OBJECT IDENTIFIER ::= { flWorkRoutingNAT 1  }
        
    flWorkRoutingNATIntfForwarding
        OBJECT IDENTIFIER ::= { flWorkRoutingNAT 2  }

    flWorkRoutingNATIntf1to1
        OBJECT IDENTIFIER ::= { flWorkRoutingNAT 3  }

    flWorkRoutingNATIntfVirtual
        OBJECT IDENTIFIER ::= { flWorkRoutingNAT 4  }
    
    --
    -- flWorkRoutingNATIntfCtrl 
    --

    flWorkRoutingNATIntfCtrlTable
        OBJECT-TYPE
            SYNTAX      SEQUENCE OF FlWorkRoutingNATIntfCtrlEntry
            MAX-ACCESS  not-accessible
            STATUS      current
            DESCRIPTION
                "Contains a List of NAT Interface configuration parameters."
        ::= { flWorkRoutingNATIntfCtrl 1 }

    flWorkRoutingNATIntfCtrlEntry
        OBJECT-TYPE
            SYNTAX      FlWorkRoutingNATIntfCtrlEntry
            MAX-ACCESS  not-accessible
            STATUS      current
            DESCRIPTION
                "An entry in the table does contain information about NAT Interface control parameters."
            INDEX       { flWorkRoutingNATIntfCtrlIntfIndex }
        ::= { flWorkRoutingNATIntfCtrlTable 1 }


    FlWorkRoutingNATIntfCtrlEntry
        ::= SEQUENCE {
            flWorkRoutingNATIntfCtrlIntfIndex
                Integer32,
            flWorkRoutingNATIntfCtrlIntfMode
                INTEGER
        }

    flWorkRoutingNATIntfCtrlIntfIndex
        OBJECT-TYPE
            SYNTAX      Integer32 (1..16)
            MAX-ACCESS  read-only
            STATUS      current
            DESCRIPTION
                "Interface Index of this entry.
				"
        ::= { flWorkRoutingNATIntfCtrlEntry 1 }

    flWorkRoutingNATIntfCtrlIntfMode
        OBJECT-TYPE
            SYNTAX      INTEGER {
                            none(0),
                            oneToOne(1),
                            virtual(2),
                            masquerade(3)
                            }
            MAX-ACCESS  read-write
            STATUS      current
            DESCRIPTION
                "NAT Mode of this Interface.
				"
        ::= { flWorkRoutingNATIntfCtrlEntry 2 }


    --
    -- flWorkRoutingNATIntfForwarding 
    --
    
    flWorkRoutingNATIntfForwardingTable
        OBJECT-TYPE
            SYNTAX      SEQUENCE OF FlWorkRoutingNATIntfForwardingEntry
            MAX-ACCESS  not-accessible
            STATUS      current
            DESCRIPTION
                "Contains a List of Interface Port Forwarding rules."
        ::= { flWorkRoutingNATIntfForwarding 1 }

    flWorkRoutingNATIntfForwardingEntry
        OBJECT-TYPE
            SYNTAX      FlWorkRoutingNATIntfForwardingEntry
            MAX-ACCESS  not-accessible
            STATUS      current
            DESCRIPTION
                "An entry in the table does contain information about Interface Port Forwarding rules."
            INDEX       { flWorkRoutingNATIntfForwardingIntfIndex,
                          flWorkRoutingNATIntfForwardingTableIndex }

        ::= { flWorkRoutingNATIntfForwardingTable 1 }


    FlWorkRoutingNATIntfForwardingEntry
        ::= SEQUENCE {
            flWorkRoutingNATIntfForwardingIntfIndex
                Integer32,
            flWorkRoutingNATIntfForwardingTableIndex
                Integer32,
            flWorkRoutingNATIntfForwardingTableProtocol
                INTEGER,
            flWorkRoutingNATIntfForwardingTableDirection
                INTEGER,
            flWorkRoutingNATIntfForwardingTableInboundAddr
                IpAddress,
            flWorkRoutingNATIntfForwardingTableInboundPort
                Integer32,
            flWorkRoutingNATIntfForwardingTableOutboundAddr
                IpAddress,	
            flWorkRoutingNATIntfForwardingTableOutboundPort
                Integer32,		
            flWorkRoutingNATIntfForwardingTableActive
                INTEGER,
            flWorkRoutingNATIntfForwardingTableStatus
                RowStatus
        }

    flWorkRoutingNATIntfForwardingIntfIndex
        OBJECT-TYPE
            SYNTAX      Integer32 (1..16)
            MAX-ACCESS  read-only
            STATUS      current
            DESCRIPTION
                "Interface Index of this entry.
				"
        ::= { flWorkRoutingNATIntfForwardingEntry 1 }

    flWorkRoutingNATIntfForwardingTableIndex
        OBJECT-TYPE
            SYNTAX      Integer32 (1..128)
            MAX-ACCESS  read-only
            STATUS      current
            DESCRIPTION
                "Table Index of this entry.
				"
        ::= { flWorkRoutingNATIntfForwardingEntry 2 }

    flWorkRoutingNATIntfForwardingTableProtocol
        OBJECT-TYPE
            SYNTAX      INTEGER {tcp(1), udp(2), both(3) }
            MAX-ACCESS  read-write
            STATUS      current
            DESCRIPTION
                "Protocol of the connection to forward."
        ::= { flWorkRoutingNATIntfForwardingEntry 3 }

    flWorkRoutingNATIntfForwardingTableDirection
        OBJECT-TYPE
            SYNTAX      INTEGER {source(1), destination(2) }
            MAX-ACCESS  read-write
            STATUS      current
            DESCRIPTION
                "direction for the Forwarding rule."
        ::= { flWorkRoutingNATIntfForwardingEntry 4 }

    flWorkRoutingNATIntfForwardingTableInboundAddr
        OBJECT-TYPE
            SYNTAX      IpAddress
            MAX-ACCESS  read-write
            STATUS      current
            DESCRIPTION
                "Inbound IP Address."
        ::= { flWorkRoutingNATIntfForwardingEntry 5 }

    flWorkRoutingNATIntfForwardingTableInboundPort
        OBJECT-TYPE
            SYNTAX      Integer32
            MAX-ACCESS  read-write
            STATUS      current
            DESCRIPTION
                "Inbound Port Number."
        ::= { flWorkRoutingNATIntfForwardingEntry 6 }
  
    flWorkRoutingNATIntfForwardingTableOutboundAddr
        OBJECT-TYPE
            SYNTAX      IpAddress
            MAX-ACCESS  read-write
            STATUS      current
            DESCRIPTION
                "Outbound IP Address."
        ::= { flWorkRoutingNATIntfForwardingEntry 7 }
		
    flWorkRoutingNATIntfForwardingTableOutboundPort
        OBJECT-TYPE
            SYNTAX      Integer32
            MAX-ACCESS  read-write
            STATUS      current
            DESCRIPTION
                "Outbound Port Number."
        ::= { flWorkRoutingNATIntfForwardingEntry 8 }
	
    flWorkRoutingNATIntfForwardingTableActive
        OBJECT-TYPE
            SYNTAX      INTEGER {disable(1), enable(2) }
            MAX-ACCESS  read-write
            STATUS      current
            DESCRIPTION
                "This object shows the status of this forwarding entry."
        ::= { flWorkRoutingNATIntfForwardingEntry 9 }	
			
    flWorkRoutingNATIntfForwardingTableStatus OBJECT-TYPE
         SYNTAX      RowStatus
         MAX-ACCESS  read-create
         STATUS      current
         DESCRIPTION
                     "Status of NAT Forwarding Table entry.
                     active(1)       - NAT Forwarding Table entry is present
                     createAndGo(4)  - Adds NAT Forwarding entry
                     destroy(6)      - Removes NAT Forwarding entry"
         ::= { flWorkRoutingNATIntfForwardingEntry 10 }
    
    flWorkRoutingNATIntf1to1Table
        OBJECT-TYPE
            SYNTAX      SEQUENCE OF FlWorkRoutingNATIntf1to1Entry
            MAX-ACCESS  not-accessible
            STATUS      current
            DESCRIPTION
                "Contains a List of Interface 1:1 NAT rules."
        ::= { flWorkRoutingNATIntf1to1 1 }

    flWorkRoutingNATIntf1to1Entry
        OBJECT-TYPE
            SYNTAX      FlWorkRoutingNATIntf1to1Entry
            MAX-ACCESS  not-accessible
            STATUS      current
            DESCRIPTION
                "An entry in the table does contain information about 1:1 NAT rules."
            INDEX       { flWorkRoutingNATIntf1to1IntfIndex,
                          flWorkRoutingNATIntf1to1TableIndex }
        ::= { flWorkRoutingNATIntf1to1Table 1 }


    FlWorkRoutingNATIntf1to1Entry
        ::= SEQUENCE {
            flWorkRoutingNATIntf1to1IntfIndex
                Integer32,
            flWorkRoutingNATIntf1to1TableIndex
                Integer32,
            flWorkRoutingNATIntf1to1TableExternalNetwork
                IpAddress,
            flWorkRoutingNATIntf1to1TableInternalNetwork
                IpAddress,
            flWorkRoutingNATIntf1to1TableRange
                Integer32,
            flWorkRoutingNATIntf1to1TableActive
                INTEGER,
            flWorkRoutingNATIntf1to1TableStatus
                RowStatus
        }

    flWorkRoutingNATIntf1to1IntfIndex
        OBJECT-TYPE
            SYNTAX      Integer32 (1..16)
            MAX-ACCESS  read-only
            STATUS      current
            DESCRIPTION
                "Interface Index of this entry."
        ::= { flWorkRoutingNATIntf1to1Entry 1 }

    flWorkRoutingNATIntf1to1TableIndex
        OBJECT-TYPE
            SYNTAX      Integer32 (1..64)
            MAX-ACCESS  read-only
            STATUS      current
            DESCRIPTION
                "Table Index of this entry."
        ::= { flWorkRoutingNATIntf1to1Entry 2 }

    flWorkRoutingNATIntf1to1TableExternalNetwork
        OBJECT-TYPE
            SYNTAX      IpAddress
            MAX-ACCESS  read-write
            STATUS      current
            DESCRIPTION
                "IP Address of the external Network or Device Address."
        ::= { flWorkRoutingNATIntf1to1Entry 3 }

    flWorkRoutingNATIntf1to1TableInternalNetwork
        OBJECT-TYPE
            SYNTAX      IpAddress
            MAX-ACCESS  read-write
            STATUS      current
            DESCRIPTION
                "IP Address of the internal Network or Device Address."
        ::= { flWorkRoutingNATIntf1to1Entry 4 }
  
    flWorkRoutingNATIntf1to1TableRange
        OBJECT-TYPE
            SYNTAX      Integer32 (0..32)
            MAX-ACCESS  read-write
            STATUS      current
            DESCRIPTION
                "Subnet Bits of the network. 
				 
				 Examples: 
				 Class C Network:
				   255.255.255.0 ->24
				 Class B Network:  
				   255.255.0.0 ->16
				 Class A Network:  
				   255.0.0.0 ->8
				 
                 Single Device: ->32
                 "
        ::= { flWorkRoutingNATIntf1to1Entry 5 }
		
	flWorkRoutingNATIntf1to1TableActive
        OBJECT-TYPE
            SYNTAX      INTEGER {disable(1), enable(2) }
            MAX-ACCESS  read-write
            STATUS      current
            DESCRIPTION
                "This object shows the status of this 1:1 Nat entry.
				"
        ::= { flWorkRoutingNATIntf1to1Entry 6 }
		    	
    flWorkRoutingNATIntf1to1TableStatus OBJECT-TYPE
         SYNTAX      RowStatus
         MAX-ACCESS  read-create
         STATUS      current
         DESCRIPTION
                     "Status of NAT 1-to-1 Table entry.
                     active(1)       - NAT 1-to-1 Table entry is present
                     createAndGo(4)  - Adds NAT 1-to-1 entry
                     destroy(6)      - Removes NAT 1-to-1 entry"
         ::= { flWorkRoutingNATIntf1to1Entry 7 }

    flWorkRoutingNATIntfVirtualTable
        OBJECT-TYPE
            SYNTAX      SEQUENCE OF FlWorkRoutingNATIntfVirtualEntry
            MAX-ACCESS  not-accessible
            STATUS      current
            DESCRIPTION
                "Contains a List of Interface Virtual NAT rules."
        ::= { flWorkRoutingNATIntfVirtual 1 }

    flWorkRoutingNATIntfVirtualEntry
        OBJECT-TYPE
            SYNTAX      FlWorkRoutingNATIntfVirtualEntry
            MAX-ACCESS  not-accessible
            STATUS      current
            DESCRIPTION
                "An entry in the table does contain information about Virtual NAT rules."
            INDEX       { flWorkRoutingNATIntfVirtualIntfIndex,
                          flWorkRoutingNATIntfVirtualTableIndex }
        ::= { flWorkRoutingNATIntfVirtualTable 1 }


    FlWorkRoutingNATIntfVirtualEntry
        ::= SEQUENCE {
            flWorkRoutingNATIntfVirtualIntfIndex
                Integer32,
            flWorkRoutingNATIntfVirtualTableIndex
                Integer32,
            flWorkRoutingNATIntfVirtualTableVirtualNetwork
                IpAddress,
            flWorkRoutingNATIntfVirtualTableInternalNetwork
                IpAddress,
            flWorkRoutingNATIntfVirtualTableRange
                Integer32
        }

    flWorkRoutingNATIntfVirtualIntfIndex
        OBJECT-TYPE
            SYNTAX      Integer32 (1..16)
            MAX-ACCESS  read-only
            STATUS      current
            DESCRIPTION
                "Interface Index of this entry."
        ::= { flWorkRoutingNATIntfVirtualEntry 1 }

    flWorkRoutingNATIntfVirtualTableIndex
        OBJECT-TYPE
            SYNTAX      Integer32 (1..64)
            MAX-ACCESS  read-only
            STATUS      current
            DESCRIPTION
                "Table Index of this entry."
        ::= { flWorkRoutingNATIntfVirtualEntry 2 }

    flWorkRoutingNATIntfVirtualTableVirtualNetwork
        OBJECT-TYPE
            SYNTAX      IpAddress
            MAX-ACCESS  read-write
            STATUS      current
            DESCRIPTION
                "Start IP Address of the Virtual Network."
        ::= { flWorkRoutingNATIntfVirtualEntry 3 }

    flWorkRoutingNATIntfVirtualTableInternalNetwork
        OBJECT-TYPE
            SYNTAX      IpAddress
            MAX-ACCESS  read-write
            STATUS      current
            DESCRIPTION
                "Start IP Address of the Internal Network."
        ::= { flWorkRoutingNATIntfVirtualEntry 4 }
  
    flWorkRoutingNATIntfVirtualTableRange
        OBJECT-TYPE
            SYNTAX      Integer32 (0..32)
            MAX-ACCESS  read-write
            STATUS      current
            DESCRIPTION
                "Subnet Bits of the network. 
				 
				 Examples: 
				 Class C Network:
				   255.255.255.0 ->24
				 Class B Network:  
				   255.255.0.0 ->16
				 Class A Network:  
				   255.0.0.0 ->8
				 
                 Single Device: ->32
				"
        ::= { flWorkRoutingNATIntfVirtualEntry 5 }
		

    --**************************************************************************************
   -- flWorkCIP
   --**************************************************************************************

   flWorkCipActiveIOConns OBJECT-TYPE
     SYNTAX      Integer32
     MAX-ACCESS  read-only
     STATUS      current
     DESCRIPTION
                "Gets the number of currently active CIP I/O Connections."
         ::= { flWorkCipInfo 1 }

   flWorkCipActiveExpMsgConns OBJECT-TYPE
     SYNTAX      Integer32
     MAX-ACCESS  read-only
     STATUS      current
     DESCRIPTION
                "Gets the number of currently active CIP Explicit Message Connections."
         ::= { flWorkCipInfo 2 }

   flWorkCipActiveMcastGroups OBJECT-TYPE
     SYNTAX      Integer32
     MAX-ACCESS  read-only
     STATUS      current
     DESCRIPTION
                "Gets the number of currently active multicast groups."
         ::= { flWorkCipInfo 3 }

   flWorkCipOpenRequestsRcvd OBJECT-TYPE
     SYNTAX      Integer32
     MAX-ACCESS  read-only
     STATUS      current
     DESCRIPTION
                "Gets the number of open connection requests received after device startup."
         ::= { flWorkCipInfo 4 }

   flWorkCipOpenResourceRejects OBJECT-TYPE
     SYNTAX      Integer32
     MAX-ACCESS  read-only
     STATUS      current
     DESCRIPTION
                "Gets the number of open connection requests rejected due to lack of resource."
         ::= { flWorkCipInfo 5 }

   flWorkCipOpenFormatRejects OBJECT-TYPE
     SYNTAX      Integer32
     MAX-ACCESS  read-only
     STATUS      current
     DESCRIPTION
                "Gets the number of open connection requests rejected due to bad format."
         ::= { flWorkCipInfo 6 }
  

   flWorkCipOpenOtherRejects OBJECT-TYPE
     SYNTAX      Integer32
     MAX-ACCESS  read-only
     STATUS      current
     DESCRIPTION
                "Gets the number of open connection requests rejected due to other reasons."
         ::= { flWorkCipInfo 7 }
 
   flWorkCipCloseRequests OBJECT-TYPE
     SYNTAX      Integer32
     MAX-ACCESS  read-only
     STATUS      current
     DESCRIPTION
                "Gets the number of close connection requests received after device startup."
         ::= { flWorkCipInfo 8 }

   flWorkCipCloseFormatRejects OBJECT-TYPE
     SYNTAX      Integer32
     MAX-ACCESS  read-only
     STATUS      current
     DESCRIPTION
                "Gets the number of close connection requests rejected due to bad format."
         ::= { flWorkCipInfo 9 }
  

   flWorkCipCloseOtherRejects OBJECT-TYPE
     SYNTAX      Integer32
     MAX-ACCESS  read-only
     STATUS      current
     DESCRIPTION
                "Gets the number of close connection requests rejected due to other reasons."
         ::= { flWorkCipInfo 10 }

   flWorkCipConnectionTimeouts OBJECT-TYPE
     SYNTAX      Integer32
     MAX-ACCESS  read-only
     STATUS      current
     DESCRIPTION
                "Gets the number of connection timeouts happened after device startup."
         ::= { flWorkCipInfo 11 }

   flWorkCipNetworkStatus OBJECT-TYPE
     SYNTAX      Integer32
     MAX-ACCESS  read-only
     STATUS      current
     DESCRIPTION
                "Describes network status."
         ::= { flWorkCipInfo 12 }

   flWorkCipModuleStatus OBJECT-TYPE
     SYNTAX      Integer32
     MAX-ACCESS  read-only
     STATUS      current
     DESCRIPTION
                "Describes Module status."
         ::= { flWorkCipInfo 13 }

   flWorkCipClearStats OBJECT-TYPE
        SYNTAX INTEGER {
               noClear(1),               
               clear(2)
	       }	
     MAX-ACCESS  read-write
     STATUS      current
     DESCRIPTION
                "Clears the following CIP Connection manager statistics
		 - flWorkCipOpenRequestsRcvd
		 - flWorkCipOpenResourceRejects
		 - flWorkCipOpenFormatRejects
		 - flWorkCipOpenOtherRejects
		 - flWorkCipCloseRequests
		 - flWorkCipCloseFormatRejects
		 - flWorkCipCloseOtherRejects
		 - flWorkCipConnectionTimeouts"
         ::= { flWorkCipInfo 14 }
    

     --**********************************************************************
     -- flWorkCipConnectionTable
     --**********************************************************************
 
   flWorkCipConnectionTable OBJECT-TYPE
       SYNTAX      SEQUENCE OF FlWorkCipConnectionEntry
       MAX-ACCESS   not-accessible
       STATUS       current
       DESCRIPTION
           "List current CIP connections where each entry consists of a
            'flWorkCipConnectionEntry' items."
       ::= { flWorkCip 2 }
   
  flWorkCipConnectionEntry OBJECT-TYPE
       SYNTAX FlWorkCipConnectionEntry
       MAX-ACCESS   not-accessible 
       STATUS       current
       DESCRIPTION 
           "Each entry in this table consists of details about current CIP Connections."
       INDEX    { flWorkCipConnectionID }
       ::= { flWorkCipConnectionTable 1 }

  FlWorkCipConnectionEntry ::=
      SEQUENCE {
			 flWorkCipConnectionID  
              Integer32,
          flWorkCipConnectionOwnerIP
              IpAddress,
          flWorkCipConnectionTransportClass
              INTEGER
          }
        
  flWorkCipConnectionID OBJECT-TYPE
      SYNTAX       Integer32 (1..255)
      MAX-ACCESS   read-only
      STATUS       current
      DESCRIPTION
          "This object specifies the sessionID of the connection."
      ::= { flWorkCipConnectionEntry 1 }

  flWorkCipConnectionOwnerIP OBJECT-TYPE
      SYNTAX       IpAddress
      MAX-ACCESS   read-only
      STATUS       current
      DESCRIPTION
          "This object specifies the originator IP address of the connection."
      ::= { flWorkCipConnectionEntry 2 }

  flWorkCipConnectionTransportClass OBJECT-TYPE
        SYNTAX INTEGER {
               class1(1),               
	       class3(3)
	       }	
      MAX-ACCESS   read-only
      STATUS       current
      DESCRIPTION
          "This object specifies the connection class 
		Class 1 - I/O Connection
		Class 3 - Explicit Connection."
      ::= { flWorkCipConnectionEntry 3 }
	  
	--**********************************************************************
	-- flWlan
	--**********************************************************************
	flWlanRadio
		OBJECT IDENTIFIER ::= { flWlan 1 }
	
	flWlanWifi
		OBJECT IDENTIFIER ::= { flWlan 2 }
   
	flWlanApplySettings OBJECT-TYPE
        SYNTAX		INTEGER {
					disable(1),
					enable(2)
        }
        MAX-ACCESS read-write
        STATUS		current
        DESCRIPTION
			"Enable applies changes in the configuration.
			Note:
			Without enabling this command changes in the configuration are not active"
        DEFVAL  	{disable}
        ::= { flWlan 3 }
		
	flWlanSettingsApplyState OBJECT-TYPE
        SYNTAX		INTEGER{
						ok (0),
						newSettingsNeedToBeApplied (1),
						inProgress (2),
						error (3)
		}
        MAX-ACCESS 	read-only
        STATUS		current
        DESCRIPTION
			"Get last wlan apply state. After configuration the changes must be applied by flWlanApplySettings."
        ::= { flWlan 4 }
		
	flWlanManagementAccess OBJECT-TYPE
        SYNTAX		INTEGER {
					disable(1),
					enable(2)
        }
        MAX-ACCESS 	read-write
        STATUS		current
        DESCRIPTION
			"Configure if access to the management interface via wlan is enabled or not"
        DEFVAL  	{disable}
        ::= { flWlan 5 }
	 
	flWlanPtcpLldpFilter OBJECT-TYPE
        SYNTAX		INTEGER {
					disable(1),
					enable(2)
        }
        MAX-ACCESS 	read-write
        STATUS		current
        DESCRIPTION
			"Configure wlan global mode for PTCP/LLDP filter"
        DEFVAL  	{disable}
        ::= { flWlan 6 }
		
	flWlanCountry OBJECT-TYPE
        SYNTAX		DisplayString
        MAX-ACCESS 	read-write
        STATUS		current
        DESCRIPTION
			"Configure country domain as string value (e.g. Germany)"
        ::= { flWlan 7 }
		
	--**********************************************************************
	-- flWlanCountryTable
	--**********************************************************************	
	flWlanCountryTable OBJECT-TYPE
		SYNTAX    	SEQUENCE OF FlWlanCountryEntry
		MAX-ACCESS 	not-accessible
		STATUS     	current
		DESCRIPTION
			"Display available country settings"
		::= { flWlan 8 }
	   
	flWlanCountryEntry OBJECT-TYPE
		SYNTAX		FlWlanCountryEntry
		MAX-ACCESS 	not-accessible 
		STATUS     	current
		DESCRIPTION 
			"Each entry in this table represents an available country."
		INDEX		{ flWlanCountryID }
		::= { flWlanCountryTable 1 }
	   
	FlWlanCountryEntry ::=
		SEQUENCE {
			flWlanCountryID  
				INTEGER,
			flWlanCountryName
				DisplayString
          }
		  
	flWlanCountryID OBJECT-TYPE
		SYNTAX     	INTEGER (1..255)
		MAX-ACCESS 	read-only
		STATUS     	current
		DESCRIPTION
			"Each country ID is the identification number of a available country."
		::= { flWlanCountryEntry 1 }
	
	flWlanCountryName OBJECT-TYPE
		SYNTAX     	DisplayString
		MAX-ACCESS 	read-only
		STATUS     	current
		DESCRIPTION
			"Name of the available countries."
		::= { flWlanCountryEntry 2 }
		
	--**********************************************************************
		
	flWlanOutdoorMode OBJECT-TYPE
        SYNTAX		INTEGER {
					disable(1),
					enable(2)
        }
        MAX-ACCESS 	read-write
        STATUS		current
        DESCRIPTION
			"Configure wlan global mode for outdoor operation"
        DEFVAL  	{disable}
        ::= { flWlan 9 }
		
	flWlanGlobalActivation OBJECT-TYPE
        SYNTAX		INTEGER {
					disable(1),
					enable(2)
        }
        MAX-ACCESS 	read-write
        STATUS		current
        DESCRIPTION
			"Configure wlan global mode."
        DEFVAL  	{disable}
        ::= { flWlan 10 }
		
	flWlanCyclicRssiTracking OBJECT-TYPE
        SYNTAX		INTEGER {
					disable(1),
					enable(2)
        }
        MAX-ACCESS 	read-write
        STATUS		current
        DESCRIPTION
			"Cyclic generation of connection information in wlan client mode. Deactivate to reduce cpu load.
			Output via syslog: configure server, activate message group Diagnosis."
        DEFVAL  	{disable}
        ::= { flWlan 11 }
		
	--**********************************************************************
	-- flWlanRadio
	--**********************************************************************
	 
	--**********************************************************************
	-- flWlanRadioHwTable
	--**********************************************************************
 
	flWlanRadioHwTable OBJECT-TYPE
		SYNTAX    	SEQUENCE OF FlWlanRadioHwEntry
		MAX-ACCESS 	not-accessible
		STATUS     	current
		DESCRIPTION
			"Wlan hardware table"
		::= { flWlanRadio 1 }
	   
	flWlanRadioHwEntry OBJECT-TYPE
		SYNTAX		FlWlanRadioHwEntry
		MAX-ACCESS 	not-accessible 
		STATUS     	current
		DESCRIPTION 
			"Each entry in this table represents a wlan hardware instance"
		INDEX		{ flWlanRadioHwID }
		::= { flWlanRadioHwTable 1 }
	   
	FlWlanRadioHwEntry ::=
		SEQUENCE {
			flWlanRadioHwID  
				INTEGER,
			flWlanRadioHwAntMask
				OCTET STRING,
			flWlanRadioHwAggMode
				INTEGER
          }
		  
	flWlanRadioHwID OBJECT-TYPE
		SYNTAX     	INTEGER (1..255)
		MAX-ACCESS 	read-only
		STATUS     	current
		DESCRIPTION
			"Each HwID is the identification number of a wlan hardware instance {1, 2, ...}"
		::= { flWlanRadioHwEntry 1 }

	flWlanRadioHwAntMask OBJECT-TYPE
		SYNTAX     	OCTET STRING
		MAX-ACCESS 	read-write
		STATUS     	current
		DESCRIPTION
			"Configure the used antenna of a specific wlan radio hardware
			(1) enables antenna port 1
			(2) enables antenna port 2 
			(3) enables antenna port 1 AND port 2"
		::= { flWlanRadioHwEntry 2 }
	  
	flWlanRadioHwAggMode OBJECT-TYPE
		SYNTAX		INTEGER {
					disable(1),
					enable(2)
		}
		MAX-ACCESS	read-write
		STATUS    	current
		DESCRIPTION
			"Configure wlan aggregation for a specific wlan radio hardware instance"
        DEFVAL  	{disable}
		::= { flWlanRadioHwEntry 3 }
				 
	--**********************************************************************
	
	--**********************************************************************
    -- flWlanWifi
    --**********************************************************************
	 
	flWlanWifiVapTable OBJECT-TYPE
		SYNTAX    	SEQUENCE OF FlWlanWifiVapEntry
		MAX-ACCESS 	not-accessible
		STATUS     	current
		DESCRIPTION
			"Virtual access point table"
		::= { flWlanWifi 1 }
	   
	flWlanWifiVapEntry OBJECT-TYPE
		SYNTAX		FlWlanWifiVapEntry
		MAX-ACCESS 	not-accessible 
		STATUS     	current
		DESCRIPTION 
			"Each entry in this table represents a virtual access point instance"
		INDEX		{ flWlanWifiVapID }
		::= { flWlanWifiVapTable 1 }
	   
	FlWlanWifiVapEntry ::=
		SEQUENCE {
			flWlanWifiVapID  
				INTEGER,
			flWlanWifiVapFastEapolRetry
				INTEGER,
			flWlanWifiVapHideSsid
				INTEGER,
			flWlanWifiVapExcessiveRetries
				INTEGER,
			flWlanWifiVapWdsBroadcast
				INTEGER,
			flWlanWifiVapWdsAgingTime
				Integer32,
			flWlanWifiVapEnableState
				INTEGER,
			flWlanWifiVapChScanlist
				DisplayString,
			flWlanWifiVapMaxNumClients
				INTEGER,
			flWlanWifiVapStartScanning
				INTEGER,
			flWlanWifiVapNetworkId
				INTEGER,
			flWlanWifiVapManRoaming
				DisplayString,
			flWlanWifiVapBgScanIdle
				INTEGER,
			flWlanWifiVapRssiThrshForceScan
				INTEGER,
			flWlanWifiVapRssiChangeRoam
				INTEGER,
			flWlanWifiVapRssiChangeBgScan
				INTEGER,
			flWlanWifiVapRssiThrshBgScan
				INTEGER,
			flWlanWifiVapScbManMac
				DisplayString,
			flWlanWifiVapScbMode
				INTEGER,
			flWlanWifiVapFragThreshold
				Integer32,
			flWlanWifiVapTxPowerRadiated
				INTEGER,
			flWlanWifiVapCurrentTxPowerRadiated
				INTEGER,
			flWlanWifiVapChBandwidth
				INTEGER,
			flWlanWifiVapWlanCh
				INTEGER,
			flWlanWifiVap80211Mode
				INTEGER,
			flWlanWifiVapHwID
				INTEGER,
			flWlanWifiVapOpMode
				INTEGER,
			flWlanWifiVapStatus
				INTEGER,			
			flWlanWifiVapActiveProfile
				INTEGER,
			flWlanWifiVapRowStatus
				RowStatus
          }
	
	flWlanWifiVapID OBJECT-TYPE
		SYNTAX     	INTEGER (1..255)
		MAX-ACCESS 	read-only
		STATUS     	current
		DESCRIPTION
			"Each VapID is the identification number of a virtual accesspoint instance {101, 102, ...}"
		::= { flWlanWifiVapEntry 1 }
		  
	flWlanWifiVapFastEapolRetry OBJECT-TYPE
		SYNTAX		INTEGER {
					disable(1),
					enable(2)
		}
		MAX-ACCESS	read-write
		STATUS    	current
		DESCRIPTION
			"Configure the fast eapol retry mode.
			Just available in access point mode."
		DEFVAL  	{enable}
		::= { flWlanWifiVapEntry 2 }
		
	flWlanWifiVapHideSsid OBJECT-TYPE
		SYNTAX		INTEGER {
					disable(1),
					enable(2)
		}
		MAX-ACCESS	read-write
		STATUS    	current
		DESCRIPTION
			"Configure the hide ssid mode.
			Default: disable (meaning the ssid is broadcasted via beacon frames)"
		DEFVAL  	{disable}		
		::= { flWlanWifiVapEntry 3 }
		
	flWlanWifiVapExcessiveRetries OBJECT-TYPE
		SYNTAX		INTEGER (0..100)
		MAX-ACCESS	read-write
		STATUS    	current
		DESCRIPTION
			"Configure the number of max. consecutive excessive retries before drop of connection."
		::= { flWlanWifiVapEntry 4 }
		
	flWlanWifiVapWdsBroadcast OBJECT-TYPE
		SYNTAX		INTEGER {
					disable(1),
					enable(2)
		}
		MAX-ACCESS	read-write
		STATUS    	current
		DESCRIPTION
			"Broadcast frames with unknown unicast destination to all ftb devices."
		DEFVAL  	{disable}
		::= { flWlanWifiVapEntry 5 }
		
	flWlanWifiVapWdsAgingTime OBJECT-TYPE
		SYNTAX		Integer32 (60..4294967)
		MAX-ACCESS	read-write
		STATUS    	current
		DESCRIPTION
			"The aging time in seconds for addresses learned from behind FTB devices can be configured.
			Min Value: 60 seconds
			Max Value: 4294967 seconds
			Note: This option is only relevant for devices operating in FTB client mode."
		DEFVAL  	{60}
		::= { flWlanWifiVapEntry 6 }
		
	flWlanWifiVapEnableState OBJECT-TYPE
		SYNTAX		INTEGER {
					disable(1),
					enable(2)
		}
		MAX-ACCESS	read-write
		STATUS    	current
		DESCRIPTION
			"Configure the vap wlan enable / disable state."
		DEFVAL  	{disable}
		::= { flWlanWifiVapEntry 7 }
		
	flWlanWifiVapChScanlist OBJECT-TYPE
		SYNTAX		DisplayString 
		MAX-ACCESS	read-write
		STATUS    	current
		DESCRIPTION
			"Configures the channel scan list.
			all(all channels),
			1(channel-1),
			2(channel-2),
			3(channel-3),
			4(channel-4),
			5(channel-5),
			6(channel-6),
			7(channel-7),
			8(channel-8),
			9(channel-9),
			10(channel-10),
			11(channel-11),
			12(channel-12),
			13(channel-13),
			14(channel-14),
			36(channel-36),
			40(channel-40),
			44(channel-44),
			48(channel-48),
			52(channel-52),
			56(channel-56),
			60(channel-60),
			64(channel-64),
			132(channel-132),
			136(channel-136),
			140(channel-140),
			149(channel-149),
			153(channel-153),
			157(channel-157),
			161(channel-161),
			165(channel-165)"
		::= { flWlanWifiVapEntry 8 }
		
	flWlanWifiVapMaxNumClients OBJECT-TYPE
		SYNTAX		INTEGER (0..60)
		MAX-ACCESS	read-write
		STATUS    	current
		DESCRIPTION
			"Configures the maximal number of connectable clients."
		::= { flWlanWifiVapEntry 9 }
		
	flWlanWifiVapStartScanning OBJECT-TYPE
		SYNTAX		INTEGER {
					disable(1),
					enable(2)
		}
		MAX-ACCESS	read-write
		STATUS    	current
		DESCRIPTION
			"Starts a scan process"
		DEFVAL  	{disable}
		::= { flWlanWifiVapEntry 10 }
		
	flWlanWifiVapNetworkId OBJECT-TYPE
		SYNTAX		INTEGER
		MAX-ACCESS	read-write
		STATUS    	current
		DESCRIPTION
			"Configure the Layer 3 instance the wifi device will be added to."
		::= { flWlanWifiVapEntry 11 }
	
	flWlanWifiVapManRoaming OBJECT-TYPE
		SYNTAX		DisplayString
		MAX-ACCESS	read-write
		STATUS    	current
		DESCRIPTION
			"Format:
				{normal 00:00:00:00:00:00}
				{bssid xx:xx:xx:xx:xx:xx}
				
			Examples: 
			1) Start a common scan process based on the best accesspoint using
			   the current configured ssid: {normal 00:00:00:00:00:00} 
			   
			2a) Leave the normal scan method and trigger a roaming process
			    to a specific accesspoint with the given BSSID: {bssid 00:a0:45:11:22:33}
				
			2b) To disable the bssid roaming mode (2a) and return back to normal scan method,
			    the following input is requiered: {bssid 00:00:00:00:00:00}
				
			This object is just writable.
			And it is only writable in client mode when a connection to an access point exists."
		::= { flWlanWifiVapEntry 12 }
		
	flWlanWifiVapBgScanIdle OBJECT-TYPE
		SYNTAX		INTEGER (1..5000)
		MAX-ACCESS	read-write
		STATUS    	current
		DESCRIPTION
			"Configure the roaming parameter for the wifi device.
			Network idle time in milliseconds (ms)."
		::= { flWlanWifiVapEntry 13 }
		
	flWlanWifiVapRssiThrshForceScan OBJECT-TYPE
		SYNTAX		INTEGER (-94.. -1)
		MAX-ACCESS	read-write
		STATUS    	current
		DESCRIPTION
			"Configure the roaming parameter for the wifi device.
			Forced scan threshold in dBm.
			RSSI value below which the device starts a forced scan
			(without respecting the network traffic)."
		DEFVAL  	{-90}
		::= { flWlanWifiVapEntry 14 }
		
	flWlanWifiVapRssiChangeRoam OBJECT-TYPE
		SYNTAX		INTEGER (1..94)
		MAX-ACCESS	read-write
		STATUS    	current
		DESCRIPTION
			"Configure the roaming parameter for the wifi device.
			Roaming threshold in dBm.
			Difference in RSSI values for current AP and new AP before
			considering a roaming to the new AP bgscan idle:
			idle time for network traffic which must pass
			before starting a new background scan run."
		DEFVAL  	{5}		
		::= { flWlanWifiVapEntry 15 }
		
	flWlanWifiVapRssiChangeBgScan OBJECT-TYPE
		SYNTAX		INTEGER (1..94)
		MAX-ACCESS	read-write
		STATUS    	current
		DESCRIPTION
			"Configure the roaming parameter for the wifi device.
			Background scan -  RSSI change threshold in dBm
			Difference in RSSI value for the current AP communication
			before considering another background scan run."
		DEFVAL  	{4}
		::= { flWlanWifiVapEntry 16 }
	
	flWlanWifiVapRssiThrshBgScan  OBJECT-TYPE
		SYNTAX		INTEGER (-94.. -1)
		MAX-ACCESS	read-write
		STATUS    	current
		DESCRIPTION
			"Configure the roaming parameter for the wifi device.
			Background scan threshold in dBm.
			RSSI value below which the device starts background scans,
			if the network traffic is idle."
		DEFVAL  	{-60}
		::= { flWlanWifiVapEntry 17 }
		
	flWlanWifiVapScbManMac OBJECT-TYPE
		SYNTAX		DisplayString
		MAX-ACCESS	read-write
		STATUS    	current
		DESCRIPTION
			"Configure the mac address, the device uses in scb mode.
			Format of the value: {xx:xx:xx:xx:xx:xx}"
		::= { flWlanWifiVapEntry 18 }
		
	flWlanWifiVapScbMode OBJECT-TYPE
		SYNTAX		INTEGER {
					auto(1),
					manual(2)
		}
		MAX-ACCESS	read-write
		STATUS    	current
		DESCRIPTION
			"Configure the way the device adopts its mac address."
		::= { flWlanWifiVapEntry 19 }
		
	flWlanWifiVapFragThreshold OBJECT-TYPE
		SYNTAX		Integer32 (0..65535)
		MAX-ACCESS	read-write
		STATUS    	current
		DESCRIPTION
			"Configure the wlan fragmentation threshold of the wifi device."
		::= { flWlanWifiVapEntry 20 }
		
	flWlanWifiVapTxPowerRadiated OBJECT-TYPE
		SYNTAX		INTEGER (5..20)
		MAX-ACCESS	read-write
		STATUS    	current
		DESCRIPTION
			"Configure the wlan transmission power in dBm of the wifi device."
		::= { flWlanWifiVapEntry 21 }
	
	flWlanWifiVapCurrentTxPowerRadiated OBJECT-TYPE
		SYNTAX		INTEGER
		MAX-ACCESS	read-only
		STATUS    	current
		DESCRIPTION
			"Shows the radiated transmit power in dBm."
		::= { flWlanWifiVapEntry 22 }
		
	flWlanWifiVapChBandwidth OBJECT-TYPE
		SYNTAX		INTEGER {
					f20MHz (1),
					f40MHz (2)
		}
		MAX-ACCESS	read-write
		STATUS    	current
		DESCRIPTION
			"Configure the wlan channel bandwidth in MHz of the wifi device.
			The wlan channel bandwidth can be set to 20 MHz or to 40 MHz,
			if higher throuput is required. The drawback on 40MHz is that
			the number of usable wlans get reduced in that environment."
		::= { flWlanWifiVapEntry 23 }
		
	flWlanWifiVapWlanCh OBJECT-TYPE
		SYNTAX		INTEGER {
					channel-1 (1),
					channel-2 (2),
					channel-3 (3),
					channel-4 (4),
					channel-5 (5),
					channel-6 (6),
					channel-7 (7),
					channel-8 (8),
					channel-9 (9),
					channel-10 (10),
					channel-11 (11),
					channel-12 (12),
					channel-13 (13),
					channel-14 (14),
					channel-36 (36),
					channel-40 (40),
					channel-44 (44),
					channel-48 (48),
					channel-52 (52),
					channel-56 (56),
					channel-60 (60),
					channel-64 (64),
					channel-132 (132),
					channel-136 (136),
					channel-140 (140),
					channel-149 (149),
					channel-153 (153),
					channel-157 (157),
					channel-161 (161),
					channel-165 (165),
					indoor8-auto (200),
					indoor16-auto (201),
					outdoor (202),
					auto (203)
		}
		MAX-ACCESS	read-write
		STATUS    	current
		DESCRIPTION
			"Configure the wlan channel of the wifi device.
			2.4 GHz: (1-14)
			5 GHz:(36) (40) (44) (48) (52) (56) (60) (64) (132) (136) (140)
			(149) (153) (157) (161) (165) (indoor8) (indoor16) (Auto)"
		::= { flWlanWifiVapEntry 24 }
		
	flWlanWifiVap80211Mode OBJECT-TYPE
		SYNTAX		INTEGER {
					a(1),
					b(2),
					bg(3),
					an(4),
					gn(5)
		}
		MAX-ACCESS	read-write
		STATUS    	current
		DESCRIPTION
			"Configure the wlan ieee 802.11 mode of the wifi device.
			{a 5 GHz | b 2.4 GHz | bg 2.4 GHz | an 5 GHz | gn 2.4 GHz}"
		::= { flWlanWifiVapEntry 25 }
		
	flWlanWifiVapHwID OBJECT-TYPE
		SYNTAX		INTEGER
		MAX-ACCESS	read-only
		STATUS    	current
		DESCRIPTION
			"Shows the wlan radio hardware instance the wifi is derived from."
		::= { flWlanWifiVapEntry 26 }
		
	flWlanWifiVapOpMode OBJECT-TYPE
		SYNTAX		INTEGER {
					ap(1),
					scb(2),
					mcb(3),
					ftb(4),
                    monitor(5),
                    mesh(6),
					natc(8)
		}
		MAX-ACCESS	read-write
		STATUS    	current
		DESCRIPTION
			"Configure the operation mode of the wifi device."
		::= { flWlanWifiVapEntry 27 }		  
	
	flWlanWifiVapStatus OBJECT-TYPE
		SYNTAX		INTEGER {
						ready  	 (0),
						scanning (1)						
		}
		MAX-ACCESS	read-only
		STATUS    	current
		DESCRIPTION
			"Shows if the wifi interface is scanning or ready."
		::= { flWlanWifiVapEntry 28 }
		
	
		
	flWlanWifiVapActiveProfile OBJECT-TYPE
		SYNTAX		INTEGER 
		MAX-ACCESS	read-only
		STATUS    	current
		DESCRIPTION
			"Shows the active profile for this virtual access point."
		DEFVAL  	{1}
		::= { flWlanWifiVapEntry 29 }
	
	flWlanWifiVapRowStatus OBJECT-TYPE
         SYNTAX      RowStatus
         MAX-ACCESS  read-create
         STATUS      current
         DESCRIPTION
                     "createAndGo(4) - create a new row/virtual access point entity.
                      destroy(6) - Removes a row/virtual access point entity."
         ::= { flWlanWifiVapEntry 30 }
		 
	--**********************************************************************
		 
	flWlanWifiVapProfileTable OBJECT-TYPE
		SYNTAX    	SEQUENCE OF FlWlanWifiVapProfileEntry
		MAX-ACCESS 	not-accessible
		STATUS     	current
		DESCRIPTION
			"Virtual access point profile table.
			Two Indices: vapID and vapProfileID.
			There can be many profiles defined for a single vap."
		::= { flWlanWifi 2 }
	   
	flWlanWifiVapProfileEntry OBJECT-TYPE
		SYNTAX		FlWlanWifiVapProfileEntry
		MAX-ACCESS 	not-accessible 
		STATUS     	current
		DESCRIPTION 
			"Each entry in this table represents a vap wlan profile."
		INDEX		{ flWlanWifiVapProfileVapID,
					  flWlanWifiVapProfileID }
		::= { flWlanWifiVapProfileTable 1 }
	   
	FlWlanWifiVapProfileEntry ::=
		SEQUENCE {
			flWlanWifiVapProfileVapID  
				INTEGER,
			flWlanWifiVapProfileID  
				INTEGER,
			flWlanWifiVapProfileEapClientcertPsKey  
				OCTET STRING,
			flWlanWifiVapProfileEapUserPw  
				OCTET STRING,
			flWlanWifiVapProfileEapIdentity  
				DisplayString,
			flWlanWifiVapProfileEapPhase2Auth  
				INTEGER,
			flWlanWifiVapProfileEapPairwiseMode  
				INTEGER,
			flWlanWifiVapProfileEapMode  
				INTEGER,
			flWlanWifiVapProfilePsKey  
				OCTET STRING,
			flWlanWifiVapProfileEnc  
				INTEGER,
			flWlanWifiVapProfileAuth  
				INTEGER,
			flWlanWifiVapProfileSsid  
				DisplayString
--			flWlanWifiVapProfileRowStatus
--				RowStatus
          }
	
	flWlanWifiVapProfileVapID OBJECT-TYPE
		SYNTAX     	INTEGER (1..255)
		MAX-ACCESS 	read-only
		STATUS     	current
		DESCRIPTION
			"First index: Each VapID is the identification number of a wlan virtual access point (101,102..)."
		::= { flWlanWifiVapProfileEntry 1 }
		
	flWlanWifiVapProfileID OBJECT-TYPE
		SYNTAX     	INTEGER (1..255)
		MAX-ACCESS 	read-only
		STATUS     	current
		DESCRIPTION
			"Second index: Each VapProfileID is the identification number of a wlan virtual access point profile (1,2..)."
		::= { flWlanWifiVapProfileEntry 2 }
		
	flWlanWifiVapProfileEapClientcertPsKey OBJECT-TYPE
		SYNTAX     	OCTET STRING (SIZE(16..128))
		MAX-ACCESS 	read-write
		STATUS     	current
		DESCRIPTION
			"Configure the client certificate preshared key for the given profile.
			This write only object changes the current
                 password to a given new password. The character
                 mask is defined as below:

                    1.) The password length is min. 8 and max. 64 characters.
                    2.) All ASCII codes allowd (except code 0x00).
                    3.) For redundancy check the password is giving
                        twice as shown below:
                        
                            password:                   nimbus3
                            
                            octetstr = 2 x password:    nimbus3nimbus3
                            
                    4.) As an result of this the absolut length of
                        octet string is even and min. 16 and max. 128 characters.
                        
                 The firmware will always return a string of five
                 asterics (*****) when this object is read."
		::= { flWlanWifiVapProfileEntry 3 }

	flWlanWifiVapProfileEapUserPw OBJECT-TYPE
		SYNTAX     	OCTET STRING (SIZE(16..128))
		MAX-ACCESS 	read-write
		STATUS     	current
		DESCRIPTION
			"Configure the eap-user password of a specific profile for the wifi device.
			This write only object changes the current
                 password to a given new password. The character
                 mask is defined as below:

                    1.) The password length is min. 8 and max. 64 characters.
                    2.) All ASCII codes allowd (except code 0x00).
                    3.) For redundancy check the password is giving
                        twice as shown below:
                        
                            password:                   nimbus3
                            
                            octetstr = 2 x password:    nimbus3nimbus3
                            
                    4.) As an result of this the absolut length of
                        octet string is even and min. 16 and max. 128 characters.
                        
                 The firmware will always return a string of five
                 asterics (*****) when this object is read."
		::= { flWlanWifiVapProfileEntry 4 }
		
	flWlanWifiVapProfileEapIdentity OBJECT-TYPE
		SYNTAX     	DisplayString
		MAX-ACCESS 	read-write
		STATUS     	current
		DESCRIPTION
			"Configure the eap-identity of a specific profile for the wifi device."
		::= { flWlanWifiVapProfileEntry 5 }
	
	flWlanWifiVapProfileEapPhase2Auth OBJECT-TYPE
		SYNTAX     	INTEGER {
						mschapv2 (1),
						md5 (2)
		}
		MAX-ACCESS 	read-write
		STATUS     	current
		DESCRIPTION
			"Configure the eap-phase 2 authentication mode of a specific profile for the wifi device."
		::= { flWlanWifiVapProfileEntry 6 }
		
	flWlanWifiVapProfileEapPairwiseMode OBJECT-TYPE
		SYNTAX     	INTEGER {
						aes (1),
						tkip (2)
		}
		MAX-ACCESS 	read-write
		STATUS     	current
		DESCRIPTION
			"Configure the eap-pairwise mode of a specific profile for the wifi device."
		::= { flWlanWifiVapProfileEntry 7 }
		
	flWlanWifiVapProfileEapMode OBJECT-TYPE
		SYNTAX     	INTEGER {
						disable (0),
						peap (1),
						ttls (2),
						tls (3)
		}
		MAX-ACCESS 	read-write
		STATUS     	current
		DESCRIPTION
			"Configure the eap-mode of a specific profile for the wifi device."
		::= { flWlanWifiVapProfileEntry 8 }
		
	flWlanWifiVapProfilePsKey OBJECT-TYPE
		SYNTAX     	OCTET STRING (SIZE(16..128))
		MAX-ACCESS 	read-write
		STATUS     	current
		DESCRIPTION
			"Configure the preshared key of a specific profile for the wifi device.
			This write only object changes the current
                 password to a given new password. The character
                 mask is defined as below:

                    1.) The password length is min. 8 and max. 64 characters.
					
					2.)	Aphabetical characters, digits and the following characters
						are permitted: $%@&/\\()=?[]{}+*-_<>#^.,:~|
						Exception for WEP:
						[WEP64] 5 alphanumerical character or 10 hex digits.
						[WEP128] 13 alphanumerical character or 26 hex digits.						
					
                    3.) For redundancy check the password is giving
                        twice as shown below:
                        
                            password:                   nimbus3
                            
                            octetstr = 2 x password:    nimbus3nimbus3
                            
                    4.) As an result of this the absolut length of
                        octet string is even and min. 10/16 and max. 128 characters.
                        
                 The firmware will always return a string of five
                 asterics (*****) when this object is read."
		::= { flWlanWifiVapProfileEntry 9 }
		
	flWlanWifiVapProfileEnc OBJECT-TYPE
		SYNTAX     	INTEGER {
						tkip (1),
						aes (2),
						tkip-aes (3)
		}
		MAX-ACCESS 	read-write
		STATUS     	current
		DESCRIPTION
			"Configure the encryption mode of a specific profile for the wifi device."
		::= { flWlanWifiVapProfileEntry 10 }
		  
	flWlanWifiVapProfileAuth OBJECT-TYPE
		SYNTAX     	INTEGER {
						none (0),
						wpa-psk (1),
						wep64 (2),
						wep128 (3),
						wpa2-psk (4),
						wpa2-eap (5),
						wpa-wpa2-psk (6),
						ft-psk (7),
						ft-eap (8)
		}
		MAX-ACCESS 	read-write
		STATUS     	current
		DESCRIPTION
			"Configure the authentication mode of a specific profile for the wifi device."
		::= { flWlanWifiVapProfileEntry 11 }
		
	flWlanWifiVapProfileSsid OBJECT-TYPE
		SYNTAX     	DisplayString
		MAX-ACCESS 	read-write
		STATUS     	current
		DESCRIPTION
			"Configure the ssid of a specific profile for the wifi device."
		::= { flWlanWifiVapProfileEntry 12 }
	
--	flWlanWifiVapProfileRowStatus OBJECT-TYPE
--         SYNTAX      RowStatus
--         MAX-ACCESS  read-create
--         STATUS      current
--         DESCRIPTION
--                     "createAndGo(4) - create a new row/virtual access point profile.
--                    destroy(6) - Removes a row/virtual access point profile."
--         ::= { flWlanWifiVapProfileEntry 13 }
		 
	--**********************************************************************
	
	flWlanWifiScanResultsTable OBJECT-TYPE
		SYNTAX    	SEQUENCE OF FlWlanWifiScanResultsEntry
		MAX-ACCESS 	not-accessible
		STATUS     	current
		DESCRIPTION
			"Shows the results of a wlan scan.
			Note! This command requires that a scan process has been processed before.
			1) Start a scan process with: flWlanWifiVapStartScanning
			2) The scan process takes some time. The status about the scan results
			can be checked by the command: flWlanWifiVapStatus
			3) If the status from the previous step switches from Scanning to Ready,
			the scan-results can be displayed with flWlanWifiScanResultsTable"
		::= { flWlanWifi 3 }
	   
	flWlanWifiScanResultsEntry OBJECT-TYPE
		SYNTAX		FlWlanWifiScanResultsEntry
		MAX-ACCESS 	not-accessible 
		STATUS     	current
		DESCRIPTION 
			"Each entry in this table shows a single wlan network in the environment of the device."
		INDEX		{ flWlanWifiScanResultsVapID, flWlanWifiScanResultsID }
		::= { flWlanWifiScanResultsTable 1 }
	   
	FlWlanWifiScanResultsEntry ::=
		SEQUENCE {
			flWlanWifiScanResultsVapID  
				INTEGER,
			flWlanWifiScanResultsID  
				INTEGER,
			flWlanWifiScanResultsEssid  
				DisplayString,
			flWlanWifiScanResultsBssid  
				DisplayString,
			flWlanWifiScanResultsCh  
				INTEGER,
			flWlanWifiScanResultsSignal  
				INTEGER,
			flWlanWifiScanResultsSecurity  
				DisplayString,
			flWlanWifiScanResultsEnc  
				INTEGER,	
			flWlanWifiScanResultsMode  
				DisplayString
          }
		  
	flWlanWifiScanResultsVapID OBJECT-TYPE
		SYNTAX     	INTEGER (1..255)
		MAX-ACCESS 	read-only
		STATUS     	current
		DESCRIPTION
			"Each ScanResultsVapID is the identification number of a virtual access point.
			 Every vap has its own scan results."
		::= { flWlanWifiScanResultsEntry 1 }
		
	flWlanWifiScanResultsID OBJECT-TYPE
		SYNTAX     	INTEGER (1..255)
		MAX-ACCESS 	read-only
		STATUS     	current
		DESCRIPTION
			"Each ScanResultsID is the identification number of a wlan network in the environment of the device."
		::= { flWlanWifiScanResultsEntry 2 }
		
	flWlanWifiScanResultsEssid OBJECT-TYPE
		SYNTAX     	DisplayString 
		MAX-ACCESS 	read-only
		STATUS     	current
		DESCRIPTION
			"The Essid (Extended Service Set Identifier) is the identifier of the found wlan network."
		::= { flWlanWifiScanResultsEntry 3 }	
		
	flWlanWifiScanResultsBssid OBJECT-TYPE
		SYNTAX     	DisplayString 
		MAX-ACCESS 	read-only
		STATUS     	current
		DESCRIPTION
			"The Bssid (Basic Service Set Identifier) is the basic identifier of the found wlan network."
		::= { flWlanWifiScanResultsEntry 4 }	
		
	flWlanWifiScanResultsCh OBJECT-TYPE
		SYNTAX     	INTEGER
		MAX-ACCESS 	read-only
		STATUS     	current
		DESCRIPTION
			"Shows the channel on which the found wlan network is operating."
		::= { flWlanWifiScanResultsEntry 5 }	
		
	flWlanWifiScanResultsSignal OBJECT-TYPE
		SYNTAX     	INTEGER 
		MAX-ACCESS 	read-only
		STATUS     	current
		DESCRIPTION
			"Shows the signal power of the found wlan network in dBm {-0dBm..-xxdBm} (-0dBm is the best result)"
		::= { flWlanWifiScanResultsEntry 6 }	
		
	flWlanWifiScanResultsSecurity OBJECT-TYPE
		SYNTAX     	DisplayString
		MAX-ACCESS 	read-only
		STATUS     	current
		DESCRIPTION
			"Shows the security authentication methode of the found wlan network.
			{none | wpa-psk | wep64 | wep128 | wpa2-psk | wpa-wpa2-psk | wpa2-eap }"
		::= { flWlanWifiScanResultsEntry 7 }	

	flWlanWifiScanResultsEnc OBJECT-TYPE
		SYNTAX     	INTEGER{
						none (0),
						tkip (1),
						aes (2)
		} 
		MAX-ACCESS 	read-only
		STATUS     	current
		DESCRIPTION
			"Shows if the tkip or aes encription methode is enabled."
		::= { flWlanWifiScanResultsEntry 8 }	
	
	flWlanWifiScanResultsMode OBJECT-TYPE
		SYNTAX     	DisplayString 
		MAX-ACCESS 	read-only
		STATUS     	current
		DESCRIPTION
			"Shows the mode of the found wlan network.
			{Master-mode | client/managed-mode | Ad-hoc-mode | Monitor-mode}"
		::= { flWlanWifiScanResultsEntry 9 }	
		
	--**********************************************************************	  
	
	flWlanWifiConnectionTable OBJECT-TYPE
		SYNTAX    	SEQUENCE OF FlWlanWifiConnectionEntry
		MAX-ACCESS 	not-accessible
		STATUS     	current
		DESCRIPTION
			"Shows the connected wlan network in client mode.
			Shows the connected clients in accesspoint mode"
		::= { flWlanWifi 4 }
	   
	flWlanWifiConnectionEntry OBJECT-TYPE
		SYNTAX		FlWlanWifiConnectionEntry
		MAX-ACCESS 	not-accessible 
		STATUS     	current
		DESCRIPTION 
			"Each entry in this table represents a connected wlan network/wlan client."
		INDEX		{ flWlanWifiConnectionVapID, flWlanWifiConnectionID }
		::= { flWlanWifiConnectionTable 1 }
	   
	FlWlanWifiConnectionEntry ::=
		SEQUENCE {
			flWlanWifiConnectionVapID  
				INTEGER,
			flWlanWifiConnectionOpMode  
				INTEGER,
			flWlanWifiConnectionID  
				INTEGER,
			flWlanWifiConnectionSsid  
				DisplayString,
			flWlanWifiConnectionMac  
				DisplayString,
			flWlanWifiConnectionRssi  
				INTEGER,
			flWlanWifiConnectionBitRate  
				INTEGER,
			flWlanWifiConnectionFreq  
				DisplayString,
			flWlanWifiConnectionCh  
				INTEGER
          }
		
	flWlanWifiConnectionVapID OBJECT-TYPE
		SYNTAX     	INTEGER (1..255)
		MAX-ACCESS 	read-only
		STATUS     	current
		DESCRIPTION
			"Each ConnectionVapID is the identification number of a virtual access point.
			 Every vap has a maximum of one entry in client mode and multiple entries in access point mode."
		::= { flWlanWifiConnectionEntry 1 }
		
	flWlanWifiConnectionID OBJECT-TYPE
		SYNTAX     	INTEGER (1..255)
		MAX-ACCESS 	read-only
		STATUS     	current
		DESCRIPTION
			"Each ConnectionID is the identification number of a connected wlan network/wlan client (depending on client or access point mode)."
		::= { flWlanWifiConnectionEntry 2 }
	
	flWlanWifiConnectionOpMode OBJECT-TYPE
		SYNTAX     	INTEGER{
					ap(1),
					scb(2),
					mcb(3),
					ftb(4),
                    monitor(5),
                    mesh(6),
					natc(8)
		} 
		MAX-ACCESS 	read-only
		STATUS     	current
		DESCRIPTION
			"Shows the operation mode of the wifi device."
		::= { flWlanWifiConnectionEntry 3 }
		
	flWlanWifiConnectionSsid OBJECT-TYPE
		SYNTAX     	DisplayString 
		MAX-ACCESS 	read-only
		STATUS     	current
		DESCRIPTION
			"The Ssid (Extended Service Set Identifier) is the identifier of a connected wlan network."
		::= { flWlanWifiConnectionEntry 4 }
		
	flWlanWifiConnectionMac OBJECT-TYPE
		SYNTAX     	DisplayString 
		MAX-ACCESS 	read-only
		STATUS     	current
		DESCRIPTION
			"Shows the mac address of the connected device."
		::= { flWlanWifiConnectionEntry 5 }
		
	flWlanWifiConnectionRssi OBJECT-TYPE
		SYNTAX     	INTEGER 
		MAX-ACCESS 	read-only
		STATUS     	current
		DESCRIPTION
			"The Received Signal Strength Indication (RSSI) is a reference value for the signal power of a connected wlan network/wlan client."
		::= { flWlanWifiConnectionEntry 6 }
		
	flWlanWifiConnectionBitRate OBJECT-TYPE
		SYNTAX     	INTEGER
		MAX-ACCESS 	read-only
		STATUS     	current
		DESCRIPTION
			"The bit rate shows the data transfer rate in Mbps of a connected wlan network/wlan client."
		::= { flWlanWifiConnectionEntry 7 }
		
	flWlanWifiConnectionFreq OBJECT-TYPE
		SYNTAX     	DisplayString
		MAX-ACCESS 	read-only
		STATUS     	current
		DESCRIPTION
			"The frequency shows the operating wlan frequency band."
		::= { flWlanWifiConnectionEntry 8 }
		
	flWlanWifiConnectionCh OBJECT-TYPE
		SYNTAX     	INTEGER {
						channel-1 (1),
						channel-2 (2),
						channel-3 (3),
						channel-4 (4),
						channel-5 (5),
						channel-6 (6),
						channel-7 (7),
						channel-8 (8),
						channel-9 (9),
						channel-10 (10),
						channel-11 (11),
						channel-12 (12),
						channel-13 (13),
						channel-14 (14),
						channel-36 (36),
						channel-40 (40),
						channel-44 (44),
						channel-48 (48),
						channel-52 (52),
						channel-56 (56),
						channel-60 (60),
						channel-64 (64),
						channel-132 (132),
						channel-136 (136),
						channel-140 (140),
						channel-149 (149),
						channel-153 (153),
						channel-157 (157),
						channel-161 (161),
						channel-165 (165),
						indoor8-auto (200),
						indoor16-auto (201),
						outdoor (202),
						auto (203)
		}
		MAX-ACCESS 	read-only
		STATUS     	current
		DESCRIPTION
			"Shows the operating channel of a connected wlan network/wlan client."
		::= { flWlanWifiConnectionEntry 9 }
				  
	--**********************************************************************	  
END
