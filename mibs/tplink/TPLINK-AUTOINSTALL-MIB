TPLINK-AUTOINSTALL-MIB DEFINITIONS ::= BEGIN

         IMPORTS
            MODULE-IDENTITY, OBJECT-TYPE
          	  	        FROM SNMPv2-SMI
            tplinkMgmt
						FROM TPLINK-MIB; 
	    
			tplinkAutoInstallMIB MODULE-IDENTITY
				LAST-UPDATED    "201212171014Z"
				ORGANIZATION    "TPLINK"
				CONTACT-INFO    "www.tplink.com"
				DESCRIPTION	    "Private MIB for Auto Install configuration."
				REVISION        "201212171014Z"
				DESCRIPTION
				"Initial version of this MIB module."
			::= { tplinkMgmt 97 }
		
			tplinkAutoInstallMIBObjects		OBJECT IDENTIFIER	::= { tplinkAutoInstallMIB 1 }
			tplinkAutoInstallNotifications		OBJECT IDENTIFIER	::= { tplinkAutoInstallMIB 2 }
  			
  			autoInstallConfig		OBJECT IDENTIFIER	::= { tplinkAutoInstallMIBObjects 1 }
				
				autoInstallStartStop OBJECT-TYPE
	          		SYNTAX  INTEGER{
	      				stop(0), 						
	      				start(1)						
	      			}
	            MAX-ACCESS  read-write
	            STATUS  current
	            DESCRIPTION
	                    "0. stop 
	                     1. start
	                     start or stop the Auto Install function."
	            ::= { autoInstallConfig 1 }
                
				autoInstallPersistentMode OBJECT-TYPE
	          		SYNTAX  INTEGER{
	      				disable(0), 						
	      				enable(1)						
	      			}
	            MAX-ACCESS  read-write
	            STATUS  current
	            DESCRIPTION
	                    "0. disable 
	                     1. enable
	                     disable or enable the Auto Install function for next reboot cycle."
	            ::= { autoInstallConfig 2 }

				autoInstallAutoSave OBJECT-TYPE
	          		SYNTAX  INTEGER{
	      				disable(0), 						
	      				enable(1)						
	      			}
	            MAX-ACCESS  read-write
	            STATUS  current
	            DESCRIPTION
	                    "0. disable 
	                     1. enable
	                     disable or enable auto save the downloaded configuration file to startup configuration file."
	            ::= { autoInstallConfig 3 }

				autoInstallAutoReboot OBJECT-TYPE
	          		SYNTAX  INTEGER{
	      				disable(0), 						
	      				enable(1)						
	      			}
	            MAX-ACCESS  read-write
	            STATUS  current
	            DESCRIPTION
	                    "0. disable 
	                     1. enable
	                     disable or enable reboot the switch after Auto Install completed successfully."
	            ::= { autoInstallConfig 4 }
                
				autoInstallRetryCount OBJECT-TYPE
	          		SYNTAX  INTEGER(1..3)
	            MAX-ACCESS  read-write
	            STATUS  current
	            DESCRIPTION
	                    "Configure retry count when Auto Install function uses TFTP to download configuration files in a cycle of Auto Install process."
	            ::= { autoInstallConfig 5 }

                autoInstallState OBJECT-TYPE
					SYNTAX  	OCTET STRING (SIZE (0..256))
					MAX-ACCESS  read-only
					STATUS  	current
					DESCRIPTION
						"Display the running state of Auto Install."
				::= { autoInstallConfig 6 }             
          
END
