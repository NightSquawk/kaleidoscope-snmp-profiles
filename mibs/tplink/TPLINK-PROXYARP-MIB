TPLINK-PROXYARP-MIB	DEFINITIONS ::= BEGIN	
    IMPORTS
		tplinkMgmt
			FROM TPLINK-MIB			
        OBJECT-TYPE,IpAddress
          	FROM SNMPv2-SMI;
	    
		tplinkProxyArpMIB MODULE-IDENTITY
		LAST-UPDATED    "201212130930Z"
		ORGANIZATION    "TPLINK"
		CONTACT-INFO    "www.tplink.com"
		DESCRIPTION	    "Private MIB for proxy arp configuration."
		REVISION        "201212130930Z"
		DESCRIPTION
				"Initial version of this MIB module."
		::= { tplinkMgmt 37 }
		
	tplinkProxyArpMIBObjects		OBJECT IDENTIFIER	::= { tplinkProxyArpMIB 1 }
	tplinkProxyArpNotifications		OBJECT IDENTIFIER	::= { tplinkProxyArpMIB 2 }
	
	--**************
	--Set Proxy Arp
	--**************
	tpProxyArpConfig	  	OBJECT IDENTIFIER ::= {tplinkProxyArpMIB 1}
	
	tpProxyArpTable OBJECT-TYPE
		SYNTAX  SEQUENCE OF PROXYARPENTRY
		MAX-ACCESS  not-accessible
		STATUS  current
		DESCRIPTION
			"Proxy Arp."
		::= { tpProxyArpConfig 1 }

	tpProxyArpEntry OBJECT-TYPE
		SYNTAX  PROXYARPENTRY
		MAX-ACCESS  not-accessible
		STATUS  current
		DESCRIPTION
			"An entry contains of the information of port configure."
		INDEX   { tpProxyArpInterface }
		::= { tpProxyArpTable 1 }

	PROXYARPENTRY ::=
		SEQUENCE {
			tpProxyArpInterface
				OCTET STRING (SIZE (0..50)),
			tpProxyArpIpAddr
				IpAddress,
			tpProxyArpIpMask
				IpAddress,	
			tpProxyArpEnable 		
				INTEGER
		}

	tpProxyArpInterface OBJECT-TYPE
		SYNTAX  OCTET STRING (SIZE (0..50))
		MAX-ACCESS  read-only
		STATUS  current
		DESCRIPTION
			"Displays the interface."
		::= { tpProxyArpEntry 1 } 

	tpProxyArpIpAddr OBJECT-TYPE
		SYNTAX  IpAddress  
		MAX-ACCESS  read-only
		STATUS  current
		DESCRIPTION
			"Displays the proxy arp ip address."
		::= { tpProxyArpEntry 2 }

	tpProxyArpIpMask OBJECT-TYPE
		SYNTAX  IpAddress
		MAX-ACCESS  read-only
		STATUS  current
		DESCRIPTION
			"Displays the proxy arp ip address mask"
		::= { tpProxyArpEntry 3 }    

	tpProxyArpEnable OBJECT-TYPE
		SYNTAX  INTEGER{
						disable(0), 					--Disable
						enable(1)						--Enable
						}
		MAX-ACCESS  read-write
		STATUS  current
		DESCRIPTION
			"Select Enable/Disable proxy arp for the interface. 
			0. Disable
			1. Enable"
		::= { tpProxyArpEntry 4 }

END
