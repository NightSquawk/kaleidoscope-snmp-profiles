TPLINK-STATICMROUTE-MIB	DEFINITIONS ::= BEGIN	
    IMPORTS
		MODULE-IDENTITY, OBJECT-TYPE, IpAddress ,Integer32
			FROM SNMPv2-SMI   
		TPRowStatus       	 
			FROM TPLINK-TC-MIB
		tplinkMgmt
			FROM TPLINK-MIB;
          	  	          
	tplinkStaticMrouteMIB MODULE-IDENTITY
		LAST-UPDATED    "201212130930Z"
		ORGANIZATION    "TPLINK"
		CONTACT-INFO    "www.tplink.com"
		DESCRIPTION	    "Private MIB for static Mroute configuration."
		REVISION        "201212130930Z"
		DESCRIPTION
				"Initial version of this MIB module."
		::= { tplinkMgmt 79 }
		
	tplinkStaticMrouteMIBObjects		OBJECT IDENTIFIER	::= { tplinkStaticMrouteMIB 1 }
	tplinkStaticMrouteNotifications	    OBJECT IDENTIFIER	::= { tplinkStaticMrouteMIB 2 }
	tplinkStaticMrouteConfig 		    OBJECT IDENTIFIER   ::= {tplinkStaticMrouteMIBObjects 1}

--Set static mroute entry	

	tpStaticMrouteTable OBJECT-TYPE
        SYNTAX  SEQUENCE OF TpStaticMrouteEntry
        MAX-ACCESS  not-accessible
        STATUS  current
        DESCRIPTION
            "Static mroutes are special routes manually configured by the 
			administrator and cannot change automatically with the network 
			topology accordingly."
        ::= { tplinkStaticMrouteConfig 1 }
        
    tpStaticMrouteEntry OBJECT-TYPE
        SYNTAX  TpStaticMrouteEntry
        MAX-ACCESS  not-accessible
        STATUS  current
        DESCRIPTION
            "The item can be added or removed ."
        INDEX   { tpStaticMrouteSource,tpStaticMrouteSourceMask}
        ::= { tpStaticMrouteTable 1 }
              
              
    TpStaticMrouteEntry ::=
        SEQUENCE {
            tpStaticMrouteSource
                IpAddress, 
            tpStaticMrouteSourceMask
                IpAddress,
            tpStaticMrouteRpfNeigbor
                IpAddress,
            tpStaticMrouteDistance
                Integer32,
            tpStaticMrouteStatus
                TPRowStatus
        }
              
    tpStaticMrouteSource OBJECT-TYPE
        SYNTAX  IpAddress  
        MAX-ACCESS  read-only
        STATUS  current
        DESCRIPTION
            "The IP Address that identifies the multicast source of the entry 
			you are creating."
        ::= { tpStaticMrouteEntry 1 }
            
    tpStaticMrouteSourceMask  OBJECT-TYPE
        SYNTAX  IpAddress  
        MAX-ACCESS  read-only
        STATUS  current
        DESCRIPTION
            "The subnet mask to be applied to the Source."
        ::= { tpStaticMrouteEntry 2 }
           
	tpStaticMrouteRpfNeigbor  OBJECT-TYPE
		SYNTAX  IpAddress  
		MAX-ACCESS  read-create
		STATUS  current
		DESCRIPTION
			"the IP address of the neighbor router on the path to the mroute 
			source."
		::= { tpStaticMrouteEntry 3 }
			      
	tpStaticMrouteDistance  OBJECT-TYPE
		SYNTAX  Integer32 (0..255)  
		MAX-ACCESS  read-create
		STATUS  current
		DESCRIPTION
			"The link state cost of the path to the multicast source."
		DEFVAL     { 1 }
		::= { tpStaticMrouteEntry 4 }
			      
	tpStaticMrouteStatus OBJECT-TYPE
        SYNTAX  TPRowStatus
        MAX-ACCESS  read-create
        STATUS  current
        DESCRIPTION
            " The following values are states:
             these values may be used as follow:
             active(1),if the entry is being used.
             notInService(2),destory the entry.
             notReady(3),destory the entry.
             createAndGo(4),not being used
             createAndWait(5),creat a new entry
             destroy(6),destory the entry."
        ::={tpStaticMrouteEntry 5}        	
     
END
