TPLINK-AUTOVOIP-MIB DEFINITIONS ::= BEGIN       	 
  		IMPORTS
  			TPRowStatus       	 
									FROM TPLINK-TC-MIB
            OBJECT-TYPE,MODULE-IDENTITY
                        	  	    FROM SNMPv2-SMI
            tplinkMgmt
									FROM TPLINK-MIB
			ifIndex
									FROM RFC1213-MIB;
									
		tplinkAutoVoipMIB MODULE-IDENTITY
			LAST-UPDATED    "201212131630Z"
			ORGANIZATION    "TPLINK"
			CONTACT-INFO    "www.tplink.com"
			DESCRIPTION	    "Private MIB for autovoip configuration."
			REVISION        "201212131630Z"
			DESCRIPTION
					"Initial version of this MIB module."
			::= { tplinkMgmt 98 } 

			tplinkAutoVoipMIBObjects			OBJECT IDENTIFIER	::= { tplinkAutoVoipMIB 1 }
			tplinkAutoVoipMIBNotifications		OBJECT IDENTIFIER	::= { tplinkAutoVoipMIB 2 }
			    	
			autoVoipGlobalConfig   	OBJECT IDENTIFIER ::= {tplinkAutoVoipMIBObjects 1}	    	    	      
      	   
          autoVoipGlobalEnable OBJECT-TYPE
          		SYNTAX  INTEGER{
	      											disable(0), 				--disable
	      											enable(1)						--enable
	      											}
              MAX-ACCESS  read-write
              STATUS  current
              DESCRIPTION
                      "Select Enable/Disable Voice VLAN function.
                      0. disable 
                      1. enable"
              ::= { autoVoipGlobalConfig 1 }
              
           autoVoipPortConfig   	OBJECT IDENTIFIER ::= {tplinkAutoVoipMIBObjects 2}
           
           autoVoipPortTable OBJECT-TYPE
              SYNTAX  SEQUENCE OF AUTOVOIPPORTENTRY
              MAX-ACCESS  not-accessible
              STATUS  current
              DESCRIPTION
                      "Here you can configure the parameters of the ports in the auto voip.."
              ::= { autoVoipPortConfig 1 }

          autoVoipPortEntry OBJECT-TYPE
              SYNTAX  AUTOVOIPPORTENTRY
              MAX-ACCESS  not-accessible
              STATUS  current
              DESCRIPTION
                      "An entry contains of the information of port param."
              INDEX   { ifIndex }
              ::= { autoVoipPortTable 1 }
      
          AUTOVOIPPORTENTRY ::=
              SEQUENCE {
				  autoVoipPortNumber
              		  OCTET STRING,
                  autoVoipPortMode
                      INTEGER,
                  autoVoipPortValue
                  	  INTEGER,
                  autoVoipCosOverrideMode
					  INTEGER,
				  autoVoipOperaState
                  	  INTEGER,
				  autoVoipDscpValue
                 	  INTEGER
              }
          autoVoipPortNumber OBJECT-TYPE
            	 SYNTAX  OCTET STRING (SIZE (0..16))  
              MAX-ACCESS  read-only
              STATUS  current
              DESCRIPTION
                      "Displays the port number of the Switch."
              ::= { autoVoipPortEntry 1 }
                     
          autoVoipPortMode OBJECT-TYPE
              SYNTAX  INTEGER{
	      										disable(0), 				--Disable
	      										vlan(1),
												dot1p(2),
												none(3),
												untagged(4)
	      										}
              MAX-ACCESS  read-write
              STATUS  current
              DESCRIPTION
                      "."
              ::= { autoVoipPortEntry 2 }
               
          autoVoipPortValue OBJECT-TYPE
              SYNTAX  INTEGER (0..4094)
              MAX-ACCESS  read-write
              STATUS  current
              DESCRIPTION
                      ""
              ::= { autoVoipPortEntry 3 }
 
          autoVoipCosOverrideMode OBJECT-TYPE
              SYNTAX  INTEGER{
	      						disable(0), 				--disable
	      						enable(1)						--enable
	      					}
              MAX-ACCESS  read-write
              STATUS  current
              DESCRIPTION
                      "."
              ::= { autoVoipPortEntry 4 }
             
          autoVoipOperaState OBJECT-TYPE
              SYNTAX  INTEGER{
	      						disable(0), 				--disable
	      						enable(1)						--enable
	      					}
              MAX-ACCESS  read-only
              STATUS  current
              DESCRIPTION
                      "."
              ::= { autoVoipPortEntry 5 }
              
          autoVoipDscpValue OBJECT-TYPE
              SYNTAX  INTEGER (0..63)
              MAX-ACCESS  read-write
              STATUS  current
              DESCRIPTION
                      ""
              ::= { autoVoipPortEntry 6 }

          END
