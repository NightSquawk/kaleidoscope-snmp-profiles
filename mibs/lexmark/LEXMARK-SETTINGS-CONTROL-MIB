-- Lexmark International
        --
        --
        -- filename: LEXMARK-SETTINGS-CONTROL.mib
        -- $Revision: 1.0 $
        -- $Date: 2014/04/15

LEXMARK-SETTINGS-CONTROL-MIB DEFINITIONS ::= BEGIN

IMPORTS
    lexmarkModules
        FROM LEXMARK-ROOT-MIB
    settingsControl, settingsMIBCompliances, settingsMIBGroups
        FROM LEXMARK-SETTINGS-MIB
    MODULE-COMPLIANCE, OBJECT-GROUP
        FROM SNMPv2-CONF
    MODULE-IDENTITY, OBJECT-TYPE
        FROM SNMPv2-SMI;

settingsControlMibModule MODULE-IDENTITY
    LAST-UPDATED "201403161242Z"
    ORGANIZATION "Lexmark International, Inc."
    CONTACT-INFO "Contact your local support team or service provider."
    DESCRIPTION
        "The MIB defines the device settings control commands, used to define
         the MIB walk response content and language.

         Copyright (C) 2014 Lexmark International, Inc."
    REVISION    "201403161242Z"
    DESCRIPTION
        "Definition of the settings control OID under settings OID"
    ::= { lexmarkModules 3 }

mibWalkControl OBJECT-TYPE        -- MIB walk definition
    SYNTAX      INTEGER  {
                        none(0),
                        settingDefinition(1)
                        }
    MAX-ACCESS  read-write
    STATUS      current
    DESCRIPTION
        "Controls what is returned in a MIB walk of the device
        settings.  A device control setting is defined which
        will specify whether the 7.2 (settingsValue) MIB data
        and/or the 7.3 (settingsDefinition) MIB data will be
        included in a device MIB walk.
        This is defined because it takes a long time (and
        generates a lot of web traffic) to return a response for
        these MIBs.     The default will be neither the 7.2 nor the
        7.3 MIBs will be included in a 1.3.6.1.4.1.641 MIB walk."
        DEFVAL { 0 }
    ::= { settingsControl 1 }

mibLocalizeControl   OBJECT-TYPE       --  Language selection
    SYNTAX      INTEGER (1..24)        -- this is the language index from prtLocalizationTable
    MAX-ACCESS  read-write
    STATUS      current
    DESCRIPTION
        "Selects the language to be retuned when a localized response is
         specified.  The desired language will be specified with the two
         byte language selection values specified for the device."
    ::= { settingsControl 2  }

-- Groups

controlGroup OBJECT-GROUP
    OBJECTS     {mibWalkControl,
                 mibLocalizeControl
                }
    STATUS      current
    DESCRIPTION
        "The Control Group."
    ::= { settingsMIBGroups 1 }

-- Compliance Statements

controlMIBCompliance MODULE-COMPLIANCE
    STATUS      current
    DESCRIPTION
        "The requirements for conformance to the LEXMARK-SETTINGS-CONTROL MIB."

    MODULE      -- this module

        MANDATORY-GROUPS        { controlGroup }

        GROUP   controlGroup
        DESCRIPTION
              "The Control Group
               Implementation of this group is mandatory"

    ::= { settingsMIBCompliances 1 }

END -- end of the LEXMARK-SETTINGS-CONTROL
