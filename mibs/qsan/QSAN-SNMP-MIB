-- *****************************************************************
-- qsan_lvm3.mib:
-- Structure of Management Information for LVM3
--
-- May 23 2010, Frank Liu
--
-- Copyright (c) by QSAN technology Inc.
-- All rights reserved.
-- 
-- *****************************************************************

QSAN-SNMP-MIB DEFINITIONS ::= BEGIN

IMPORTS DisplayString FROM SNMPv2-TC;

-- QSAN SNMP tree structur
internet				OBJECT IDENTIFIER ::= { iso org(3) dod(6) 1 }
directory				OBJECT IDENTIFIER ::= { internet 1 }
mgmt					OBJECT IDENTIFIER ::= { internet 2 }
experimental			OBJECT IDENTIFIER ::= { internet 3 }
private					OBJECT IDENTIFIER ::= { internet 4 }
enterprises				OBJECT IDENTIFIER ::= { private 1 }
qsan					OBJECT IDENTIFIER ::= { enterprises 22274 }
raid					OBJECT IDENTIFIER ::= { qsan 1 }
system-config			OBJECT IDENTIFIER ::= { raid 1 }
system-config-status	OBJECT IDENTIFIER ::= { system-config 1 }
system-config-setting	OBJECT IDENTIFIER ::= { system-config 4 }
system-config-ip		OBJECT IDENTIFIER ::= { system-config 5 }
system-config-mail		OBJECT IDENTIFIER ::= { system-config 6 }
volume-config	 		OBJECT IDENTIFIER ::= { raid 2 }
enclosure-management	OBJECT IDENTIFIER ::= { raid 3 }
enclosure-management-ses	OBJECT IDENTIFIER ::= { enclosure-management 3 }
maintenance				OBJECT IDENTIFIER ::= { raid 4 }
maintenance-info		OBJECT IDENTIFIER ::= { maintenance 1 }
iscsi-config			OBJECT IDENTIFIER ::= { raid 5 }
iscsi-config-entity		OBJECT IDENTIFIER ::= { iscsi-config 2 }

-- definition of object
-- raid/system-config
-- raid/system-config/status
sys-status-raid	OBJECT-TYPE
	SYNTAX	DisplayString
	ACCESS 	read-only
	STATUS	mandatory
	DESCRIPTION
		"RAID status. 1:NG, 0:OK."
	::= { system-config-status 1 }
sys-status-temp	OBJECT-TYPE
	SYNTAX	DisplayString
	ACCESS 	read-only
	STATUS	mandatory
	DESCRIPTION
		"Temperatue overheat. 1:NG, 0:OK."
	::= { system-config-status 2 }
sys-status-volt	OBJECT-TYPE
	SYNTAX	DisplayString
	ACCESS 	read-only
	STATUS	mandatory
	DESCRIPTION
		"Voltage. 1:NG, 0:OK."
	::= { system-config-status 3 }
sys-status-ups	OBJECT-TYPE
	SYNTAX	DisplayString
	ACCESS 	read-only
	STATUS	mandatory
	DESCRIPTION
		"UPS. 1:NG, 0:OK."
	::= { system-config-status 4 }
sys-status-fan	OBJECT-TYPE
	SYNTAX	DisplayString
	ACCESS 	read-only
	STATUS	mandatory
	DESCRIPTION
		"FAN. 1:NG, 0:OK."
	::= { system-config-status 5 }
sys-status-psu	OBJECT-TYPE
	SYNTAX	DisplayString
	ACCESS 	read-only
	STATUS	mandatory
	DESCRIPTION
		"Power supply. 1:NG, 0:OK."
	::= { system-config-status 6 }
sys-status-dual	OBJECT-TYPE
	SYNTAX	DisplayString
	ACCESS 	read-only
	STATUS	mandatory
	DESCRIPTION
		"Dual controller. 1:NG, 0:OK."
	::= { system-config-status 7 }
-- raid/system-config/setting
sys-name	OBJECT-TYPE
	SYNTAX	DisplayString
	ACCESS 	read-only
	STATUS	mandatory
	DESCRIPTION
		"system name"
	::= { system-config-setting 1 }
sys-current-time	OBJECT-TYPE
	SYNTAX	DisplayString
	ACCESS 	read-only
	STATUS	mandatory
	DESCRIPTION
		"system current time"
	::= { system-config-setting 2 }
sys-ntp-server	OBJECT-TYPE
	SYNTAX	DisplayString
	ACCESS 	read-only
	STATUS	mandatory
	DESCRIPTION
		"NTP server"
	::= { system-config-setting 3 }
-- raid/system-config/ip
sys-mac	OBJECT-TYPE
	SYNTAX	DisplayString
	ACCESS 	read-only
	STATUS	mandatory
	DESCRIPTION
		"Management port MAC address"
	::= { system-config-ip 1 }
sys-ip	OBJECT-TYPE
	SYNTAX	DisplayString
	ACCESS 	read-only
	STATUS	mandatory
	DESCRIPTION
		"Management port IP address"
	::= { system-config-ip 2 }
sys-mask	OBJECT-TYPE
	SYNTAX	DisplayString
	ACCESS 	read-only
	STATUS	mandatory
	DESCRIPTION
		"Management port subnet mask"
	::= { system-config-ip 3 }
sys-gateway	OBJECT-TYPE
	SYNTAX	DisplayString
	ACCESS 	read-only
	STATUS	mandatory
	DESCRIPTION
		"Management port gateway"
	::= { system-config-ip 4 }
sys-dns	OBJECT-TYPE
	SYNTAX	DisplayString
	ACCESS 	read-only
	STATUS	mandatory
	DESCRIPTION
		"Management port DNS"
	::= { system-config-ip 5 }
sys-http-port	OBJECT-TYPE
	SYNTAX	DisplayString
	ACCESS 	read-only
	STATUS	mandatory
	DESCRIPTION
		"HTTP port"
	::= { system-config-ip 6 }
sys-https-port	OBJECT-TYPE
	SYNTAX	DisplayString
	ACCESS 	read-only
	STATUS	mandatory
	DESCRIPTION
		"HTTPS port"
	::= { system-config-ip 7 }
sys-ssh-port	OBJECT-TYPE
	SYNTAX	DisplayString
	ACCESS 	read-only
	STATUS	mandatory
	DESCRIPTION
		"SSH port"
	::= { system-config-ip 8 }
-- raid/system-config/mail
sys-mailfrom	OBJECT-TYPE
	SYNTAX	DisplayString
	ACCESS 	read-only
	STATUS	mandatory
	DESCRIPTION
		"Mail-from address"
	::= { system-config-mail 1 }
sys-mailto1	OBJECT-TYPE
	SYNTAX	DisplayString
	ACCESS 	read-only
	STATUS	mandatory
	DESCRIPTION
		"Mail-to address 1"
	::= { system-config-mail 2 }
sys-mailto1-filter	OBJECT-TYPE
	SYNTAX	DisplayString
	ACCESS 	read-only
	STATUS	mandatory
	DESCRIPTION
		"Mail-to address 1 filter. 0b100:INFO, 0b010:WARNING, 0b001:ERROR."
	::= { system-config-mail 3 }
sys-mailto2	OBJECT-TYPE
	SYNTAX	DisplayString
	ACCESS 	read-only
	STATUS	mandatory
	DESCRIPTION
		"Mail-to address 2"
	::= { system-config-mail 4 }
sys-mailto2-filter	OBJECT-TYPE
	SYNTAX	DisplayString
	ACCESS 	read-only
	STATUS	mandatory
	DESCRIPTION
		"Mail-to address 2 filter. 0b100:INFO, 0b010:WARNING, 0b001:ERROR."
	::= { system-config-mail 5 }
sys-mailto3	OBJECT-TYPE
	SYNTAX	DisplayString
	ACCESS 	read-only
	STATUS	mandatory
	DESCRIPTION
		"Mail-to address 3"
	::= { system-config-mail 6 }
sys-mailto3-filter	OBJECT-TYPE
	SYNTAX	DisplayString
	ACCESS 	read-only
	STATUS	mandatory
	DESCRIPTION
		"Mail-to address 3 filter. 0b100:INFO, 0b010:WARNING, 0b001:ERROR."
	::= { system-config-mail 7 }
sys-smpt-relay	OBJECT-TYPE
	SYNTAX	DisplayString
	ACCESS 	read-only
	STATUS	mandatory
	DESCRIPTION
		"SMPT relay"
	::= { system-config-mail 8 }


-- raid/volume-config
-- raid/volume-config/physical-disk
physical-disk OBJECT-TYPE
	SYNTAX 	SEQUENCE OF PD-ITEM
	ACCESS	not-accessible
	STATUS	mandatory
	DESCRIPTION
		"physical disk list"
	::= { volume-config 1 }
physical-disk-item 	OBJECT-TYPE
	SYNTAX	PD-ITEM
	ACCESS	not-accessible
	STATUS	mandatory
	DESCRIPTION
		"physical disk item"
	INDEX	{ pd-location }
	::= { physical-disk 1 }
PD-ITEM ::= SEQUENCE {
	pd-location DisplayString,
	pd-size DisplayString,
	pd-RG DisplayString,
	pd-status DisplayString,
	pd-status-health DisplayString,
	pd-status-usage DisplayString,
	pd-vendor DisplayString,
	pd-serial DisplayString,
	pd-type DisplayString,
	pd-write-cache DisplayString,
	pd-standby DisplayString,
	pd-readahead DisplayString,
	pd-command-queuing DisplayString,
  pd-performance DisplayString
}
pd-location	OBJECT-TYPE
	SYNTAX	DisplayString
	ACCESS 	read-only
	STATUS	mandatory
	DESCRIPTION
		"PD location. e0d0: local controller slot 1, e1d0: JBOD slot 1, etc..."
	::= { physical-disk-item 1 }
pd-size	OBJECT-TYPE
	SYNTAX	DisplayString
	ACCESS 	read-only
	STATUS	mandatory
	DESCRIPTION
		"Size(GB)"
	::= { physical-disk-item 2 }
pd-RG	OBJECT-TYPE
	SYNTAX	DisplayString
	ACCESS 	read-only
	STATUS	mandatory
	DESCRIPTION
		"RG name"
	::= { physical-disk-item 3 }
pd-status	OBJECT-TYPE
	SYNTAX	DisplayString
	ACCESS 	read-only
	STATUS	mandatory
	DESCRIPTION
		"status"
	::= { physical-disk-item 4 }
pd-status-health	OBJECT-TYPE
	SYNTAX	DisplayString
	ACCESS 	read-only
	STATUS	mandatory
	DESCRIPTION
		"health"
	::= { physical-disk-item 5 }
pd-status-usage	OBJECT-TYPE
	SYNTAX	DisplayString
	ACCESS 	read-only
	STATUS	mandatory
	DESCRIPTION
		"usage"
	::= { physical-disk-item 6 }
pd-vendor	OBJECT-TYPE
	SYNTAX	DisplayString
	ACCESS 	read-only
	STATUS	mandatory
	DESCRIPTION
		"vendor"
	::= { physical-disk-item 7 }
pd-serial	OBJECT-TYPE
	SYNTAX	DisplayString
	ACCESS 	read-only
	STATUS	mandatory
	DESCRIPTION
		"serial number"
	::= { physical-disk-item 8 }
pd-type	OBJECT-TYPE
	SYNTAX	DisplayString
	ACCESS 	read-only
	STATUS	mandatory
	DESCRIPTION
		"type"
	::= { physical-disk-item 9 }
pd-write-cache	OBJECT-TYPE
	SYNTAX	DisplayString
	ACCESS 	read-only
	STATUS	mandatory
	DESCRIPTION
		"write cache enable"
	::= { physical-disk-item 10 }
pd-standby	OBJECT-TYPE
	SYNTAX	DisplayString
	ACCESS 	read-only
	STATUS	mandatory
	DESCRIPTION
		"standby timeout"
	::= { physical-disk-item 11 }
pd-readahead	OBJECT-TYPE
	SYNTAX	DisplayString
	ACCESS 	read-only
	STATUS	mandatory
	DESCRIPTION
		"readahead enable"
	::= { physical-disk-item 12 }
pd-command-queuing	OBJECT-TYPE
	SYNTAX	DisplayString
	ACCESS 	read-only
	STATUS	mandatory
	DESCRIPTION
		"command queuing"
	::= { physical-disk-item 13 }
pd-performance  OBJECT-TYPE
  SYNTAX  DisplayString
  ACCESS  read-only
  STATUS  mandatory
  DESCRIPTION
    "PD performance (size:KB)"
  ::= { physical-disk-item 14 }


-- raid/volume-config/raid-group
raid-group OBJECT-TYPE
	SYNTAX 	SEQUENCE OF RG-ITEM
	ACCESS	not-accessible
	STATUS	mandatory
	DESCRIPTION
		"RAID group list"
	::= { volume-config 2 }
raid-group-item 	OBJECT-TYPE
	SYNTAX	RG-ITEM
	ACCESS	not-accessible
	STATUS	mandatory
	DESCRIPTION
		"RAID group item"
	INDEX	{ rg-name }
	::= { raid-group 1 }
RG-ITEM ::= SEQUENCE {
	rg-name DisplayString,
	rg-total DisplayString,
	rg-free DisplayString,
	rg-pd DisplayString,
	rg-vd DisplayString,
	rg-status DisplayString,
	rg-health DisplayString,
	rg-raid DisplayString,
	rg-owner DisplayString,
	rg-powner DisplayString
}
rg-name	OBJECT-TYPE
	SYNTAX	DisplayString
	ACCESS 	read-only
	STATUS	mandatory
	DESCRIPTION
		"name"
	::= { raid-group-item 1 }
rg-total	OBJECT-TYPE
	SYNTAX	DisplayString
	ACCESS 	read-only
	STATUS	mandatory
	DESCRIPTION
		"total size in GB"
	::= { raid-group-item 2 }
rg-free	OBJECT-TYPE
	SYNTAX	DisplayString
	ACCESS 	read-only
	STATUS	mandatory
	DESCRIPTION
		"free size in GB"
	::= { raid-group-item 3 }
rg-pd	OBJECT-TYPE
	SYNTAX	DisplayString
	ACCESS 	read-only
	STATUS	mandatory
	DESCRIPTION
		"number of PD"
	::= { raid-group-item 4 }
rg-vd	OBJECT-TYPE
	SYNTAX	DisplayString
	ACCESS 	read-only
	STATUS	mandatory
	DESCRIPTION
		"number of VD"
	::= { raid-group-item 5 }
rg-status	OBJECT-TYPE
	SYNTAX	DisplayString
	ACCESS 	read-only
	STATUS	mandatory
	DESCRIPTION
		"status"
	::= { raid-group-item 6 }
rg-health	OBJECT-TYPE
	SYNTAX	DisplayString
	ACCESS 	read-only
	STATUS	mandatory
	DESCRIPTION
		"health"
	::= { raid-group-item 7 }
rg-raid	OBJECT-TYPE
	SYNTAX	DisplayString
	ACCESS 	read-only
	STATUS	mandatory
	DESCRIPTION
		"RAID"
	::= { raid-group-item 8 }
rg-owner	OBJECT-TYPE
	SYNTAX	DisplayString
	ACCESS 	read-only
	STATUS	mandatory
	DESCRIPTION
		"current owner"
	::= { raid-group-item 9 }
rg-powner	OBJECT-TYPE
	SYNTAX	DisplayString
	ACCESS 	read-only
	STATUS	mandatory
	DESCRIPTION
		"preferred owner"
	::= { raid-group-item 10 }


-- raid/volume-config/virtual disk
virtual-disk OBJECT-TYPE
	SYNTAX 	SEQUENCE OF VD-ITEM
	ACCESS	not-accessible
	STATUS	mandatory
	DESCRIPTION
		"virtual disk list"
	::= { volume-config 3 }
virtual-disk-item 	OBJECT-TYPE
	SYNTAX	VD-ITEM
	ACCESS	not-accessible
	STATUS	mandatory
	DESCRIPTION
		"virtual disk item"
	INDEX	{ vd-name }
	::= { virtual-disk 1 }
VD-ITEM ::= SEQUENCE {
	vd-name DisplayString,
	vd-size DisplayString,
	vd-right DisplayString,
	vd-priority DisplayString,
	vd-bgrate DisplayString,
	vd-status DisplayString,
	vd-health DisplayString,
	vd-progress DisplayString,
	vd-raid DisplayString,
	vd-lun DisplayString,
	vd-snapshot-space DisplayString,
	vd-snapshot DisplayString,
	vd-rg DisplayString
}
vd-name	OBJECT-TYPE
	SYNTAX	DisplayString
	ACCESS 	read-only
	STATUS	mandatory
	DESCRIPTION
		"name"
	::= { virtual-disk-item 1 }
vd-size	OBJECT-TYPE
	SYNTAX	DisplayString
	ACCESS 	read-only
	STATUS	mandatory
	DESCRIPTION
		"size in GB"
	::= { virtual-disk-item 2 }
vd-right	OBJECT-TYPE
	SYNTAX	DisplayString
	ACCESS 	read-only
	STATUS	mandatory
	DESCRIPTION
		"access right"
	::= { virtual-disk-item 3 }
vd-priority	OBJECT-TYPE
	SYNTAX	DisplayString
	ACCESS 	read-only
	STATUS	mandatory
	DESCRIPTION
		"access priority"
	::= { virtual-disk-item 4 }
vd-bgrate	OBJECT-TYPE
	SYNTAX	DisplayString
	ACCESS 	read-only
	STATUS	mandatory
	DESCRIPTION
		"background IO rate"
	::= { virtual-disk-item 5 }
vd-status	OBJECT-TYPE
	SYNTAX	DisplayString
	ACCESS 	read-only
	STATUS	mandatory
	DESCRIPTION
		"status"
	::= { virtual-disk-item 6 }
vd-health	OBJECT-TYPE
	SYNTAX	DisplayString
	ACCESS 	read-only
	STATUS	mandatory
	DESCRIPTION
		"health"
	::= { virtual-disk-item 7 }
vd-progress	OBJECT-TYPE
	SYNTAX	DisplayString
	ACCESS 	read-only
	STATUS	mandatory
	DESCRIPTION
		"background IO progress"
	::= { virtual-disk-item 8 }
vd-raid	OBJECT-TYPE
	SYNTAX	DisplayString
	ACCESS 	read-only
	STATUS	mandatory
	DESCRIPTION
		"RAID"
	::= { virtual-disk-item 9 }
vd-lun	OBJECT-TYPE
	SYNTAX	DisplayString
	ACCESS 	read-only
	STATUS	mandatory
	DESCRIPTION
		"#LUN"
	::= { virtual-disk-item 10 }
vd-snapshot-space	OBJECT-TYPE
	SYNTAX	DisplayString
	ACCESS 	read-only
	STATUS	mandatory
	DESCRIPTION
		"Snapshot space in MB"
	::= { virtual-disk-item 11 }
vd-snapshot	OBJECT-TYPE
	SYNTAX	DisplayString
	ACCESS 	read-only
	STATUS	mandatory
	DESCRIPTION
		"Snapshot"
	::= { virtual-disk-item 12 }
vd-rg	OBJECT-TYPE
	SYNTAX	DisplayString
	ACCESS 	read-only
	STATUS	mandatory
	DESCRIPTION
		"RG"
	::= { virtual-disk-item 13 }


-- raid/volume-config/Logical Unit
logical-unit OBJECT-TYPE
	SYNTAX 	SEQUENCE OF LUN-ITEM
	ACCESS	not-accessible
	STATUS	mandatory
	DESCRIPTION
		"logical unit list"
	::= { volume-config 4 }
logical-unit-item 	OBJECT-TYPE
	SYNTAX	LUN-ITEM
	ACCESS	not-accessible
	STATUS	mandatory
	DESCRIPTION
		"logical unit item"
	INDEX	{ lun-index }
	::= { logical-unit 1 }
LUN-ITEM ::= SEQUENCE {
	lun-index DisplayString,
	lun-host DisplayString,
	lun-target DisplayString,
	lun-num DisplayString,
	lun-permission DisplayString,
	lun-vd DisplayString
}
lun-index	OBJECT-TYPE
	SYNTAX	DisplayString
	ACCESS 	read-only
	STATUS	mandatory
	DESCRIPTION
		"index"
	::= { logical-unit-item 1 }
lun-host	OBJECT-TYPE
	SYNTAX	DisplayString
	ACCESS 	read-only
	STATUS	mandatory
	DESCRIPTION
		"host"
	::= { logical-unit-item 2 }
lun-target	OBJECT-TYPE
	SYNTAX	DisplayString
	ACCESS 	read-only
	STATUS	mandatory
	DESCRIPTION
		"target"
	::= { logical-unit-item 3 }
lun-num	OBJECT-TYPE
	SYNTAX	DisplayString
	ACCESS 	read-only
	STATUS	mandatory
	DESCRIPTION
		"LUN"
	::= { logical-unit-item 4 }
lun-permission	OBJECT-TYPE
	SYNTAX	DisplayString
	ACCESS 	read-only
	STATUS	mandatory
	DESCRIPTION
		"permission"
	::= { logical-unit-item 5 }
lun-vd	OBJECT-TYPE
	SYNTAX	DisplayString
	ACCESS 	read-only
	STATUS	mandatory
	DESCRIPTION
		"VD"
	::= { logical-unit-item 6 }
-- raid/enclosure-management/hardware-monitor
hardware-monitor OBJECT-TYPE
	SYNTAX 	SEQUENCE OF EMS-ITEM
	ACCESS	not-accessible
	STATUS	mandatory
	DESCRIPTION
		"hardware monitor list"
	::= { enclosure-management 2 }
hardware-monitor-item 	OBJECT-TYPE
	SYNTAX	EMS-ITEM
	ACCESS	not-accessible
	STATUS	mandatory
	DESCRIPTION
		"hardware monitor item"
	INDEX	{ ems-item }
	::= { hardware-monitor 1 }
EMS-ITEM ::= SEQUENCE {
				ems-loc DisplayString,
				ems-type DisplayString,
				ems-item DisplayString,
				ems-value DisplayString,
				ems-status DisplayString	}
ems-loc	OBJECT-TYPE
	SYNTAX	DisplayString
	ACCESS 	read-only
	STATUS	mandatory
	DESCRIPTION
		"Location"
	::= { hardware-monitor-item 1 }
ems-type	OBJECT-TYPE
	SYNTAX	DisplayString
	ACCESS 	read-only
	STATUS	mandatory
	DESCRIPTION
		"Item type"
	::= { hardware-monitor-item 2 }
ems-item	OBJECT-TYPE
	SYNTAX	DisplayString
	ACCESS 	read-only
	STATUS	mandatory
	DESCRIPTION
		"item"
	::= { hardware-monitor-item 3 }
ems-value	OBJECT-TYPE
	SYNTAX	DisplayString
	ACCESS 	read-only
	STATUS	mandatory
	DESCRIPTION
		"Value"
	::= { hardware-monitor-item 4 }
ems-status	OBJECT-TYPE
	SYNTAX	DisplayString
	ACCESS 	read-only
	STATUS	mandatory
	DESCRIPTION
		"Status"
	::= { hardware-monitor-item 5 }
-- raid/enclosure-management/SES
ems-ses	OBJECT-TYPE
	SYNTAX	DisplayString
	ACCESS 	read-only
	STATUS	mandatory
	DESCRIPTION
		"SES/SAFTE enable. enable or NA."
	::= { enclosure-management-ses 1 }
-- raid/enclosure-management/SMART
hdd-smart OBJECT-TYPE
	SYNTAX 	SEQUENCE OF SMART-ITEM
	ACCESS	not-accessible
	STATUS	mandatory
	DESCRIPTION
		"S.M.A.R.T. list"
	::= { enclosure-management 4 }
hdd-smart-item 	OBJECT-TYPE
	SYNTAX	SMART-ITEM
	ACCESS	not-accessible
	STATUS	mandatory
	DESCRIPTION
		"HDD S.M.A.R.T. item"
	INDEX	{ hdd-loc }
	::= { hdd-smart 1 }
SMART-ITEM ::= SEQUENCE {
				hdd-loc DisplayString,
				hdd-type DisplayString,
				hdd-readerror DisplayString,
				hdd-temperature DisplayString	}
hdd-loc	OBJECT-TYPE
	SYNTAX	DisplayString
	ACCESS 	read-only
	STATUS	mandatory
	DESCRIPTION
		"Location"
	::= { hdd-smart-item 1 }
hdd-type	OBJECT-TYPE
	SYNTAX	DisplayString
	ACCESS 	read-only
	STATUS	mandatory
	DESCRIPTION
		"Disk type"
	::= { hdd-smart-item 2 }
hdd-readerror	OBJECT-TYPE
	SYNTAX	DisplayString
	ACCESS 	read-only
	STATUS	mandatory
	DESCRIPTION
		"Read error"
	::= { hdd-smart-item 3 }
hdd-temperature	OBJECT-TYPE
	SYNTAX	DisplayString
	ACCESS 	read-only
	STATUS	mandatory
	DESCRIPTION
		"HDD temperature in celsius"
	::= { hdd-smart-item 4 }
-- raid/maintenance
-- raid/maintenance/info
maintenance-info-cpu	OBJECT-TYPE
	SYNTAX	DisplayString
	ACCESS 	read-only
	STATUS	mandatory
	DESCRIPTION
		"CPU type"
	::= { maintenance-info 1 }
maintenance-info-mem	OBJECT-TYPE
	SYNTAX	DisplayString
	ACCESS 	read-only
	STATUS	mandatory
	DESCRIPTION
		"System memory"
	::= { maintenance-info 2 }
maintenance-info-fw	OBJECT-TYPE
	SYNTAX	DisplayString
	ACCESS 	read-only
	STATUS	mandatory
	DESCRIPTION
		"Firmware version"
	::= { maintenance-info 3 }
maintenance-info-serial-no	OBJECT-TYPE
	SYNTAX	DisplayString
	ACCESS 	read-only
	STATUS	mandatory
	DESCRIPTION
		"Serial number"
	::= { maintenance-info 4 }
maintenance-info-backplane-id	OBJECT-TYPE
	SYNTAX	DisplayString
	ACCESS 	read-only
	STATUS	mandatory
	DESCRIPTION
		"Backplane ID"
	::= { maintenance-info 5 }
maintenance-info-status	OBJECT-TYPE
	SYNTAX	DisplayString
	ACCESS 	read-only
	STATUS	mandatory
	DESCRIPTION
		"Status"
	::= { maintenance-info 6 }
maintenance-info-message	OBJECT-TYPE
	SYNTAX	DisplayString
	ACCESS 	read-only
	STATUS	mandatory
	DESCRIPTION
		"Error message"
	::= { maintenance-info 7 }
-- raid/iscsi-config
-- raid/iscsi-config/iscsi-config-nic
iscsi-config-nic OBJECT-TYPE
	SYNTAX 	SEQUENCE OF ISCSINIC-ITEM
	ACCESS	not-accessible
	STATUS	mandatory
	DESCRIPTION
		"iSCSI NIC list"
	::= { iscsi-config 1 }
iscsi-nic-item 	OBJECT-TYPE
	SYNTAX	ISCSINIC-ITEM
	ACCESS	not-accessible
	STATUS	mandatory
	DESCRIPTION
		"iSCSI NIC item"
	INDEX	{ iscsi-nic-id }
	::= { iscsi-config-nic 1 }
ISCSINIC-ITEM ::= SEQUENCE {
	iscsi-nic-id DisplayString,
	iscsi-nic-ctrl DisplayString,
	iscsi-nic-ip DisplayString,
	iscsi-nic-mask DisplayString,
	iscsi-nic-gw DisplayString,
	iscsi-nic-jumbo DisplayString,
	iscsi-nic-mac DisplayString,
  iscsi-nic-performance DisplayString
}
iscsi-nic-id	OBJECT-TYPE
	SYNTAX	DisplayString
	ACCESS 	read-only
	STATUS	mandatory
	DESCRIPTION
		"iSCSI NIC ID, start from 0"
	::= { iscsi-nic-item 1 }
iscsi-nic-ctrl	OBJECT-TYPE
	SYNTAX	DisplayString
	ACCESS 	read-only
	STATUS	mandatory
	DESCRIPTION
		"On which controller. CTR1 or CTR2"
	::= { iscsi-nic-item 2 }
iscsi-nic-ip	OBJECT-TYPE
	SYNTAX	DisplayString
	ACCESS 	read-only
	STATUS	mandatory
	DESCRIPTION
		"IP address"
	::= { iscsi-nic-item 3 }
iscsi-nic-mask	OBJECT-TYPE
	SYNTAX	DisplayString
	ACCESS 	read-only
	STATUS	mandatory
	DESCRIPTION
		"Subnet mask"
	::= { iscsi-nic-item 4 }
iscsi-nic-gw	OBJECT-TYPE
	SYNTAX	DisplayString
	ACCESS 	read-only
	STATUS	mandatory
	DESCRIPTION
		"Gateway"
	::= { iscsi-nic-item 5 }
iscsi-nic-jumbo	OBJECT-TYPE
	SYNTAX	DisplayString
	ACCESS 	read-only
	STATUS	mandatory
	DESCRIPTION
		"Jumbo flame"
	::= { iscsi-nic-item 6 }
iscsi-nic-mac	OBJECT-TYPE
	SYNTAX	DisplayString
	ACCESS 	read-only
	STATUS	mandatory
	DESCRIPTION
		"MAC address"
	::= { iscsi-nic-item 7 }
iscsi-nic-performance OBJECT-TYPE
  SYNTAX  DisplayString
  ACCESS  read-only
  STATUS  mandatory
  DESCRIPTION
    "Performance"
  ::= { iscsi-nic-item 8 }
-- raid/iscsi-config/iscsi-config-entity
iscsi-config-entity-item	OBJECT-TYPE
	SYNTAX	DisplayString
	ACCESS 	read-only
	STATUS	mandatory
	DESCRIPTION
		"iSCSI entity"
	::= { iscsi-config-entity 1 }
iscsi-config-isns-item	OBJECT-TYPE
	SYNTAX	DisplayString
	ACCESS 	read-only
	STATUS	mandatory
	DESCRIPTION
		"iSNS server"
	::= { iscsi-config-entity 2 }
-- raid/iscsi-config/iscsi-config-node
iscsi-config-node OBJECT-TYPE
	SYNTAX 	SEQUENCE OF ISCSINODE-ITEM
	ACCESS	not-accessible
	STATUS	mandatory
	DESCRIPTION
		"iSCSI target node list"
	::= { iscsi-config 3 }
iscsi-node-item 	OBJECT-TYPE
	SYNTAX	ISCSINODE-ITEM
	ACCESS	not-accessible
	STATUS	mandatory
	DESCRIPTION
		"iSCSI node item"
	INDEX	{ iscsi-node-id }
	::= { iscsi-config-node 1 }
ISCSINODE-ITEM ::= SEQUENCE {
	iscsi-node-id DisplayString,
	iscsi-node-ctrl DisplayString,
	iscsi-node-auth DisplayString,
	iscsi-node-name DisplayString,
	iscsi-node-portal DisplayString
}
iscsi-node-id	OBJECT-TYPE
	SYNTAX	DisplayString
	ACCESS 	read-only
	STATUS	mandatory
	DESCRIPTION
		"iSCSI node ID, start from 0"
	::= { iscsi-node-item 1 }
iscsi-node-ctrl	OBJECT-TYPE
	SYNTAX	DisplayString
	ACCESS 	read-only
	STATUS	mandatory
	DESCRIPTION
		"On which controller. CTR1 or CTR2"
	::= { iscsi-node-item 2 }
iscsi-node-auth	OBJECT-TYPE
	SYNTAX	DisplayString
	ACCESS 	read-only
	STATUS	mandatory
	DESCRIPTION
		"CHAP enable or not"
	::= { iscsi-node-item 3 }
iscsi-node-name	OBJECT-TYPE
	SYNTAX	DisplayString
	ACCESS 	read-only
	STATUS	mandatory
	DESCRIPTION
		"iSCSI target node name"
	::= { iscsi-node-item 4 }
iscsi-node-portal	OBJECT-TYPE
	SYNTAX	DisplayString
	ACCESS 	read-only
	STATUS	mandatory
	DESCRIPTION
		"iSCSI portal"
	::= { iscsi-node-item 5 }


-- definition of trap
-- raid/event
event		OBJECT IDENTIFIER ::= { raid	8000 }
eventString OBJECT-TYPE
	SYNTAX	DisplayString
	ACCESS	not-accessible
	STATUS	mandatory
	DESCRIPTION
		"event message"
	::= { raid 8001 }

-- SNMP traps


evtid-test	TRAP-TYPE
	ENTERPRISE	event
	VARIABLES	{ eventString }
	DESCRIPTION
		"%s"
	::= 0
evtid-ecc-single	TRAP-TYPE
	ENTERPRISE	event
	VARIABLES	{ eventString }
	DESCRIPTION
		"%s"
	::= 1
evtid-ecc-multiple	TRAP-TYPE
	ENTERPRISE	event
	VARIABLES	{ eventString }
	DESCRIPTION
		"%s"
	::= 2
evtid-ecc-dimm	TRAP-TYPE
	ENTERPRISE	event
	VARIABLES	{ eventString }
	DESCRIPTION
		"%s"
	::= 3
evtid-ecc-none	TRAP-TYPE
	ENTERPRISE	event
	VARIABLES	{ eventString }
	DESCRIPTION
		"%s"
	::= 4
evtid-bbm-start-syncing	TRAP-TYPE
	ENTERPRISE	event
	VARIABLES	{ eventString }
	DESCRIPTION
		"%s"
	::= 5
evtid-bbm-stop-syncing	TRAP-TYPE
	ENTERPRISE	event
	VARIABLES	{ eventString }
	DESCRIPTION
		"%s"
	::= 6
evtid-bbm-installed	TRAP-TYPE
	ENTERPRISE	event
	VARIABLES	{ eventString }
	DESCRIPTION
		"%s"
	::= 7
evtid-bbm-sts-good	TRAP-TYPE
	ENTERPRISE	event
	VARIABLES	{ eventString }
	DESCRIPTION
		"%s"
	::= 8
evtid-bbm-sts-charging	TRAP-TYPE
	ENTERPRISE	event
	VARIABLES	{ eventString }
	DESCRIPTION
		"%s"
	::= 9
evtid-bbm-sts-fail	TRAP-TYPE
	ENTERPRISE	event
	VARIABLES	{ eventString }
	DESCRIPTION
		"%s"
	::= 10
evtid-bbm-enabled	TRAP-TYPE
	ENTERPRISE	event
	VARIABLES	{ eventString }
	DESCRIPTION
		"%s"
	::= 11
evtid-bbm-ml-enabled	TRAP-TYPE
	ENTERPRISE	event
	VARIABLES	{ eventString }
	DESCRIPTION
		"%s"
	::= 12
evtid-bbm-ml-disabled	TRAP-TYPE
	ENTERPRISE	event
	VARIABLES	{ eventString }
	DESCRIPTION
		"%s"
	::= 13
evtid-bbm-inserted	TRAP-TYPE
	ENTERPRISE	event
	VARIABLES	{ eventString }
	DESCRIPTION
		"%s"
	::= 14
evtid-bbm-removed	TRAP-TYPE
	ENTERPRISE	event
	VARIABLES	{ eventString }
	DESCRIPTION
		"%s"
	::= 15
evtid-bbm-warning-temperature	TRAP-TYPE
	ENTERPRISE	event
	VARIABLES	{ eventString }
	DESCRIPTION
		"%s"
	::= 16
evtid-bbm-memory-over-limit	TRAP-TYPE
	ENTERPRISE	event
	VARIABLES	{ eventString }
	DESCRIPTION
		"%s"
	::= 17
evtid-c2f-flash-too-small	TRAP-TYPE
	ENTERPRISE	event
	VARIABLES	{ eventString }
	DESCRIPTION
		"%s"
	::= 18
evtid-qcopy-job-info	TRAP-TYPE
	ENTERPRISE	event
	VARIABLES	{ eventString }
	DESCRIPTION
		"%s"
	::= 19
evtid-qcopy-job-restart	TRAP-TYPE
	ENTERPRISE	event
	VARIABLES	{ eventString }
	DESCRIPTION
		"%s"
	::= 20
evtid-qcopy-job-fail	TRAP-TYPE
	ENTERPRISE	event
	VARIABLES	{ eventString }
	DESCRIPTION
		"%s"
	::= 21
evtid-qcopy-job-abort	TRAP-TYPE
	ENTERPRISE	event
	VARIABLES	{ eventString }
	DESCRIPTION
		"%s"
	::= 22
evtid-qcopy-job-abort-lba-size	TRAP-TYPE
	ENTERPRISE	event
	VARIABLES	{ eventString }
	DESCRIPTION
		"%s"
	::= 23
evtid-scsi-busreset	TRAP-TYPE
	ENTERPRISE	event
	VARIABLES	{ eventString }
	DESCRIPTION
		"%s"
	::= 24
evtid-scsi-host-error	TRAP-TYPE
	ENTERPRISE	event
	VARIABLES	{ eventString }
	DESCRIPTION
		"%s"
	::= 25
evtid-sas-port-reply-error	TRAP-TYPE
	ENTERPRISE	event
	VARIABLES	{ eventString }
	DESCRIPTION
		"%s"
	::= 26
evtid-sas-unknown-port-reply-error	TRAP-TYPE
	ENTERPRISE	event
	VARIABLES	{ eventString }
	DESCRIPTION
		"%s"
	::= 27
evtid-fc-port-reply-error	TRAP-TYPE
	ENTERPRISE	event
	VARIABLES	{ eventString }
	DESCRIPTION
		"%s"
	::= 28
evtid-fc-unknown-port-reply-error	TRAP-TYPE
	ENTERPRISE	event
	VARIABLES	{ eventString }
	DESCRIPTION
		"%s"
	::= 29
evtid-fc-port-linkup	TRAP-TYPE
	ENTERPRISE	event
	VARIABLES	{ eventString }
	DESCRIPTION
		"%s"
	::= 30
evtid-fc-port-linkdown	TRAP-TYPE
	ENTERPRISE	event
	VARIABLES	{ eventString }
	DESCRIPTION
		"%s"
	::= 31
evtid-fc-link-up-at-slot	TRAP-TYPE
	ENTERPRISE	event
	VARIABLES	{ eventString }
	DESCRIPTION
		"%s"
	::= 32
evtid-fc-link-down-at-slot	TRAP-TYPE
	ENTERPRISE	event
	VARIABLES	{ eventString }
	DESCRIPTION
		"%s"
	::= 33
evtid-fc-login	TRAP-TYPE
	ENTERPRISE	event
	VARIABLES	{ eventString }
	DESCRIPTION
		"%s"
	::= 34
evtid-fc-logout	TRAP-TYPE
	ENTERPRISE	event
	VARIABLES	{ eventString }
	DESCRIPTION
		"%s"
	::= 35
evtid-iscsi-login-accepted	TRAP-TYPE
	ENTERPRISE	event
	VARIABLES	{ eventString }
	DESCRIPTION
		"%s"
	::= 36
evtid-iscsi-login-rejected	TRAP-TYPE
	ENTERPRISE	event
	VARIABLES	{ eventString }
	DESCRIPTION
		"%s"
	::= 37
evtid-iscsi-logout-recvd	TRAP-TYPE
	ENTERPRISE	event
	VARIABLES	{ eventString }
	DESCRIPTION
		"%s"
	::= 38
evtid-iscsi-link-up	TRAP-TYPE
	ENTERPRISE	event
	VARIABLES	{ eventString }
	DESCRIPTION
		"%s"
	::= 39
evtid-iscsi-link-up-at-slot	TRAP-TYPE
	ENTERPRISE	event
	VARIABLES	{ eventString }
	DESCRIPTION
		"%s"
	::= 40
evtid-iscsi-link-down	TRAP-TYPE
	ENTERPRISE	event
	VARIABLES	{ eventString }
	DESCRIPTION
		"%s"
	::= 41
evtid-iscsi-link-down-at-slot	TRAP-TYPE
	ENTERPRISE	event
	VARIABLES	{ eventString }
	DESCRIPTION
		"%s"
	::= 42
evtid-sata-enable-dev-fail	TRAP-TYPE
	ENTERPRISE	event
	VARIABLES	{ eventString }
	DESCRIPTION
		"%s"
	::= 43
evtid-sata-edma-mem-fail	TRAP-TYPE
	ENTERPRISE	event
	VARIABLES	{ eventString }
	DESCRIPTION
		"%s"
	::= 44
evtid-sata-remap-mem-fail	TRAP-TYPE
	ENTERPRISE	event
	VARIABLES	{ eventString }
	DESCRIPTION
		"%s"
	::= 45
evtid-sata-prd-mem-fail	TRAP-TYPE
	ENTERPRISE	event
	VARIABLES	{ eventString }
	DESCRIPTION
		"%s"
	::= 46
evtid-sata-revision-id-fail	TRAP-TYPE
	ENTERPRISE	event
	VARIABLES	{ eventString }
	DESCRIPTION
		"%s"
	::= 47
evtid-sata-set-reg-fail	TRAP-TYPE
	ENTERPRISE	event
	VARIABLES	{ eventString }
	DESCRIPTION
		"%s"
	::= 48
evtid-sata-init-fail	TRAP-TYPE
	ENTERPRISE	event
	VARIABLES	{ eventString }
	DESCRIPTION
		"%s"
	::= 49
evtid-sata-diag-fail	TRAP-TYPE
	ENTERPRISE	event
	VARIABLES	{ eventString }
	DESCRIPTION
		"%s"
	::= 50
evtid-mode-id-fail	TRAP-TYPE
	ENTERPRISE	event
	VARIABLES	{ eventString }
	DESCRIPTION
		"%s"
	::= 51
evtid-sata-chip-count-error	TRAP-TYPE
	ENTERPRISE	event
	VARIABLES	{ eventString }
	DESCRIPTION
		"%s"
	::= 52
evtid-disk-upgrade-started	TRAP-TYPE
	ENTERPRISE	event
	VARIABLES	{ eventString }
	DESCRIPTION
		"%s"
	::= 53
evtid-disk-upgrade-finished	TRAP-TYPE
	ENTERPRISE	event
	VARIABLES	{ eventString }
	DESCRIPTION
		"%s"
	::= 54
evtid-disk-upgrade-failed	TRAP-TYPE
	ENTERPRISE	event
	VARIABLES	{ eventString }
	DESCRIPTION
		"%s"
	::= 55
evtid-jbod-disk-upgrade-started	TRAP-TYPE
	ENTERPRISE	event
	VARIABLES	{ eventString }
	DESCRIPTION
		"%s"
	::= 56
evtid-jbod-disk-upgrade-finished	TRAP-TYPE
	ENTERPRISE	event
	VARIABLES	{ eventString }
	DESCRIPTION
		"%s"
	::= 57
evtid-jbod-disk-upgrade-failed	TRAP-TYPE
	ENTERPRISE	event
	VARIABLES	{ eventString }
	DESCRIPTION
		"%s"
	::= 58
evtid-pd-inserted	TRAP-TYPE
	ENTERPRISE	event
	VARIABLES	{ eventString }
	DESCRIPTION
		"%s"
	::= 59
evtid-pd-removed	TRAP-TYPE
	ENTERPRISE	event
	VARIABLES	{ eventString }
	DESCRIPTION
		"%s"
	::= 60
evtid-hdd-readerr	TRAP-TYPE
	ENTERPRISE	event
	VARIABLES	{ eventString }
	DESCRIPTION
		"%s"
	::= 61
evtid-hdd-writeerr	TRAP-TYPE
	ENTERPRISE	event
	VARIABLES	{ eventString }
	DESCRIPTION
		"%s"
	::= 62
evtid-hdd-error	TRAP-TYPE
	ENTERPRISE	event
	VARIABLES	{ eventString }
	DESCRIPTION
		"%s"
	::= 63
evtid-hdd-io-timeout	TRAP-TYPE
	ENTERPRISE	event
	VARIABLES	{ eventString }
	DESCRIPTION
		"%s"
	::= 64
evtid-hdd-temp-warning	TRAP-TYPE
	ENTERPRISE	event
	VARIABLES	{ eventString }
	DESCRIPTION
		"%s"
	::= 65
evtid-hdd-spinup-failed	TRAP-TYPE
	ENTERPRISE	event
	VARIABLES	{ eventString }
	DESCRIPTION
		"%s"
	::= 66
evtid-pd-inserted-w-serial	TRAP-TYPE
	ENTERPRISE	event
	VARIABLES	{ eventString }
	DESCRIPTION
		"%s"
	::= 67
evtid-pd-removed-w-serial	TRAP-TYPE
	ENTERPRISE	event
	VARIABLES	{ eventString }
	DESCRIPTION
		"%s"
	::= 68
evtid-hdd-spinup-failed-w-serial	TRAP-TYPE
	ENTERPRISE	event
	VARIABLES	{ eventString }
	DESCRIPTION
		"%s"
	::= 69
evtid-hdd-error-w-serial	TRAP-TYPE
	ENTERPRISE	event
	VARIABLES	{ eventString }
	DESCRIPTION
		"%s"
	::= 70
evtid-hdd-io-timeout-w-serial	TRAP-TYPE
	ENTERPRISE	event
	VARIABLES	{ eventString }
	DESCRIPTION
		"%s"
	::= 71
evtid-env-power-install	TRAP-TYPE
	ENTERPRISE	event
	VARIABLES	{ eventString }
	DESCRIPTION
		"%s"
	::= 72
evtid-env-power-absent	TRAP-TYPE
	ENTERPRISE	event
	VARIABLES	{ eventString }
	DESCRIPTION
		"%s"
	::= 73
evtid-env-power-rst	TRAP-TYPE
	ENTERPRISE	event
	VARIABLES	{ eventString }
	DESCRIPTION
		"%s"
	::= 74
evtid-env-power-fail	TRAP-TYPE
	ENTERPRISE	event
	VARIABLES	{ eventString }
	DESCRIPTION
		"%s"
	::= 75
evtid-env-power-sig-vol	TRAP-TYPE
	ENTERPRISE	event
	VARIABLES	{ eventString }
	DESCRIPTION
		"%s"
	::= 76
evtid-env-fan-rst	TRAP-TYPE
	ENTERPRISE	event
	VARIABLES	{ eventString }
	DESCRIPTION
		"%s"
	::= 77
evtid-env-fan-fail	TRAP-TYPE
	ENTERPRISE	event
	VARIABLES	{ eventString }
	DESCRIPTION
		"%s"
	::= 78
evtid-env-fan-pr	TRAP-TYPE
	ENTERPRISE	event
	VARIABLES	{ eventString }
	DESCRIPTION
		"%s"
	::= 79
evtid-env-fan-not-pr	TRAP-TYPE
	ENTERPRISE	event
	VARIABLES	{ eventString }
	DESCRIPTION
		"%s"
	::= 80
evtid-env-fan-over-speed	TRAP-TYPE
	ENTERPRISE	event
	VARIABLES	{ eventString }
	DESCRIPTION
		"%s"
	::= 81
evtid-env-fan-track	TRAP-TYPE
	ENTERPRISE	event
	VARIABLES	{ eventString }
	DESCRIPTION
		"%s"
	::= 82
evtid-env-therm-level-1	TRAP-TYPE
	ENTERPRISE	event
	VARIABLES	{ eventString }
	DESCRIPTION
		"%s"
	::= 83
evtid-env-therm-level-2	TRAP-TYPE
	ENTERPRISE	event
	VARIABLES	{ eventString }
	DESCRIPTION
		"%s"
	::= 84
evtid-env-therm-level-2-shutdown	TRAP-TYPE
	ENTERPRISE	event
	VARIABLES	{ eventString }
	DESCRIPTION
		"%s"
	::= 85
evtid-env-therm-l2-ctr-shutdown	TRAP-TYPE
	ENTERPRISE	event
	VARIABLES	{ eventString }
	DESCRIPTION
		"%s"
	::= 86
evtid-env-therm-ignore-value	TRAP-TYPE
	ENTERPRISE	event
	VARIABLES	{ eventString }
	DESCRIPTION
		"%s"
	::= 87
evtid-env-therm-track	TRAP-TYPE
	ENTERPRISE	event
	VARIABLES	{ eventString }
	DESCRIPTION
		"%s"
	::= 88
evtid-env-vol-level-1	TRAP-TYPE
	ENTERPRISE	event
	VARIABLES	{ eventString }
	DESCRIPTION
		"%s"
	::= 89
evtid-env-vol-level-2	TRAP-TYPE
	ENTERPRISE	event
	VARIABLES	{ eventString }
	DESCRIPTION
		"%s"
	::= 90
evtid-env-vol-level-2-shutdown	TRAP-TYPE
	ENTERPRISE	event
	VARIABLES	{ eventString }
	DESCRIPTION
		"%s"
	::= 91
evtid-env-vol-l2-ctr-shutdown	TRAP-TYPE
	ENTERPRISE	event
	VARIABLES	{ eventString }
	DESCRIPTION
		"%s"
	::= 92
evtid-env-vol-level-3	TRAP-TYPE
	ENTERPRISE	event
	VARIABLES	{ eventString }
	DESCRIPTION
		"%s"
	::= 93
evtid-env-vol-track	TRAP-TYPE
	ENTERPRISE	event
	VARIABLES	{ eventString }
	DESCRIPTION
		"%s"
	::= 94
evtid-env-ups-ok	TRAP-TYPE
	ENTERPRISE	event
	VARIABLES	{ eventString }
	DESCRIPTION
		"%s"
	::= 95
evtid-env-ups-fail	TRAP-TYPE
	ENTERPRISE	event
	VARIABLES	{ eventString }
	DESCRIPTION
		"%s"
	::= 96
evtid-env-ups-ac-loss	TRAP-TYPE
	ENTERPRISE	event
	VARIABLES	{ eventString }
	DESCRIPTION
		"%s"
	::= 97
evtid-env-ups-power-low	TRAP-TYPE
	ENTERPRISE	event
	VARIABLES	{ eventString }
	DESCRIPTION
		"%s"
	::= 98
evtid-smart-polling-disabled	TRAP-TYPE
	ENTERPRISE	event
	VARIABLES	{ eventString }
	DESCRIPTION
		"%s"
	::= 99
evtid-smart-polling-inquiry	TRAP-TYPE
	ENTERPRISE	event
	VARIABLES	{ eventString }
	DESCRIPTION
		"%s"
	::= 100
evtid-smart-polling-action	TRAP-TYPE
	ENTERPRISE	event
	VARIABLES	{ eventString }
	DESCRIPTION
		"%s"
	::= 101
evtid-smart-tec	TRAP-TYPE
	ENTERPRISE	event
	VARIABLES	{ eventString }
	DESCRIPTION
		"%s"
	::= 102
evtid-smart-fail	TRAP-TYPE
	ENTERPRISE	event
	VARIABLES	{ eventString }
	DESCRIPTION
		"%s"
	::= 103
evtid-rb-failover	TRAP-TYPE
	ENTERPRISE	event
	VARIABLES	{ eventString }
	DESCRIPTION
		"%s"
	::= 104
evtid-wdt-shutdown	TRAP-TYPE
	ENTERPRISE	event
	VARIABLES	{ eventString }
	DESCRIPTION
		"%s"
	::= 105
evtid-wdt-reset	TRAP-TYPE
	ENTERPRISE	event
	VARIABLES	{ eventString }
	DESCRIPTION
		"%s"
	::= 106
evtid-smart-endurance	TRAP-TYPE
	ENTERPRISE	event
	VARIABLES	{ eventString }
	DESCRIPTION
		"%s"
	::= 107
evtid-expansion-smart-endurance	TRAP-TYPE
	ENTERPRISE	event
	VARIABLES	{ eventString }
	DESCRIPTION
		"%s"
	::= 108
evtid-qslife-set-alert-noact	TRAP-TYPE
	ENTERPRISE	event
	VARIABLES	{ eventString }
	DESCRIPTION
		"%s"
	::= 109
evtid-qslife-set-alert	TRAP-TYPE
	ENTERPRISE	event
	VARIABLES	{ eventString }
	DESCRIPTION
		"%s"
	::= 110
evtid-disk-latency-warn	TRAP-TYPE
	ENTERPRISE	event
	VARIABLES	{ eventString }
	DESCRIPTION
		"%s"
	::= 111
evtid-expansion-disk-latency-warn	TRAP-TYPE
	ENTERPRISE	event
	VARIABLES	{ eventString }
	DESCRIPTION
		"%s"
	::= 112
evtid-jbod-pd-inserted	TRAP-TYPE
	ENTERPRISE	event
	VARIABLES	{ eventString }
	DESCRIPTION
		"%s"
	::= 113
evtid-jbod-pd-removed	TRAP-TYPE
	ENTERPRISE	event
	VARIABLES	{ eventString }
	DESCRIPTION
		"%s"
	::= 114
evtid-jbod-hdd-readerr	TRAP-TYPE
	ENTERPRISE	event
	VARIABLES	{ eventString }
	DESCRIPTION
		"%s"
	::= 115
evtid-jbod-hdd-writeerr	TRAP-TYPE
	ENTERPRISE	event
	VARIABLES	{ eventString }
	DESCRIPTION
		"%s"
	::= 116
evtid-jbod-hdd-error	TRAP-TYPE
	ENTERPRISE	event
	VARIABLES	{ eventString }
	DESCRIPTION
		"%s"
	::= 117
evtid-jbod-hdd-io-timeout	TRAP-TYPE
	ENTERPRISE	event
	VARIABLES	{ eventString }
	DESCRIPTION
		"%s"
	::= 118
evtid-jbod-hdd-spinup-failed	TRAP-TYPE
	ENTERPRISE	event
	VARIABLES	{ eventString }
	DESCRIPTION
		"%s"
	::= 119
evtid-jbod-unsupported-inserted	TRAP-TYPE
	ENTERPRISE	event
	VARIABLES	{ eventString }
	DESCRIPTION
		"%s"
	::= 120
evtid-jbod-unsupported-removed	TRAP-TYPE
	ENTERPRISE	event
	VARIABLES	{ eventString }
	DESCRIPTION
		"%s"
	::= 121
evtid-jbod-pd-inserted-w-serial	TRAP-TYPE
	ENTERPRISE	event
	VARIABLES	{ eventString }
	DESCRIPTION
		"%s"
	::= 122
evtid-jbod-pd-removed-w-serial	TRAP-TYPE
	ENTERPRISE	event
	VARIABLES	{ eventString }
	DESCRIPTION
		"%s"
	::= 123
evtid-jbod-hdd-error-w-serial	TRAP-TYPE
	ENTERPRISE	event
	VARIABLES	{ eventString }
	DESCRIPTION
		"%s"
	::= 124
evtid-jbod-hdd-io-timeout-w-serial	TRAP-TYPE
	ENTERPRISE	event
	VARIABLES	{ eventString }
	DESCRIPTION
		"%s"
	::= 125
evtid-jbod-hdd-spinup-failed-w-serial	TRAP-TYPE
	ENTERPRISE	event
	VARIABLES	{ eventString }
	DESCRIPTION
		"%s"
	::= 126
evtid-jbod-inserted	TRAP-TYPE
	ENTERPRISE	event
	VARIABLES	{ eventString }
	DESCRIPTION
		"%s"
	::= 127
evtid-jbod-removed	TRAP-TYPE
	ENTERPRISE	event
	VARIABLES	{ eventString }
	DESCRIPTION
		"%s"
	::= 128
evtid-jbod-ctr-inserted	TRAP-TYPE
	ENTERPRISE	event
	VARIABLES	{ eventString }
	DESCRIPTION
		"%s"
	::= 129
evtid-jbod-ctr-removed	TRAP-TYPE
	ENTERPRISE	event
	VARIABLES	{ eventString }
	DESCRIPTION
		"%s"
	::= 130
evtid-jbod-smart-tec	TRAP-TYPE
	ENTERPRISE	event
	VARIABLES	{ eventString }
	DESCRIPTION
		"%s"
	::= 131
evtid-jbod-smart-fail	TRAP-TYPE
	ENTERPRISE	event
	VARIABLES	{ eventString }
	DESCRIPTION
		"%s"
	::= 132
evtid-jbod-degraded	TRAP-TYPE
	ENTERPRISE	event
	VARIABLES	{ eventString }
	DESCRIPTION
		"%s"
	::= 133
evtid-jbod-recovered	TRAP-TYPE
	ENTERPRISE	event
	VARIABLES	{ eventString }
	DESCRIPTION
		"%s"
	::= 134
evtid-enc-ps-fail	TRAP-TYPE
	ENTERPRISE	event
	VARIABLES	{ eventString }
	DESCRIPTION
		"%s"
	::= 135
evtid-enc-ps-normal	TRAP-TYPE
	ENTERPRISE	event
	VARIABLES	{ eventString }
	DESCRIPTION
		"%s"
	::= 136
evtid-enc-fan-fail	TRAP-TYPE
	ENTERPRISE	event
	VARIABLES	{ eventString }
	DESCRIPTION
		"%s"
	::= 137
evtid-enc-fan-normal	TRAP-TYPE
	ENTERPRISE	event
	VARIABLES	{ eventString }
	DESCRIPTION
		"%s"
	::= 138
evtid-enc-volt-warn-ov	TRAP-TYPE
	ENTERPRISE	event
	VARIABLES	{ eventString }
	DESCRIPTION
		"%s"
	::= 139
evtid-enc-volt-warn-uv	TRAP-TYPE
	ENTERPRISE	event
	VARIABLES	{ eventString }
	DESCRIPTION
		"%s"
	::= 140
evtid-enc-volt-crit-ov	TRAP-TYPE
	ENTERPRISE	event
	VARIABLES	{ eventString }
	DESCRIPTION
		"%s"
	::= 141
evtid-enc-volt-crit-uv	TRAP-TYPE
	ENTERPRISE	event
	VARIABLES	{ eventString }
	DESCRIPTION
		"%s"
	::= 142
evtid-enc-volt-recovery	TRAP-TYPE
	ENTERPRISE	event
	VARIABLES	{ eventString }
	DESCRIPTION
		"%s"
	::= 143
evtid-enc-therm-warn-ot	TRAP-TYPE
	ENTERPRISE	event
	VARIABLES	{ eventString }
	DESCRIPTION
		"%s"
	::= 144
evtid-enc-therm-warn-ut	TRAP-TYPE
	ENTERPRISE	event
	VARIABLES	{ eventString }
	DESCRIPTION
		"%s"
	::= 145
evtid-enc-therm-fail-ot	TRAP-TYPE
	ENTERPRISE	event
	VARIABLES	{ eventString }
	DESCRIPTION
		"%s"
	::= 146
evtid-enc-therm-fail-ut	TRAP-TYPE
	ENTERPRISE	event
	VARIABLES	{ eventString }
	DESCRIPTION
		"%s"
	::= 147
evtid-enc-therm-recovery	TRAP-TYPE
	ENTERPRISE	event
	VARIABLES	{ eventString }
	DESCRIPTION
		"%s"
	::= 148
evtid-lvm-vg-create-ok	TRAP-TYPE
	ENTERPRISE	event
	VARIABLES	{ eventString }
	DESCRIPTION
		"%s"
	::= 149
evtid-lvm-vg-create-ok-smi	TRAP-TYPE
	ENTERPRISE	event
	VARIABLES	{ eventString }
	DESCRIPTION
		"%s"
	::= 150
evtid-lvm-vg-create-fail	TRAP-TYPE
	ENTERPRISE	event
	VARIABLES	{ eventString }
	DESCRIPTION
		"%s"
	::= 151
evtid-lvm-vg-delete	TRAP-TYPE
	ENTERPRISE	event
	VARIABLES	{ eventString }
	DESCRIPTION
		"%s"
	::= 152
evtid-lvm-vg-delete-smi	TRAP-TYPE
	ENTERPRISE	event
	VARIABLES	{ eventString }
	DESCRIPTION
		"%s"
	::= 153
evtid-lvm-vg-rename	TRAP-TYPE
	ENTERPRISE	event
	VARIABLES	{ eventString }
	DESCRIPTION
		"%s"
	::= 154
evtid-lvm-udv-create-ok	TRAP-TYPE
	ENTERPRISE	event
	VARIABLES	{ eventString }
	DESCRIPTION
		"%s"
	::= 155
evtid-lvm-udv-create-ok-smi	TRAP-TYPE
	ENTERPRISE	event
	VARIABLES	{ eventString }
	DESCRIPTION
		"%s"
	::= 156
evtid-lvm-udv-create-fail	TRAP-TYPE
	ENTERPRISE	event
	VARIABLES	{ eventString }
	DESCRIPTION
		"%s"
	::= 157
evtid-lvm-udv-delete	TRAP-TYPE
	ENTERPRISE	event
	VARIABLES	{ eventString }
	DESCRIPTION
		"%s"
	::= 158
evtid-lvm-udv-delete-smi	TRAP-TYPE
	ENTERPRISE	event
	VARIABLES	{ eventString }
	DESCRIPTION
		"%s"
	::= 159
evtid-lvm-udv-rename	TRAP-TYPE
	ENTERPRISE	event
	VARIABLES	{ eventString }
	DESCRIPTION
		"%s"
	::= 160
evtid-lvm-udv-readonly	TRAP-TYPE
	ENTERPRISE	event
	VARIABLES	{ eventString }
	DESCRIPTION
		"%s"
	::= 161
evtid-lvm-udv-wr-back	TRAP-TYPE
	ENTERPRISE	event
	VARIABLES	{ eventString }
	DESCRIPTION
		"%s"
	::= 162
evtid-lvm-udv-wr-thru	TRAP-TYPE
	ENTERPRISE	event
	VARIABLES	{ eventString }
	DESCRIPTION
		"%s"
	::= 163
evtid-lvm-udv-extend	TRAP-TYPE
	ENTERPRISE	event
	VARIABLES	{ eventString }
	DESCRIPTION
		"%s"
	::= 164
evtid-lvm-udv-attach-lun-ok	TRAP-TYPE
	ENTERPRISE	event
	VARIABLES	{ eventString }
	DESCRIPTION
		"%s"
	::= 165
evtid-lvm-udv-attach-lun-fail	TRAP-TYPE
	ENTERPRISE	event
	VARIABLES	{ eventString }
	DESCRIPTION
		"%s"
	::= 166
evtid-lvm-udv-detach-lun-ok	TRAP-TYPE
	ENTERPRISE	event
	VARIABLES	{ eventString }
	DESCRIPTION
		"%s"
	::= 167
evtid-lvm-udv-detach-lun-fail	TRAP-TYPE
	ENTERPRISE	event
	VARIABLES	{ eventString }
	DESCRIPTION
		"%s"
	::= 168
evtid-lvm-udv-init-started	TRAP-TYPE
	ENTERPRISE	event
	VARIABLES	{ eventString }
	DESCRIPTION
		"%s"
	::= 169
evtid-lvm-udv-init-finished	TRAP-TYPE
	ENTERPRISE	event
	VARIABLES	{ eventString }
	DESCRIPTION
		"%s"
	::= 170
evtid-lvm-udv-init-failed	TRAP-TYPE
	ENTERPRISE	event
	VARIABLES	{ eventString }
	DESCRIPTION
		"%s"
	::= 171
evtid-lvm-udv-rebuild-started	TRAP-TYPE
	ENTERPRISE	event
	VARIABLES	{ eventString }
	DESCRIPTION
		"%s"
	::= 172
evtid-lvm-udv-rebuild-finished	TRAP-TYPE
	ENTERPRISE	event
	VARIABLES	{ eventString }
	DESCRIPTION
		"%s"
	::= 173
evtid-lvm-udv-rebuild-failed	TRAP-TYPE
	ENTERPRISE	event
	VARIABLES	{ eventString }
	DESCRIPTION
		"%s"
	::= 174
evtid-lvm-udv-migrate-started	TRAP-TYPE
	ENTERPRISE	event
	VARIABLES	{ eventString }
	DESCRIPTION
		"%s"
	::= 175
evtid-lvm-udv-migrate-finished	TRAP-TYPE
	ENTERPRISE	event
	VARIABLES	{ eventString }
	DESCRIPTION
		"%s"
	::= 176
evtid-lvm-udv-migrate-failed	TRAP-TYPE
	ENTERPRISE	event
	VARIABLES	{ eventString }
	DESCRIPTION
		"%s"
	::= 177
evtid-lvm-udv-scrub-started	TRAP-TYPE
	ENTERPRISE	event
	VARIABLES	{ eventString }
	DESCRIPTION
		"%s"
	::= 178
evtid-lvm-udv-scrub-finished	TRAP-TYPE
	ENTERPRISE	event
	VARIABLES	{ eventString }
	DESCRIPTION
		"%s"
	::= 179
evtid-lvm-vg-migrate-started	TRAP-TYPE
	ENTERPRISE	event
	VARIABLES	{ eventString }
	DESCRIPTION
		"%s"
	::= 180
evtid-lvm-vg-migrate-finished	TRAP-TYPE
	ENTERPRISE	event
	VARIABLES	{ eventString }
	DESCRIPTION
		"%s"
	::= 181
evtid-lvm-vg-move-started	TRAP-TYPE
	ENTERPRISE	event
	VARIABLES	{ eventString }
	DESCRIPTION
		"%s"
	::= 182
evtid-lvm-vg-move-finished	TRAP-TYPE
	ENTERPRISE	event
	VARIABLES	{ eventString }
	DESCRIPTION
		"%s"
	::= 183
evtid-lvm-udv-move-started	TRAP-TYPE
	ENTERPRISE	event
	VARIABLES	{ eventString }
	DESCRIPTION
		"%s"
	::= 184
evtid-lvm-udv-move-finished	TRAP-TYPE
	ENTERPRISE	event
	VARIABLES	{ eventString }
	DESCRIPTION
		"%s"
	::= 185
evtid-lvm-udv-move-failed	TRAP-TYPE
	ENTERPRISE	event
	VARIABLES	{ eventString }
	DESCRIPTION
		"%s"
	::= 186
evtid-lvm-udv-attach-lun	TRAP-TYPE
	ENTERPRISE	event
	VARIABLES	{ eventString }
	DESCRIPTION
		"%s"
	::= 187
evtid-lvm-udv-detach-lun	TRAP-TYPE
	ENTERPRISE	event
	VARIABLES	{ eventString }
	DESCRIPTION
		"%s"
	::= 188
evtid-lvm-vg-activated	TRAP-TYPE
	ENTERPRISE	event
	VARIABLES	{ eventString }
	DESCRIPTION
		"%s"
	::= 189
evtid-lvm-vg-deactivated	TRAP-TYPE
	ENTERPRISE	event
	VARIABLES	{ eventString }
	DESCRIPTION
		"%s"
	::= 190
evtid-lvm-udv-rewrite-started	TRAP-TYPE
	ENTERPRISE	event
	VARIABLES	{ eventString }
	DESCRIPTION
		"%s"
	::= 191
evtid-lvm-udv-rewrite-finished	TRAP-TYPE
	ENTERPRISE	event
	VARIABLES	{ eventString }
	DESCRIPTION
		"%s"
	::= 192
evtid-lvm-udv-rewrite-failed	TRAP-TYPE
	ENTERPRISE	event
	VARIABLES	{ eventString }
	DESCRIPTION
		"%s"
	::= 193
evtid-lvm-vg-degraded	TRAP-TYPE
	ENTERPRISE	event
	VARIABLES	{ eventString }
	DESCRIPTION
		"%s"
	::= 194
evtid-lvm-udv-degraded	TRAP-TYPE
	ENTERPRISE	event
	VARIABLES	{ eventString }
	DESCRIPTION
		"%s"
	::= 195
evtid-lvm-vg-failed	TRAP-TYPE
	ENTERPRISE	event
	VARIABLES	{ eventString }
	DESCRIPTION
		"%s"
	::= 196
evtid-lvm-udv-failed	TRAP-TYPE
	ENTERPRISE	event
	VARIABLES	{ eventString }
	DESCRIPTION
		"%s"
	::= 197
evtid-lvm-udv-io-fault	TRAP-TYPE
	ENTERPRISE	event
	VARIABLES	{ eventString }
	DESCRIPTION
		"%s"
	::= 198
evtid-lvm-recoverable-read-error	TRAP-TYPE
	ENTERPRISE	event
	VARIABLES	{ eventString }
	DESCRIPTION
		"%s"
	::= 199
evtid-lvm-recover-rd-much-error	TRAP-TYPE
	ENTERPRISE	event
	VARIABLES	{ eventString }
	DESCRIPTION
		"%s"
	::= 200
evtid-lvm-recoverable-write-error	TRAP-TYPE
	ENTERPRISE	event
	VARIABLES	{ eventString }
	DESCRIPTION
		"%s"
	::= 201
evtid-lvm-unrecoverable-read-error	TRAP-TYPE
	ENTERPRISE	event
	VARIABLES	{ eventString }
	DESCRIPTION
		"%s"
	::= 202
evtid-lvm-unrecover-rd-much-error	TRAP-TYPE
	ENTERPRISE	event
	VARIABLES	{ eventString }
	DESCRIPTION
		"%s"
	::= 203
evtid-lvm-unrecoverable-write-error	TRAP-TYPE
	ENTERPRISE	event
	VARIABLES	{ eventString }
	DESCRIPTION
		"%s"
	::= 204
evtid-lvm-config-read-fail	TRAP-TYPE
	ENTERPRISE	event
	VARIABLES	{ eventString }
	DESCRIPTION
		"%s"
	::= 205
evtid-lvm-config-write-fail	TRAP-TYPE
	ENTERPRISE	event
	VARIABLES	{ eventString }
	DESCRIPTION
		"%s"
	::= 206
evtid-lvm-cv-boot-error-adjust-global	TRAP-TYPE
	ENTERPRISE	event
	VARIABLES	{ eventString }
	DESCRIPTION
		"%s"
	::= 207
evtid-lvm-cv-boot-global	TRAP-TYPE
	ENTERPRISE	event
	VARIABLES	{ eventString }
	DESCRIPTION
		"%s"
	::= 208
evtid-lvm-cv-boot-error-create-global	TRAP-TYPE
	ENTERPRISE	event
	VARIABLES	{ eventString }
	DESCRIPTION
		"%s"
	::= 209
evtid-lvm-pd-dedicated-spare	TRAP-TYPE
	ENTERPRISE	event
	VARIABLES	{ eventString }
	DESCRIPTION
		"%s"
	::= 210
evtid-lvm-pd-global-spare	TRAP-TYPE
	ENTERPRISE	event
	VARIABLES	{ eventString }
	DESCRIPTION
		"%s"
	::= 211
evtid-lvm-pd-read-error	TRAP-TYPE
	ENTERPRISE	event
	VARIABLES	{ eventString }
	DESCRIPTION
		"%s"
	::= 212
evtid-lvm-pd-write-error	TRAP-TYPE
	ENTERPRISE	event
	VARIABLES	{ eventString }
	DESCRIPTION
		"%s"
	::= 213
evtid-lvm-snap-mem	TRAP-TYPE
	ENTERPRISE	event
	VARIABLES	{ eventString }
	DESCRIPTION
		"%s"
	::= 214
evtid-lvm-snap-space-overflow	TRAP-TYPE
	ENTERPRISE	event
	VARIABLES	{ eventString }
	DESCRIPTION
		"%s"
	::= 215
evtid-lvm-snap-threshold	TRAP-TYPE
	ENTERPRISE	event
	VARIABLES	{ eventString }
	DESCRIPTION
		"%s"
	::= 216
evtid-lvm-snap-delete	TRAP-TYPE
	ENTERPRISE	event
	VARIABLES	{ eventString }
	DESCRIPTION
		"%s"
	::= 217
evtid-lvm-snap-auto-delete	TRAP-TYPE
	ENTERPRISE	event
	VARIABLES	{ eventString }
	DESCRIPTION
		"%s"
	::= 218
evtid-lvm-snap-take	TRAP-TYPE
	ENTERPRISE	event
	VARIABLES	{ eventString }
	DESCRIPTION
		"%s"
	::= 219
evtid-lvm-snap-set-space	TRAP-TYPE
	ENTERPRISE	event
	VARIABLES	{ eventString }
	DESCRIPTION
		"%s"
	::= 220
evtid-lvm-snap-rollback-started	TRAP-TYPE
	ENTERPRISE	event
	VARIABLES	{ eventString }
	DESCRIPTION
		"%s"
	::= 221
evtid-lvm-snap-rollback-finished	TRAP-TYPE
	ENTERPRISE	event
	VARIABLES	{ eventString }
	DESCRIPTION
		"%s"
	::= 222
evtid-lvm-snap-quota-reached	TRAP-TYPE
	ENTERPRISE	event
	VARIABLES	{ eventString }
	DESCRIPTION
		"%s"
	::= 223
evtid-lvm-scrub-wrong-parity	TRAP-TYPE
	ENTERPRISE	event
	VARIABLES	{ eventString }
	DESCRIPTION
		"%s"
	::= 224
evtid-lvm-scrub-data-recovered	TRAP-TYPE
	ENTERPRISE	event
	VARIABLES	{ eventString }
	DESCRIPTION
		"%s"
	::= 225
evtid-lvm-pd-freed	TRAP-TYPE
	ENTERPRISE	event
	VARIABLES	{ eventString }
	DESCRIPTION
		"%s"
	::= 226
evtid-jbod-lvm-pd-freed	TRAP-TYPE
	ENTERPRISE	event
	VARIABLES	{ eventString }
	DESCRIPTION
		"%s"
	::= 227
evtid-lvm-vg-imported	TRAP-TYPE
	ENTERPRISE	event
	VARIABLES	{ eventString }
	DESCRIPTION
		"%s"
	::= 228
evtid-lvm-vg-restored	TRAP-TYPE
	ENTERPRISE	event
	VARIABLES	{ eventString }
	DESCRIPTION
		"%s"
	::= 229
evtid-lvm-udv-restored	TRAP-TYPE
	ENTERPRISE	event
	VARIABLES	{ eventString }
	DESCRIPTION
		"%s"
	::= 230
evtid-jbod-lvm-pd-dedicated-spare	TRAP-TYPE
	ENTERPRISE	event
	VARIABLES	{ eventString }
	DESCRIPTION
		"%s"
	::= 231
evtid-jbod-lvm-pd-global-spare	TRAP-TYPE
	ENTERPRISE	event
	VARIABLES	{ eventString }
	DESCRIPTION
		"%s"
	::= 232
evtid-jbod-lvm-config-read-fail	TRAP-TYPE
	ENTERPRISE	event
	VARIABLES	{ eventString }
	DESCRIPTION
		"%s"
	::= 233
evtid-jbod-lvm-config-write-fail	TRAP-TYPE
	ENTERPRISE	event
	VARIABLES	{ eventString }
	DESCRIPTION
		"%s"
	::= 234
evtid-jbod-lvm-pd-read-error	TRAP-TYPE
	ENTERPRISE	event
	VARIABLES	{ eventString }
	DESCRIPTION
		"%s"
	::= 235
evtid-jbod-lvm-pd-write-error	TRAP-TYPE
	ENTERPRISE	event
	VARIABLES	{ eventString }
	DESCRIPTION
		"%s"
	::= 236
evtid-lvm-rg-owner-changed	TRAP-TYPE
	ENTERPRISE	event
	VARIABLES	{ eventString }
	DESCRIPTION
		"%s"
	::= 237
evtid-lvm-force-ctr-write-thru	TRAP-TYPE
	ENTERPRISE	event
	VARIABLES	{ eventString }
	DESCRIPTION
		"%s"
	::= 238
evtid-lvm-restore-ctr-cache-mode	TRAP-TYPE
	ENTERPRISE	event
	VARIABLES	{ eventString }
	DESCRIPTION
		"%s"
	::= 239
evtid-lvm-failover-completed	TRAP-TYPE
	ENTERPRISE	event
	VARIABLES	{ eventString }
	DESCRIPTION
		"%s"
	::= 240
evtid-lvm-failback-completed	TRAP-TYPE
	ENTERPRISE	event
	VARIABLES	{ eventString }
	DESCRIPTION
		"%s"
	::= 241
evtid-lvm-pd-scrub-started	TRAP-TYPE
	ENTERPRISE	event
	VARIABLES	{ eventString }
	DESCRIPTION
		"%s"
	::= 242
evtid-lvm-pd-scrub-completed	TRAP-TYPE
	ENTERPRISE	event
	VARIABLES	{ eventString }
	DESCRIPTION
		"%s"
	::= 243
evtid-jbod-lvm-pd-scrub-started	TRAP-TYPE
	ENTERPRISE	event
	VARIABLES	{ eventString }
	DESCRIPTION
		"%s"
	::= 244
evtid-jbod-lvm-pd-scrub-completed	TRAP-TYPE
	ENTERPRISE	event
	VARIABLES	{ eventString }
	DESCRIPTION
		"%s"
	::= 245
evtid-lvm-pd-check-started	TRAP-TYPE
	ENTERPRISE	event
	VARIABLES	{ eventString }
	DESCRIPTION
		"%s"
	::= 246
evtid-lvm-pd-check-completed	TRAP-TYPE
	ENTERPRISE	event
	VARIABLES	{ eventString }
	DESCRIPTION
		"%s"
	::= 247
evtid-lvm-pd-check-term	TRAP-TYPE
	ENTERPRISE	event
	VARIABLES	{ eventString }
	DESCRIPTION
		"%s"
	::= 248
evtid-jbod-lvm-pd-check-started	TRAP-TYPE
	ENTERPRISE	event
	VARIABLES	{ eventString }
	DESCRIPTION
		"%s"
	::= 249
evtid-jbod-lvm-pd-check-completed	TRAP-TYPE
	ENTERPRISE	event
	VARIABLES	{ eventString }
	DESCRIPTION
		"%s"
	::= 250
evtid-jbod-lvm-pd-check-term	TRAP-TYPE
	ENTERPRISE	event
	VARIABLES	{ eventString }
	DESCRIPTION
		"%s"
	::= 251
evtid-lvm-scrub-recovered-data	TRAP-TYPE
	ENTERPRISE	event
	VARIABLES	{ eventString }
	DESCRIPTION
		"%s"
	::= 252
evtid-lvm-scrub-parity-recovered	TRAP-TYPE
	ENTERPRISE	event
	VARIABLES	{ eventString }
	DESCRIPTION
		"%s"
	::= 253
evtid-lvm-udv-scrub-aborted	TRAP-TYPE
	ENTERPRISE	event
	VARIABLES	{ eventString }
	DESCRIPTION
		"%s"
	::= 254
evtid-lvm-snap-clear-space	TRAP-TYPE
	ENTERPRISE	event
	VARIABLES	{ eventString }
	DESCRIPTION
		"%s"
	::= 255
evtid-lvm-large-vg-created	TRAP-TYPE
	ENTERPRISE	event
	VARIABLES	{ eventString }
	DESCRIPTION
		"%s"
	::= 256
evtid-lvm-weak-vg-created	TRAP-TYPE
	ENTERPRISE	event
	VARIABLES	{ eventString }
	DESCRIPTION
		"%s"
	::= 257
evtid-lvm-vg-size-shrunk	TRAP-TYPE
	ENTERPRISE	event
	VARIABLES	{ eventString }
	DESCRIPTION
		"%s"
	::= 258
evtid-lvm-udv-clone-started	TRAP-TYPE
	ENTERPRISE	event
	VARIABLES	{ eventString }
	DESCRIPTION
		"%s"
	::= 259
evtid-lvm-udv-clone-finished	TRAP-TYPE
	ENTERPRISE	event
	VARIABLES	{ eventString }
	DESCRIPTION
		"%s"
	::= 260
evtid-lvm-udv-clone-failed	TRAP-TYPE
	ENTERPRISE	event
	VARIABLES	{ eventString }
	DESCRIPTION
		"%s"
	::= 261
evtid-lvm-udv-clone-aborted	TRAP-TYPE
	ENTERPRISE	event
	VARIABLES	{ eventString }
	DESCRIPTION
		"%s"
	::= 262
evtid-lvm-udv-replicate-started	TRAP-TYPE
	ENTERPRISE	event
	VARIABLES	{ eventString }
	DESCRIPTION
		"%s"
	::= 263
evtid-lvm-udv-replicate-finished	TRAP-TYPE
	ENTERPRISE	event
	VARIABLES	{ eventString }
	DESCRIPTION
		"%s"
	::= 264
evtid-lvm-udv-replicate-failed	TRAP-TYPE
	ENTERPRISE	event
	VARIABLES	{ eventString }
	DESCRIPTION
		"%s"
	::= 265
evtid-lvm-udv-replicate-aborted	TRAP-TYPE
	ENTERPRISE	event
	VARIABLES	{ eventString }
	DESCRIPTION
		"%s"
	::= 266
evtid-lvm-udv-erase-finished	TRAP-TYPE
	ENTERPRISE	event
	VARIABLES	{ eventString }
	DESCRIPTION
		"%s"
	::= 267
evtid-lvm-udv-erase-failed	TRAP-TYPE
	ENTERPRISE	event
	VARIABLES	{ eventString }
	DESCRIPTION
		"%s"
	::= 268
evtid-lvm-udv-erase-started	TRAP-TYPE
	ENTERPRISE	event
	VARIABLES	{ eventString }
	DESCRIPTION
		"%s"
	::= 269
evtid-lvm-udv-set-as-replica	TRAP-TYPE
	ENTERPRISE	event
	VARIABLES	{ eventString }
	DESCRIPTION
		"%s"
	::= 270
evtid-lvm-udv-set-as-raid	TRAP-TYPE
	ENTERPRISE	event
	VARIABLES	{ eventString }
	DESCRIPTION
		"%s"
	::= 271
evtid-lvm-udv-replica-set	TRAP-TYPE
	ENTERPRISE	event
	VARIABLES	{ eventString }
	DESCRIPTION
		"%s"
	::= 272
evtid-lvm-udv-replica-reset	TRAP-TYPE
	ENTERPRISE	event
	VARIABLES	{ eventString }
	DESCRIPTION
		"%s"
	::= 273
evtid-lvm-udv-clone-set	TRAP-TYPE
	ENTERPRISE	event
	VARIABLES	{ eventString }
	DESCRIPTION
		"%s"
	::= 274
evtid-lvm-udv-clone-reset	TRAP-TYPE
	ENTERPRISE	event
	VARIABLES	{ eventString }
	DESCRIPTION
		"%s"
	::= 275
evtid-lvm-sync-replica-set	TRAP-TYPE
	ENTERPRISE	event
	VARIABLES	{ eventString }
	DESCRIPTION
		"%s"
	::= 276
evtid-lvm-sync-replica-reset	TRAP-TYPE
	ENTERPRISE	event
	VARIABLES	{ eventString }
	DESCRIPTION
		"%s"
	::= 277
evtid-lvm-qrep-full-start	TRAP-TYPE
	ENTERPRISE	event
	VARIABLES	{ eventString }
	DESCRIPTION
		"%s"
	::= 278
evtid-lvm-qrep-full-done	TRAP-TYPE
	ENTERPRISE	event
	VARIABLES	{ eventString }
	DESCRIPTION
		"%s"
	::= 279
evtid-lvm-qrep-sync-fail-1	TRAP-TYPE
	ENTERPRISE	event
	VARIABLES	{ eventString }
	DESCRIPTION
		"%s"
	::= 280
evtid-lvm-qrep-sync-fail-2	TRAP-TYPE
	ENTERPRISE	event
	VARIABLES	{ eventString }
	DESCRIPTION
		"%s"
	::= 281
evtid-lvm-src-replicate-started	TRAP-TYPE
	ENTERPRISE	event
	VARIABLES	{ eventString }
	DESCRIPTION
		"%s"
	::= 282
evtid-lvm-src-replicate-finished	TRAP-TYPE
	ENTERPRISE	event
	VARIABLES	{ eventString }
	DESCRIPTION
		"%s"
	::= 283
evtid-lvm-src-replicate-failed	TRAP-TYPE
	ENTERPRISE	event
	VARIABLES	{ eventString }
	DESCRIPTION
		"%s"
	::= 284
evtid-lvm-src-replicate-aborted	TRAP-TYPE
	ENTERPRISE	event
	VARIABLES	{ eventString }
	DESCRIPTION
		"%s"
	::= 285
evtid-lvm-vg-disk-missing	TRAP-TYPE
	ENTERPRISE	event
	VARIABLES	{ eventString }
	DESCRIPTION
		"%s"
	::= 286
evtid-lvm-pd-rps-started-l2l	TRAP-TYPE
	ENTERPRISE	event
	VARIABLES	{ eventString }
	DESCRIPTION
		"%s"
	::= 287
evtid-lvm-pd-rps-started-l2f	TRAP-TYPE
	ENTERPRISE	event
	VARIABLES	{ eventString }
	DESCRIPTION
		"%s"
	::= 288
evtid-lvm-pd-rps-started-f2l	TRAP-TYPE
	ENTERPRISE	event
	VARIABLES	{ eventString }
	DESCRIPTION
		"%s"
	::= 289
evtid-lvm-pd-rps-started-f2f	TRAP-TYPE
	ENTERPRISE	event
	VARIABLES	{ eventString }
	DESCRIPTION
		"%s"
	::= 290
evtid-lvm-pd-rps-finished-l2l	TRAP-TYPE
	ENTERPRISE	event
	VARIABLES	{ eventString }
	DESCRIPTION
		"%s"
	::= 291
evtid-lvm-pd-rps-finished-l2f	TRAP-TYPE
	ENTERPRISE	event
	VARIABLES	{ eventString }
	DESCRIPTION
		"%s"
	::= 292
evtid-lvm-pd-rps-finished-f2l	TRAP-TYPE
	ENTERPRISE	event
	VARIABLES	{ eventString }
	DESCRIPTION
		"%s"
	::= 293
evtid-lvm-pd-rps-finished-f2f	TRAP-TYPE
	ENTERPRISE	event
	VARIABLES	{ eventString }
	DESCRIPTION
		"%s"
	::= 294
evtid-lvm-pd-rps-failed-l2l	TRAP-TYPE
	ENTERPRISE	event
	VARIABLES	{ eventString }
	DESCRIPTION
		"%s"
	::= 295
evtid-lvm-pd-rps-failed-l2f	TRAP-TYPE
	ENTERPRISE	event
	VARIABLES	{ eventString }
	DESCRIPTION
		"%s"
	::= 296
evtid-lvm-pd-rps-failed-f2l	TRAP-TYPE
	ENTERPRISE	event
	VARIABLES	{ eventString }
	DESCRIPTION
		"%s"
	::= 297
evtid-lvm-pd-rps-failed-f2f	TRAP-TYPE
	ENTERPRISE	event
	VARIABLES	{ eventString }
	DESCRIPTION
		"%s"
	::= 298
evtid-lvm-l-pd-udv-rewr-fault	TRAP-TYPE
	ENTERPRISE	event
	VARIABLES	{ eventString }
	DESCRIPTION
		"%s"
	::= 299
evtid-lvm-f-pd-udv-rewr-fault	TRAP-TYPE
	ENTERPRISE	event
	VARIABLES	{ eventString }
	DESCRIPTION
		"%s"
	::= 300
evtid-lvm-l-pd-io-retry-fault	TRAP-TYPE
	ENTERPRISE	event
	VARIABLES	{ eventString }
	DESCRIPTION
		"%s"
	::= 301
evtid-lvm-f-pd-io-retry-fault	TRAP-TYPE
	ENTERPRISE	event
	VARIABLES	{ eventString }
	DESCRIPTION
		"%s"
	::= 302
evtid-lvm-pd-substitute-l2l	TRAP-TYPE
	ENTERPRISE	event
	VARIABLES	{ eventString }
	DESCRIPTION
		"%s"
	::= 303
evtid-lvm-pd-substitute-l2f	TRAP-TYPE
	ENTERPRISE	event
	VARIABLES	{ eventString }
	DESCRIPTION
		"%s"
	::= 304
evtid-lvm-pd-substitute-f2l	TRAP-TYPE
	ENTERPRISE	event
	VARIABLES	{ eventString }
	DESCRIPTION
		"%s"
	::= 305
evtid-lvm-pd-substitute-f2f	TRAP-TYPE
	ENTERPRISE	event
	VARIABLES	{ eventString }
	DESCRIPTION
		"%s"
	::= 306
evtid-lvm-vg-threshold-hit	TRAP-TYPE
	ENTERPRISE	event
	VARIABLES	{ eventString }
	DESCRIPTION
		"%s"
	::= 307
evtid-lvm-raid-set-created	TRAP-TYPE
	ENTERPRISE	event
	VARIABLES	{ eventString }
	DESCRIPTION
		"%s"
	::= 308
evtid-lvm-raid-set-deleted	TRAP-TYPE
	ENTERPRISE	event
	VARIABLES	{ eventString }
	DESCRIPTION
		"%s"
	::= 309
evtid-lvm-udv-reclaim-started	TRAP-TYPE
	ENTERPRISE	event
	VARIABLES	{ eventString }
	DESCRIPTION
		"%s"
	::= 310
evtid-lvm-udv-reclaim-completed	TRAP-TYPE
	ENTERPRISE	event
	VARIABLES	{ eventString }
	DESCRIPTION
		"%s"
	::= 311
evtid-lvm-udv-reclaim-aborted	TRAP-TYPE
	ENTERPRISE	event
	VARIABLES	{ eventString }
	DESCRIPTION
		"%s"
	::= 312
evtid-lvm-gspare-freed	TRAP-TYPE
	ENTERPRISE	event
	VARIABLES	{ eventString }
	DESCRIPTION
		"%s"
	::= 313
evtid-jbod-lvm-gspare-freed	TRAP-TYPE
	ENTERPRISE	event
	VARIABLES	{ eventString }
	DESCRIPTION
		"%s"
	::= 314
evtid-lvm-udv-full-replicate-started	TRAP-TYPE
	ENTERPRISE	event
	VARIABLES	{ eventString }
	DESCRIPTION
		"%s"
	::= 315
evtid-lvm-pd-local-spare	TRAP-TYPE
	ENTERPRISE	event
	VARIABLES	{ eventString }
	DESCRIPTION
		"%s"
	::= 316
evtid-jbod-lvm-pd-local-spare	TRAP-TYPE
	ENTERPRISE	event
	VARIABLES	{ eventString }
	DESCRIPTION
		"%s"
	::= 317
evtid-lvm-lspare-freed	TRAP-TYPE
	ENTERPRISE	event
	VARIABLES	{ eventString }
	DESCRIPTION
		"%s"
	::= 318
evtid-jbod-lvm-lspare-freed	TRAP-TYPE
	ENTERPRISE	event
	VARIABLES	{ eventString }
	DESCRIPTION
		"%s"
	::= 319
evtid-lvm-pd-ssd-cache	TRAP-TYPE
	ENTERPRISE	event
	VARIABLES	{ eventString }
	DESCRIPTION
		"%s"
	::= 320
evtid-jbod-lvm-pd-ssd-cahe	TRAP-TYPE
	ENTERPRISE	event
	VARIABLES	{ eventString }
	DESCRIPTION
		"%s"
	::= 321
evtid-lvm-ssd-cache-freed	TRAP-TYPE
	ENTERPRISE	event
	VARIABLES	{ eventString }
	DESCRIPTION
		"%s"
	::= 322
evtid-jbod-lvm-ssd-cache-freed	TRAP-TYPE
	ENTERPRISE	event
	VARIABLES	{ eventString }
	DESCRIPTION
		"%s"
	::= 323
evtid-lvm-rg-relocate-started	TRAP-TYPE
	ENTERPRISE	event
	VARIABLES	{ eventString }
	DESCRIPTION
		"%s"
	::= 324
evtid-lvm-rg-relocate-completed	TRAP-TYPE
	ENTERPRISE	event
	VARIABLES	{ eventString }
	DESCRIPTION
		"%s"
	::= 325
evtid-lvm-rg-rebuild-disk	TRAP-TYPE
	ENTERPRISE	event
	VARIABLES	{ eventString }
	DESCRIPTION
		"%s"
	::= 326
evtid-jbod-lvm-rg-rebuild-disk	TRAP-TYPE
	ENTERPRISE	event
	VARIABLES	{ eventString }
	DESCRIPTION
		"%s"
	::= 327
evtid-lvm-ssdc-pool-created	TRAP-TYPE
	ENTERPRISE	event
	VARIABLES	{ eventString }
	DESCRIPTION
		"%s"
	::= 328
evtid-lvm-ssdc-pool-deleted	TRAP-TYPE
	ENTERPRISE	event
	VARIABLES	{ eventString }
	DESCRIPTION
		"%s"
	::= 329
evtid-lvm-ssdc-vdev-added	TRAP-TYPE
	ENTERPRISE	event
	VARIABLES	{ eventString }
	DESCRIPTION
		"%s"
	::= 330
evtid-lvm-ssdc-vdev-removed	TRAP-TYPE
	ENTERPRISE	event
	VARIABLES	{ eventString }
	DESCRIPTION
		"%s"
	::= 331
evtid-lvm-ssdc-vd-enabled	TRAP-TYPE
	ENTERPRISE	event
	VARIABLES	{ eventString }
	DESCRIPTION
		"%s"
	::= 332
evtid-lvm-ssdc-vd-disabled	TRAP-TYPE
	ENTERPRISE	event
	VARIABLES	{ eventString }
	DESCRIPTION
		"%s"
	::= 333
evtid-lvm-ssdc-spare-added	TRAP-TYPE
	ENTERPRISE	event
	VARIABLES	{ eventString }
	DESCRIPTION
		"%s"
	::= 334
evtid-ssdc-vol-flushing-start	TRAP-TYPE
	ENTERPRISE	event
	VARIABLES	{ eventString }
	DESCRIPTION
		"%s"
	::= 335
evtid-ssdc-vol-flushing-completed	TRAP-TYPE
	ENTERPRISE	event
	VARIABLES	{ eventString }
	DESCRIPTION
		"%s"
	::= 336
evtid-ssdc-vol-flushing-failed	TRAP-TYPE
	ENTERPRISE	event
	VARIABLES	{ eventString }
	DESCRIPTION
		"%s"
	::= 337
evtid-jbod-lvm-ssdc-spare-added	TRAP-TYPE
	ENTERPRISE	event
	VARIABLES	{ eventString }
	DESCRIPTION
		"%s"
	::= 338
evtid-ssdc-ssd-rebuild-started	TRAP-TYPE
	ENTERPRISE	event
	VARIABLES	{ eventString }
	DESCRIPTION
		"%s"
	::= 339
evtid-ssdc-ssd-rebuild-aborted	TRAP-TYPE
	ENTERPRISE	event
	VARIABLES	{ eventString }
	DESCRIPTION
		"%s"
	::= 340
evtid-ssdc-ssd-rebuild-completed	TRAP-TYPE
	ENTERPRISE	event
	VARIABLES	{ eventString }
	DESCRIPTION
		"%s"
	::= 341
evtid-ssdc-jbod-ssd-rebuild-started	TRAP-TYPE
	ENTERPRISE	event
	VARIABLES	{ eventString }
	DESCRIPTION
		"%s"
	::= 342
evtid-ssdc-jbod-ssd-rebuild-aborted	TRAP-TYPE
	ENTERPRISE	event
	VARIABLES	{ eventString }
	DESCRIPTION
		"%s"
	::= 343
evtid-ssdc-jbod-ssd-rebuild-completed	TRAP-TYPE
	ENTERPRISE	event
	VARIABLES	{ eventString }
	DESCRIPTION
		"%s"
	::= 344
evtid-ssdc-pool-health-good	TRAP-TYPE
	ENTERPRISE	event
	VARIABLES	{ eventString }
	DESCRIPTION
		"%s"
	::= 345
evtid-ssdc-pool-health-degraded	TRAP-TYPE
	ENTERPRISE	event
	VARIABLES	{ eventString }
	DESCRIPTION
		"%s"
	::= 346
evtid-ssdc-pool-health-failed	TRAP-TYPE
	ENTERPRISE	event
	VARIABLES	{ eventString }
	DESCRIPTION
		"%s"
	::= 347
evtid-ssdc-pool-flushing-start	TRAP-TYPE
	ENTERPRISE	event
	VARIABLES	{ eventString }
	DESCRIPTION
		"%s"
	::= 348
evtid-ssdc-pool-flushing-completed	TRAP-TYPE
	ENTERPRISE	event
	VARIABLES	{ eventString }
	DESCRIPTION
		"%s"
	::= 349
evtid-ssdc-pool-flushing-failed	TRAP-TYPE
	ENTERPRISE	event
	VARIABLES	{ eventString }
	DESCRIPTION
		"%s"
	::= 350
evtid-lvm-rg-rebuild-disk	TRAP-TYPE
	ENTERPRISE	event
	VARIABLES	{ eventString }
	DESCRIPTION
		"%s"
	::= 351
evtid-jbod-lvm-rg-rebuild-disk	TRAP-TYPE
	ENTERPRISE	event
	VARIABLES	{ eventString }
	DESCRIPTION
		"%s"
	::= 352
evtid-lvm-ssdc-pool-created	TRAP-TYPE
	ENTERPRISE	event
	VARIABLES	{ eventString }
	DESCRIPTION
		"%s"
	::= 353
evtid-lvm-ssdc-pool-deleted	TRAP-TYPE
	ENTERPRISE	event
	VARIABLES	{ eventString }
	DESCRIPTION
		"%s"
	::= 354
evtid-lvm-ssdc-vdev-added	TRAP-TYPE
	ENTERPRISE	event
	VARIABLES	{ eventString }
	DESCRIPTION
		"%s"
	::= 355
evtid-lvm-ssdc-vdev-removed	TRAP-TYPE
	ENTERPRISE	event
	VARIABLES	{ eventString }
	DESCRIPTION
		"%s"
	::= 356
evtid-lvm-ssdc-vd-enabled	TRAP-TYPE
	ENTERPRISE	event
	VARIABLES	{ eventString }
	DESCRIPTION
		"%s"
	::= 357
evtid-lvm-ssdc-vd-disabled	TRAP-TYPE
	ENTERPRISE	event
	VARIABLES	{ eventString }
	DESCRIPTION
		"%s"
	::= 358
evtid-lvm-ssdc-spare-added	TRAP-TYPE
	ENTERPRISE	event
	VARIABLES	{ eventString }
	DESCRIPTION
		"%s"
	::= 359
evtid-jbod-lvm-ssdc-spare-added	TRAP-TYPE
	ENTERPRISE	event
	VARIABLES	{ eventString }
	DESCRIPTION
		"%s"
	::= 360
evtid-ssdc-ssd-rebuild-started	TRAP-TYPE
	ENTERPRISE	event
	VARIABLES	{ eventString }
	DESCRIPTION
		"%s"
	::= 361
evtid-ssdc-ssd-rebuild-aborted	TRAP-TYPE
	ENTERPRISE	event
	VARIABLES	{ eventString }
	DESCRIPTION
		"%s"
	::= 362
evtid-ssdc-ssd-rebuild-completed	TRAP-TYPE
	ENTERPRISE	event
	VARIABLES	{ eventString }
	DESCRIPTION
		"%s"
	::= 363
evtid-ssdc-jbod-ssd-rebuild-started	TRAP-TYPE
	ENTERPRISE	event
	VARIABLES	{ eventString }
	DESCRIPTION
		"%s"
	::= 364
evtid-ssdc-jbod-ssd-rebuild-aborted	TRAP-TYPE
	ENTERPRISE	event
	VARIABLES	{ eventString }
	DESCRIPTION
		"%s"
	::= 365
evtid-ssdc-jbod-ssd-rebuild-completed	TRAP-TYPE
	ENTERPRISE	event
	VARIABLES	{ eventString }
	DESCRIPTION
		"%s"
	::= 366
evtid-ssdc-pool-health-good	TRAP-TYPE
	ENTERPRISE	event
	VARIABLES	{ eventString }
	DESCRIPTION
		"%s"
	::= 367
evtid-ssdc-pool-health-degraded	TRAP-TYPE
	ENTERPRISE	event
	VARIABLES	{ eventString }
	DESCRIPTION
		"%s"
	::= 368
evtid-ssdc-pool-health-failed	TRAP-TYPE
	ENTERPRISE	event
	VARIABLES	{ eventString }
	DESCRIPTION
		"%s"
	::= 369
evtid-lvm-pd-clear-error	TRAP-TYPE
	ENTERPRISE	event
	VARIABLES	{ eventString }
	DESCRIPTION
		"%s"
	::= 370
evtid-jbod-lvm-pd-clear-error	TRAP-TYPE
	ENTERPRISE	event
	VARIABLES	{ eventString }
	DESCRIPTION
		"%s"
	::= 371
evtid-lvm-raid2-rebuild-spare	TRAP-TYPE
	ENTERPRISE	event
	VARIABLES	{ eventString }
	DESCRIPTION
		"%s"
	::= 372
evtid-lvm-pd-copyback-started	TRAP-TYPE
	ENTERPRISE	event
	VARIABLES	{ eventString }
	DESCRIPTION
		"%s"
	::= 373
evtid-jbod-lvm-pd-copyback-started	TRAP-TYPE
	ENTERPRISE	event
	VARIABLES	{ eventString }
	DESCRIPTION
		"%s"
	::= 374
evtid-lvm-pd-copyback-completed	TRAP-TYPE
	ENTERPRISE	event
	VARIABLES	{ eventString }
	DESCRIPTION
		"%s"
	::= 375
evtid-jbod-lvm-pd-copyback-completed	TRAP-TYPE
	ENTERPRISE	event
	VARIABLES	{ eventString }
	DESCRIPTION
		"%s"
	::= 376
evtid-lvm-rg-relocate-stopped	TRAP-TYPE
	ENTERPRISE	event
	VARIABLES	{ eventString }
	DESCRIPTION
		"%s"
	::= 377
evtid-lvm-vd-set-as-readonly	TRAP-TYPE
	ENTERPRISE	event
	VARIABLES	{ eventString }
	DESCRIPTION
		"%s"
	::= 378
evtid-lvm-rg-set-thin-threshold	TRAP-TYPE
	ENTERPRISE	event
	VARIABLES	{ eventString }
	DESCRIPTION
		"%s"
	::= 379
evtid-lvm-ise-erase-completed	TRAP-TYPE
	ENTERPRISE	event
	VARIABLES	{ eventString }
	DESCRIPTION
		"%s"
	::= 380
evtid-jbod-lvm-ise-erase-completed	TRAP-TYPE
	ENTERPRISE	event
	VARIABLES	{ eventString }
	DESCRIPTION
		"%s"
	::= 381
evtid-lvm-ise-erase-failed	TRAP-TYPE
	ENTERPRISE	event
	VARIABLES	{ eventString }
	DESCRIPTION
		"%s"
	::= 382
evtid-jbod-lvm-ise-erase-failed	TRAP-TYPE
	ENTERPRISE	event
	VARIABLES	{ eventString }
	DESCRIPTION
		"%s"
	::= 383
evtid-hac-ctr-inserted	TRAP-TYPE
	ENTERPRISE	event
	VARIABLES	{ eventString }
	DESCRIPTION
		"%s"
	::= 384
evtid-hac-ctr-removed	TRAP-TYPE
	ENTERPRISE	event
	VARIABLES	{ eventString }
	DESCRIPTION
		"%s"
	::= 385
evtid-hac-ctr-timeout	TRAP-TYPE
	ENTERPRISE	event
	VARIABLES	{ eventString }
	DESCRIPTION
		"%s"
	::= 386
evtid-hac-ctr-lockdown	TRAP-TYPE
	ENTERPRISE	event
	VARIABLES	{ eventString }
	DESCRIPTION
		"%s"
	::= 387
evtid-hac-ctr-failover	TRAP-TYPE
	ENTERPRISE	event
	VARIABLES	{ eventString }
	DESCRIPTION
		"%s"
	::= 388
evtid-hac-ctr-reset	TRAP-TYPE
	ENTERPRISE	event
	VARIABLES	{ eventString }
	DESCRIPTION
		"%s"
	::= 389
evtid-hac-ctr-memory-ng	TRAP-TYPE
	ENTERPRISE	event
	VARIABLES	{ eventString }
	DESCRIPTION
		"%s"
	::= 390
evtid-hac-ctr-firmware-ng	TRAP-TYPE
	ENTERPRISE	event
	VARIABLES	{ eventString }
	DESCRIPTION
		"%s"
	::= 391
evtid-hac-ctr-hwconfig-ng	TRAP-TYPE
	ENTERPRISE	event
	VARIABLES	{ eventString }
	DESCRIPTION
		"%s"
	::= 392
evtid-hac-ctr-lowspeed-ng	TRAP-TYPE
	ENTERPRISE	event
	VARIABLES	{ eventString }
	DESCRIPTION
		"%s"
	::= 393
evtid-hac-ctr-highspeed-ng	TRAP-TYPE
	ENTERPRISE	event
	VARIABLES	{ eventString }
	DESCRIPTION
		"%s"
	::= 394
evtid-hac-ctr-be-ng	TRAP-TYPE
	ENTERPRISE	event
	VARIABLES	{ eventString }
	DESCRIPTION
		"%s"
	::= 395
evtid-hac-ctr-fe-ng	TRAP-TYPE
	ENTERPRISE	event
	VARIABLES	{ eventString }
	DESCRIPTION
		"%s"
	::= 396
evtid-hac-jbod-hdd-path-ng	TRAP-TYPE
	ENTERPRISE	event
	VARIABLES	{ eventString }
	DESCRIPTION
		"%s"
	::= 397
evtid-hac-hdd-ng-to-failover	TRAP-TYPE
	ENTERPRISE	event
	VARIABLES	{ eventString }
	DESCRIPTION
		"%s"
	::= 398
evtid-rms-console-login	TRAP-TYPE
	ENTERPRISE	event
	VARIABLES	{ eventString }
	DESCRIPTION
		"%s"
	::= 399
evtid-rms-console-logout	TRAP-TYPE
	ENTERPRISE	event
	VARIABLES	{ eventString }
	DESCRIPTION
		"%s"
	::= 400
evtid-rms-web-login	TRAP-TYPE
	ENTERPRISE	event
	VARIABLES	{ eventString }
	DESCRIPTION
		"%s"
	::= 401
evtid-rms-web-logout	TRAP-TYPE
	ENTERPRISE	event
	VARIABLES	{ eventString }
	DESCRIPTION
		"%s"
	::= 402
evtid-rms-log-clear	TRAP-TYPE
	ENTERPRISE	event
	VARIABLES	{ eventString }
	DESCRIPTION
		"%s"
	::= 403
evtid-rms-reset-port	TRAP-TYPE
	ENTERPRISE	event
	VARIABLES	{ eventString }
	DESCRIPTION
		"%s"
	::= 404
evtid-rms-web-login-failed	TRAP-TYPE
	ENTERPRISE	event
	VARIABLES	{ eventString }
	DESCRIPTION
		"%s"
	::= 405
evtid-sys-shutdown	TRAP-TYPE
	ENTERPRISE	event
	VARIABLES	{ eventString }
	DESCRIPTION
		"%s"
	::= 406
evtid-sys-reboot	TRAP-TYPE
	ENTERPRISE	event
	VARIABLES	{ eventString }
	DESCRIPTION
		"%s"
	::= 407
evtid-fw-upgrade-start	TRAP-TYPE
	ENTERPRISE	event
	VARIABLES	{ eventString }
	DESCRIPTION
		"%s"
	::= 408
evtid-fw-upgrade-success	TRAP-TYPE
	ENTERPRISE	event
	VARIABLES	{ eventString }
	DESCRIPTION
		"%s"
	::= 409
evtid-fw-upgrade-failure	TRAP-TYPE
	ENTERPRISE	event
	VARIABLES	{ eventString }
	DESCRIPTION
		"%s"
	::= 410
evtid-ipc-fw-upgrade-timeout	TRAP-TYPE
	ENTERPRISE	event
	VARIABLES	{ eventString }
	DESCRIPTION
		"%s"
	::= 411
evtid-bios-upgrade-start	TRAP-TYPE
	ENTERPRISE	event
	VARIABLES	{ eventString }
	DESCRIPTION
		"%s"
	::= 412
evtid-bios-upgrade-success	TRAP-TYPE
	ENTERPRISE	event
	VARIABLES	{ eventString }
	DESCRIPTION
		"%s"
	::= 413
evtid-bios-upgrade-failure	TRAP-TYPE
	ENTERPRISE	event
	VARIABLES	{ eventString }
	DESCRIPTION
		"%s"
	::= 414
evtid-local-expander-fw-upgrade-start	TRAP-TYPE
	ENTERPRISE	event
	VARIABLES	{ eventString }
	DESCRIPTION
		"%s"
	::= 415
evtid-local-expander-fw-upgrade-success	TRAP-TYPE
	ENTERPRISE	event
	VARIABLES	{ eventString }
	DESCRIPTION
		"%s"
	::= 416
evtid-local-expander-fw-upgrade-failure	TRAP-TYPE
	ENTERPRISE	event
	VARIABLES	{ eventString }
	DESCRIPTION
		"%s"
	::= 417
evtid-jbod-fw-upgrade-start	TRAP-TYPE
	ENTERPRISE	event
	VARIABLES	{ eventString }
	DESCRIPTION
		"%s"
	::= 418
evtid-jbod-fw-upgrade-success	TRAP-TYPE
	ENTERPRISE	event
	VARIABLES	{ eventString }
	DESCRIPTION
		"%s"
	::= 419
evtid-jbod-fw-upgrade-failure	TRAP-TYPE
	ENTERPRISE	event
	VARIABLES	{ eventString }
	DESCRIPTION
		"%s"
	::= 420
evtid-sys-console-shutdown	TRAP-TYPE
	ENTERPRISE	event
	VARIABLES	{ eventString }
	DESCRIPTION
		"%s"
	::= 421
evtid-sys-web-shutdown	TRAP-TYPE
	ENTERPRISE	event
	VARIABLES	{ eventString }
	DESCRIPTION
		"%s"
	::= 422
evtid-sys-btn-shutdown	TRAP-TYPE
	ENTERPRISE	event
	VARIABLES	{ eventString }
	DESCRIPTION
		"%s"
	::= 423
evtid-sys-console-reboot	TRAP-TYPE
	ENTERPRISE	event
	VARIABLES	{ eventString }
	DESCRIPTION
		"%s"
	::= 424
evtid-sys-web-reboot	TRAP-TYPE
	ENTERPRISE	event
	VARIABLES	{ eventString }
	DESCRIPTION
		"%s"
	::= 425
evtid-sys-lcm-shutdown	TRAP-TYPE
	ENTERPRISE	event
	VARIABLES	{ eventString }
	DESCRIPTION
		"%s"
	::= 426
evtid-sys-lcm-reboot	TRAP-TYPE
	ENTERPRISE	event
	VARIABLES	{ eventString }
	DESCRIPTION
		"%s"
	::= 427
evtid-sys-lcm-plugin	TRAP-TYPE
	ENTERPRISE	event
	VARIABLES	{ eventString }
	DESCRIPTION
		"%s"
	::= 428
evtid-sys-lcm-plugout	TRAP-TYPE
	ENTERPRISE	event
	VARIABLES	{ eventString }
	DESCRIPTION
		"%s"
	::= 429
evtid-sys-change-name	TRAP-TYPE
	ENTERPRISE	event
	VARIABLES	{ eventString }
	DESCRIPTION
		"%s"
	::= 430
evtid-sys-add-mailaddr	TRAP-TYPE
	ENTERPRISE	event
	VARIABLES	{ eventString }
	DESCRIPTION
		"%s"
	::= 431
evtid-ctr-reboot-fwsync	TRAP-TYPE
	ENTERPRISE	event
	VARIABLES	{ eventString }
	DESCRIPTION
		"%s"
	::= 432
evtid-auto-qrep-not-enable	TRAP-TYPE
	ENTERPRISE	event
	VARIABLES	{ eventString }
	DESCRIPTION
		"%s"
	::= 433
evtid-auto-qrep-err	TRAP-TYPE
	ENTERPRISE	event
	VARIABLES	{ eventString }
	DESCRIPTION
		"%s"
	::= 434
evtid-auto-qrep-no-snap	TRAP-TYPE
	ENTERPRISE	event
	VARIABLES	{ eventString }
	DESCRIPTION
		"%s"
	::= 435
evtid-auto-clone-err	TRAP-TYPE
	ENTERPRISE	event
	VARIABLES	{ eventString }
	DESCRIPTION
		"%s"
	::= 436
evtid-auto-clone-no-snap	TRAP-TYPE
	ENTERPRISE	event
	VARIABLES	{ eventString }
	DESCRIPTION
		"%s"
	::= 437
evtid-dump-system-info	TRAP-TYPE
	ENTERPRISE	event
	VARIABLES	{ eventString }
	DESCRIPTION
		"%s"
	::= 438
evtid-auto-snap-err	TRAP-TYPE
	ENTERPRISE	event
	VARIABLES	{ eventString }
	DESCRIPTION
		"%s"
	::= 439
evtid-auto-map-err	TRAP-TYPE
	ENTERPRISE	event
	VARIABLES	{ eventString }
	DESCRIPTION
		"%s"
	::= 440
evtid-qrep2-snap-replica-success	TRAP-TYPE
	ENTERPRISE	event
	VARIABLES	{ eventString }
	DESCRIPTION
		"%s"
	::= 441
evtid-qrep2-snap-replica-failed	TRAP-TYPE
	ENTERPRISE	event
	VARIABLES	{ eventString }
	DESCRIPTION
		"%s"
	::= 442
evtid-qrep2-replica-snap-deleted	TRAP-TYPE
	ENTERPRISE	event
	VARIABLES	{ eventString }
	DESCRIPTION
		"%s"
	::= 443
evtid-qrep2-replica-rollback	TRAP-TYPE
	ENTERPRISE	event
	VARIABLES	{ eventString }
	DESCRIPTION
		"%s"
	::= 444
evtid-qrep-portal-enabled	TRAP-TYPE
	ENTERPRISE	event
	VARIABLES	{ eventString }
	DESCRIPTION
		"%s"
	::= 445
evtid-qrep-portal-disabled	TRAP-TYPE
	ENTERPRISE	event
	VARIABLES	{ eventString }
	DESCRIPTION
		"%s"
	::= 446
evtid-send-mail-fail	TRAP-TYPE
	ENTERPRISE	event
	VARIABLES	{ eventString }
	DESCRIPTION
		"%s"
	::= 447
evtid-config-imported	TRAP-TYPE
	ENTERPRISE	event
	VARIABLES	{ eventString }
	DESCRIPTION
		"%s"
	::= 448
evtid-c2fmon-plugin	TRAP-TYPE
	ENTERPRISE	event
	VARIABLES	{ eventString }
	DESCRIPTION
		"%s"
	::= 449
evtid-c2fmon-plugout	TRAP-TYPE
	ENTERPRISE	event
	VARIABLES	{ eventString }
	DESCRIPTION
		"%s"
	::= 450
evtid-c2fmon-attention	TRAP-TYPE
	ENTERPRISE	event
	VARIABLES	{ eventString }
	DESCRIPTION
		"%s"
	::= 451
evtid-c2fmon-poweroff	TRAP-TYPE
	ENTERPRISE	event
	VARIABLES	{ eventString }
	DESCRIPTION
		"%s"
	::= 452
evtid-c2fmon-poweron	TRAP-TYPE
	ENTERPRISE	event
	VARIABLES	{ eventString }
	DESCRIPTION
		"%s"
	::= 453
evtid-c2fmon-detect-success	TRAP-TYPE
	ENTERPRISE	event
	VARIABLES	{ eventString }
	DESCRIPTION
		"%s"
	::= 454
evtid-c2fmon-detect-failure	TRAP-TYPE
	ENTERPRISE	event
	VARIABLES	{ eventString }
	DESCRIPTION
		"%s"
	::= 455
evtid-c2fmon-surprise-remove	TRAP-TYPE
	ENTERPRISE	event
	VARIABLES	{ eventString }
	DESCRIPTION
		"%s"
	::= 456
evtid-sed-enable-ak	TRAP-TYPE
	ENTERPRISE	event
	VARIABLES	{ eventString }
	DESCRIPTION
		"%s"
	::= 457
evtid-sed-disable-ak	TRAP-TYPE
	ENTERPRISE	event
	VARIABLES	{ eventString }
	DESCRIPTION
		"%s"
	::= 458
evtid-sed-change-sys-ak	TRAP-TYPE
	ENTERPRISE	event
	VARIABLES	{ eventString }
	DESCRIPTION
		"%s"
	::= 459
evtid-lvm-sed-init-completed	TRAP-TYPE
	ENTERPRISE	event
	VARIABLES	{ eventString }
	DESCRIPTION
		"%s"
	::= 460
evtid-jbod-lvm-sed-init-completed	TRAP-TYPE
	ENTERPRISE	event
	VARIABLES	{ eventString }
	DESCRIPTION
		"%s"
	::= 461
evtid-lvm-sed-init-failed	TRAP-TYPE
	ENTERPRISE	event
	VARIABLES	{ eventString }
	DESCRIPTION
		"%s"
	::= 462
evtid-jbod-lvm-sed-init-failed	TRAP-TYPE
	ENTERPRISE	event
	VARIABLES	{ eventString }
	DESCRIPTION
		"%s"
	::= 463
evtid-lvm-sed-change-ak-completed	TRAP-TYPE
	ENTERPRISE	event
	VARIABLES	{ eventString }
	DESCRIPTION
		"%s"
	::= 464
evtid-jbod-lvm-sed-change-ak-completed	TRAP-TYPE
	ENTERPRISE	event
	VARIABLES	{ eventString }
	DESCRIPTION
		"%s"
	::= 465
evtid-lvm-sed-change-ak-failed	TRAP-TYPE
	ENTERPRISE	event
	VARIABLES	{ eventString }
	DESCRIPTION
		"%s"
	::= 466
evtid-jbod-lvm-sed-change-ak-failed	TRAP-TYPE
	ENTERPRISE	event
	VARIABLES	{ eventString }
	DESCRIPTION
		"%s"
	::= 467
evtid-lvm-sed-unlock-completed	TRAP-TYPE
	ENTERPRISE	event
	VARIABLES	{ eventString }
	DESCRIPTION
		"%s"
	::= 468
evtid-jbod-lvm-sed-unlock-completed	TRAP-TYPE
	ENTERPRISE	event
	VARIABLES	{ eventString }
	DESCRIPTION
		"%s"
	::= 469
evtid-lvm-sed-unlock-failed	TRAP-TYPE
	ENTERPRISE	event
	VARIABLES	{ eventString }
	DESCRIPTION
		"%s"
	::= 470
evtid-jbod-lvm-sed-unlock-failed	TRAP-TYPE
	ENTERPRISE	event
	VARIABLES	{ eventString }
	DESCRIPTION
		"%s"
	::= 471
evtid-lvm-sed-erase-completed	TRAP-TYPE
	ENTERPRISE	event
	VARIABLES	{ eventString }
	DESCRIPTION
		"%s"
	::= 472
evtid-jbod-lvm-sed-erase-completed	TRAP-TYPE
	ENTERPRISE	event
	VARIABLES	{ eventString }
	DESCRIPTION
		"%s"
	::= 473
evtid-lvm-sed-erase-failed	TRAP-TYPE
	ENTERPRISE	event
	VARIABLES	{ eventString }
	DESCRIPTION
		"%s"
	::= 474
evtid-jbod-lvm-sed-erase-failed	TRAP-TYPE
	ENTERPRISE	event
	VARIABLES	{ eventString }
	DESCRIPTION
		"%s"
	::= 475
evtid-lvm-sed-is-blocked	TRAP-TYPE
	ENTERPRISE	event
	VARIABLES	{ eventString }
	DESCRIPTION
		"%s"
	::= 476
evtid-jbod-lvm-sed-is-blocked	TRAP-TYPE
	ENTERPRISE	event
	VARIABLES	{ eventString }
	DESCRIPTION
		"%s"
	::= 477
evtid-create-multi-volume-success	TRAP-TYPE
	ENTERPRISE	event
	VARIABLES	{ eventString }
	DESCRIPTION
		"%s"
	::= 478
evtid-create-multi-volume-failed	TRAP-TYPE
	ENTERPRISE	event
	VARIABLES	{ eventString }
	DESCRIPTION
		"%s"
	::= 479
evtid-map-multi-lun-success	TRAP-TYPE
	ENTERPRISE	event
	VARIABLES	{ eventString }
	DESCRIPTION
		"%s"
	::= 480
evtid-map-multi-lun-failed	TRAP-TYPE
	ENTERPRISE	event
	VARIABLES	{ eventString }
	DESCRIPTION
		"%s"
	::= 481
evtid-assign-multi-volume-to-hostgroup-success	TRAP-TYPE
	ENTERPRISE	event
	VARIABLES	{ eventString }
	DESCRIPTION
		"%s"
	::= 482
evtid-assign-multi-volume-to-hostgroup-failed	TRAP-TYPE
	ENTERPRISE	event
	VARIABLES	{ eventString }
	DESCRIPTION
		"%s"
	::= 483
evtid-move-snapshot-to-recyclebin	TRAP-TYPE
	ENTERPRISE	event
	VARIABLES	{ eventString }
	DESCRIPTION
		"%s"
	::= 484
evtid-restore-snapshot-from-recyclebin	TRAP-TYPE
	ENTERPRISE	event
	VARIABLES	{ eventString }
	DESCRIPTION
		"%s"
	::= 485
evtid-hostgroup-create	TRAP-TYPE
	ENTERPRISE	event
	VARIABLES	{ eventString }
	DESCRIPTION
		"%s"
	::= 486
evtid-hostgroup-rename	TRAP-TYPE
	ENTERPRISE	event
	VARIABLES	{ eventString }
	DESCRIPTION
		"%s"
	::= 487
evtid-hostgroup-delete	TRAP-TYPE
	ENTERPRISE	event
	VARIABLES	{ eventString }
	DESCRIPTION
		"%s"
	::= 488
evtid-add-host-to-hostgroup-success	TRAP-TYPE
	ENTERPRISE	event
	VARIABLES	{ eventString }
	DESCRIPTION
		"%s"
	::= 489
evtid-add-host-to-hostgroup-failed	TRAP-TYPE
	ENTERPRISE	event
	VARIABLES	{ eventString }
	DESCRIPTION
		"%s"
	::= 490
evtid-host-rename-success	TRAP-TYPE
	ENTERPRISE	event
	VARIABLES	{ eventString }
	DESCRIPTION
		"%s"
	::= 491
evtid-host-rename-failed	TRAP-TYPE
	ENTERPRISE	event
	VARIABLES	{ eventString }
	DESCRIPTION
		"%s"
	::= 492
evtid-add-volume-to-hostgroup-success	TRAP-TYPE
	ENTERPRISE	event
	VARIABLES	{ eventString }
	DESCRIPTION
		"%s"
	::= 493
evtid-add-volume-to-hostgroup-failed	TRAP-TYPE
	ENTERPRISE	event
	VARIABLES	{ eventString }
	DESCRIPTION
		"%s"
	::= 494
evtid-remove-volume-from-hostgroup-success	TRAP-TYPE
	ENTERPRISE	event
	VARIABLES	{ eventString }
	DESCRIPTION
		"%s"
	::= 495
evtid-remove-volume-from-hostgroup-failed	TRAP-TYPE
	ENTERPRISE	event
	VARIABLES	{ eventString }
	DESCRIPTION
		"%s"
	::= 496
evtid-create-protectiongroup-success	TRAP-TYPE
	ENTERPRISE	event
	VARIABLES	{ eventString }
	DESCRIPTION
		"%s"
	::= 497
evtid-add-host-to-protectiongroup-success	TRAP-TYPE
	ENTERPRISE	event
	VARIABLES	{ eventString }
	DESCRIPTION
		"%s"
	::= 498
evtid-add-host-to-protectiongroup-failed	TRAP-TYPE
	ENTERPRISE	event
	VARIABLES	{ eventString }
	DESCRIPTION
		"%s"
	::= 499
evtid-auto-remote-replica-success	TRAP-TYPE
	ENTERPRISE	event
	VARIABLES	{ eventString }
	DESCRIPTION
		"%s"
	::= 500
evtid-auto-remote-replica-failed	TRAP-TYPE
	ENTERPRISE	event
	VARIABLES	{ eventString }
	DESCRIPTION
		"%s"
	::= 501
evtid-switch-replica-from-local-to-remote-success	TRAP-TYPE
	ENTERPRISE	event
	VARIABLES	{ eventString }
	DESCRIPTION
		"%s"
	::= 502
evtid-switch-replica-from-local-to-remote-failed	TRAP-TYPE
	ENTERPRISE	event
	VARIABLES	{ eventString }
	DESCRIPTION
		"%s"
	::= 503
evtid-remove-host-from-protectiongroup-success	TRAP-TYPE
	ENTERPRISE	event
	VARIABLES	{ eventString }
	DESCRIPTION
		"%s"
	::= 504
evtid-remove-host-from-protectiongroup-failed	TRAP-TYPE
	ENTERPRISE	event
	VARIABLES	{ eventString }
	DESCRIPTION
		"%s"
	::= 505
evtid-create-account-success	TRAP-TYPE
	ENTERPRISE	event
	VARIABLES	{ eventString }
	DESCRIPTION
		"%s"
	::= 506
evtid-create-account-failed	TRAP-TYPE
	ENTERPRISE	event
	VARIABLES	{ eventString }
	DESCRIPTION
		"%s"
	::= 507
evtid-edit-account-success	TRAP-TYPE
	ENTERPRISE	event
	VARIABLES	{ eventString }
	DESCRIPTION
		"%s"
	::= 508
evtid-edit-account-failed	TRAP-TYPE
	ENTERPRISE	event
	VARIABLES	{ eventString }
	DESCRIPTION
		"%s"
	::= 509
evtid-delete-account-success	TRAP-TYPE
	ENTERPRISE	event
	VARIABLES	{ eventString }
	DESCRIPTION
		"%s"
	::= 510
evtid-delete-account-failed	TRAP-TYPE
	ENTERPRISE	event
	VARIABLES	{ eventString }
	DESCRIPTION
		"%s"
	::= 511
evtid-disable-account-success	TRAP-TYPE
	ENTERPRISE	event
	VARIABLES	{ eventString }
	DESCRIPTION
		"%s"
	::= 512
evtid-disable-account-failed	TRAP-TYPE
	ENTERPRISE	event
	VARIABLES	{ eventString }
	DESCRIPTION
		"%s"
	::= 513
evtid-enable-account-success	TRAP-TYPE
	ENTERPRISE	event
	VARIABLES	{ eventString }
	DESCRIPTION
		"%s"
	::= 514
evtid-enable-account-failed	TRAP-TYPE
	ENTERPRISE	event
	VARIABLES	{ eventString }
	DESCRIPTION
		"%s"
	::= 515
evtid-rename-group-success	TRAP-TYPE
	ENTERPRISE	event
	VARIABLES	{ eventString }
	DESCRIPTION
		"%s"
	::= 516
evtid-rename-group-failed	TRAP-TYPE
	ENTERPRISE	event
	VARIABLES	{ eventString }
	DESCRIPTION
		"%s"
	::= 517
evtid-set-permission-success	TRAP-TYPE
	ENTERPRISE	event
	VARIABLES	{ eventString }
	DESCRIPTION
		"%s"
	::= 518
evtid-set-permission-failed	TRAP-TYPE
	ENTERPRISE	event
	VARIABLES	{ eventString }
	DESCRIPTION
		"%s"
	::= 519
evtid-lvm-vg-too-large-stripe	TRAP-TYPE
	ENTERPRISE	event
	VARIABLES	{ eventString }
	DESCRIPTION
		"%s"
	::= 520
evtid-ssdc-license-enable	TRAP-TYPE
	ENTERPRISE	event
	VARIABLES	{ eventString }
	DESCRIPTION
		"%s"
	::= 521
evtid-lvm-rg-relocate-license-enable	TRAP-TYPE
	ENTERPRISE	event
	VARIABLES	{ eventString }
	DESCRIPTION
		"%s"
	::= 522
evtid-trial-license-enable	TRAP-TYPE
	ENTERPRISE	event
	VARIABLES	{ eventString }
	DESCRIPTION
		"%s"
	::= 523
evtid-trial-license-remaining	TRAP-TYPE
	ENTERPRISE	event
	VARIABLES	{ eventString }
	DESCRIPTION
		"%s"
	::= 524
evtid-trial-license-expired	TRAP-TYPE
	ENTERPRISE	event
	VARIABLES	{ eventString }
	DESCRIPTION
		"%s"
	::= 525
evtid-trial-license-disabled	TRAP-TYPE
	ENTERPRISE	event
	VARIABLES	{ eventString }
	DESCRIPTION
		"%s"
	::= 526
END
