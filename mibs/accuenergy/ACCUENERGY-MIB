-- *******************************************************************************
--	Accuenergy MIB File
 --*******************************************************************************
--	File:	AcuvimII.txt
--	Coding:	GB2312
--	Font:	Courier
-- 	Description:	
--		This MIB file defines the Power Meter AcuvimII type. 
-- *******************************************************************************
--	History:
--	created		2012-03-26	George Zhao			Mark: -Toronto-
-- *******************************************************************************

-- ACCUENERGY-MIB { iso org(3) dod(6) internet(1) private(4)
--                 enterprises(1) accuenergy(39604) }

ACCUENERGY-MIB DEFINITIONS ::= BEGIN

IMPORTS
	enterprises, Integer32, Counter32, TimeTicks
		FROM RFC1155-SMI
	DisplayString
		FROM SNMPv2-TC;

DisplayString ::= OCTET STRING
			
accuenergy MODULE-IDENTITY
	LAST-UPDATED    "201203260000Z"
	ORGANIZATION    "www.accuenergy.com"
	CONTACT-INFO
                    "Accuenergy Canada Address"
	DESCRIPTION
                    "Accuenergy Enterprise MIB"
	REVISION        "201203260000Z"
	DESCRIPTION
                    "First revision."
    ::= { enterprises 39604 }

accuenergy                     OBJECT IDENTIFIER ::= { enterprises 39604 }

products                       OBJECT IDENTIFIER ::= { accuenergy 1 }

hardware                       OBJECT IDENTIFIER ::=  { products 1 }

powermeter                     OBJECT IDENTIFIER ::= { hardware 1 } 

acuvimII                       OBJECT IDENTIFIER ::= { powermeter 1 }

realTimeMetering               OBJECT IDENTIFIER ::=  { acuvimII 1 }
energy                         OBJECT IDENTIFIER ::=  { acuvimII 2 }
powerQuality                   OBJECT IDENTIFIER ::=  { acuvimII 3 }
maxAndMin                      OBJECT IDENTIFIER ::=  { acuvimII 4 }
ioStatus                       OBJECT IDENTIFIER ::=  { acuvimII 5 }
setting                        OBJECT IDENTIFIER ::=  { acuvimII 6 }
timeOfUse                      OBJECT IDENTIFIER ::=  { acuvimII 7 } 
traps                          OBJECT IDENTIFIER ::=  { acuvimII 8 } 
         
phaseVoltage                   OBJECT IDENTIFIER ::=  { realTimeMetering 1 }
lineVoltage                    OBJECT IDENTIFIER ::=  { realTimeMetering 2 }
currentMetering                OBJECT IDENTIFIER ::=  { realTimeMetering 3 }
power                          OBJECT IDENTIFIER ::=  { realTimeMetering 4 }
reactivePower                  OBJECT IDENTIFIER ::=  { realTimeMetering 5 }
apparentPower                  OBJECT IDENTIFIER ::=  { realTimeMetering 6 }
powerFactor                    OBJECT IDENTIFIER ::=  { realTimeMetering 7 }
demand                         OBJECT IDENTIFIER ::=  { realTimeMetering 8 }
           
unbalanceFactor                OBJECT IDENTIFIER ::=  { powerQuality 1 }
sequence                       OBJECT IDENTIFIER ::=  { powerQuality 2 }
phaseAngle                     OBJECT IDENTIFIER ::=  { powerQuality 3 }
thd                            OBJECT IDENTIFIER ::=  { powerQuality 4 }
crestFactor                    OBJECT IDENTIFIER ::=  { powerQuality 5 }
thff                           OBJECT IDENTIFIER ::=  { powerQuality 6 }
kFactor                        OBJECT IDENTIFIER ::=  { powerQuality 7 }
--harmonics                      OBJECT IDENTIFIER ::=  { powerQuality 8 } 

ioDIStatus                     OBJECT IDENTIFIER ::=  { ioStatus 1 }
ioAIStatus                     OBJECT IDENTIFIER ::=  { ioStatus 2 }
ioAOStatus                     OBJECT IDENTIFIER ::=  { ioStatus 3 }
ioRelayStatus                  OBJECT IDENTIFIER ::=  { ioStatus 4 }
                                                            
expandedIOModulesConnectStatus OBJECT IDENTIFIER ::=  { setting  1 } 

currentMonthTou                OBJECT IDENTIFIER ::=  { timeOfUse 1 }
lastMonthTou                   OBJECT IDENTIFIER ::=  { timeOfUse 2 }  

ioStatusTraps                  OBJECT IDENTIFIER ::=  { traps 2 }                  
             
--------------------------------------------------------------------            
--------------------------------------------------------------------         
-- object types                                                     
--------------------------------------------------------------------
-------------------------------------------------------------------- 

-- ******************************************************************
--  realTimeMetering
-- ******************************************************************    
--  the phaseVoltage GROUP(realTimeMetering.1)      
phaseVoltageA         OBJECT-TYPE
        	      	  SYNTAX Integer32
                      ACCESS read-only
                      STATUS current
                      DESCRIPTION
                             "This is Phase Voltage of Va.
                              Secondary Mode Relationship : U=Rx * (PT1/PT2)
                              Type:         float\
							  Note: There are two different modes to read basic analog measurements, 
							  one is secondary mode, and another is primary mode. In primary mode,
							  the numerical value in the register of the meter is equal to the real
							  physical value. In secondary mode, the relationship between the numerical
							  value in the register and the real physical value is shown in the following
							  table. (Rx is the numerical value in register of Acuvim II series meter)"
                      ::= { phaseVoltage 1 }

phaseVoltageB         OBJECT-TYPE
        	          SYNTAX Integer32
                      ACCESS read-only
                      STATUS current
                      DESCRIPTION
                             "This is Phase Voltage of Vb. In primary mode,
							  the numerical value in the register of the meter
							  is equal to the real physical value. 
                              Secondary Mode Relationship : U=Rx * (PT1/PT2)
                              Type:         float"
                      ::= { phaseVoltage 2 } 
                
phaseVoltageC         OBJECT-TYPE
        	      	  SYNTAX Integer32
                      ACCESS read-only
                      STATUS current
                      DESCRIPTION
                             "This is Phase Voltage of Vc.  In primary mode,
							  the numerical value in the register of the meter
							  is equal to the real physical value.
                              Secondary Mode Relationship : U=Rx * (PT1/PT2)
                              Type:         float"
                      ::= { phaseVoltage 3 }

averagePhaseVoltage   OBJECT-TYPE
        		      SYNTAX Integer32
                      ACCESS read-only
                      STATUS current
                      DESCRIPTION
                              "This is Average voltage Vavg. In primary mode,
							  the numerical value in the register of the meter
							  is equal to the real physical value.
                              Secondary Mode Relationship : U=Rx * (PT1/PT2)
                              Type:         float"

                ::= { phaseVoltage 4 }     
                
--  the lineVoltage GROUP (realTimeMetering.2)        

lineVoltageAB         OBJECT-TYPE
        		      SYNTAX Integer32
                      ACCESS read-only
                      STATUS current
                      DESCRIPTION
                             "This is Line Voltage of Vab. In primary mode,
							  the numerical value in the register of the meter
							  is equal to the real physical value.
                              Secondary Mode Relationship : U=Rx * (PT1/PT2)
                              Type:         float"
                      ::= { lineVoltage 1 }

lineVoltageBC         OBJECT-TYPE
        		      SYNTAX Integer32
                      ACCESS read-only
                      STATUS current
                      DESCRIPTION
                             "This is Line Voltage of Vbc.  In primary mode,
							  the numerical value in the register of the meter
							  is equal to the real physical value.
                              Secondary Mode Relationship : U=Rx * (PT1/PT2)
                              Type:         float"
                      ::= { lineVoltage 2 } 
                
lineVoltageCA         OBJECT-TYPE
        		      SYNTAX Integer32
                      ACCESS read-only
                      STATUS current
                      DESCRIPTION
                             "This is Line Voltage of Vca.  In primary mode,
							  the numerical value in the register of the meter
							  is equal to the real physical value.
                              Secondary Mode Relationship : U=Rx * (PT1/PT2)
                              Type:         float"
                      ::= { lineVoltage 3 }

averageLineVoltage    OBJECT-TYPE
        		      SYNTAX Integer32
                      ACCESS read-only
                      STATUS current
                      DESCRIPTION
                             "This is Average line voltage Vlavg. In primary mode,
							  the numerical value in the register of the meter
							  is equal to the real physical value.
                              Secondary Mode Relationship : U=Rx * (PT1/PT2)
                              Type:         float"
                      ::= { lineVoltage 4 }  
                
--  the currentMetering GROUP (realTimeMetering.3)  
phaseCurrentA         OBJECT-TYPE
        		      SYNTAX Integer32
                      ACCESS read-only
                      STATUS current
                      DESCRIPTION
                             "This is Phase(line)current Ia. In primary mode,
							  the numerical value in the register of the meter
							  is equal to the real physical value.
                              Secondary Mode Relationship : I=Rx * (CT1/CT2)
                              Type:         float"
                      ::= { currentMetering 1 }

phaseCurrentB         OBJECT-TYPE
        		      SYNTAX Integer32
                      ACCESS read-only
                      STATUS current
                      DESCRIPTION
                             "This is Phase(line)current Ib. In primary mode,
							  the numerical value in the register of the meter
							  is equal to the real physical value.
                              Secondary Mode Relationship : I=Rx * (CT1/CT2)
                              Type:         float"
                      ::= { currentMetering 2 }  
                      
phaseCurrentC         OBJECT-TYPE
        		      SYNTAX Integer32
                      ACCESS read-only
                      STATUS current
                      DESCRIPTION
                             "This is Phase(line)current Ic. In primary mode,
							  the numerical value in the register of the meter
							  is equal to the real physical value.
                              Secondary Mode Relationship : I=Rx * (CT1/CT2)
                              Type:         float"
                      ::= { currentMetering 3 }            
                      
averageCurrent        OBJECT-TYPE
        		      SYNTAX Integer32
                      ACCESS read-only
                      STATUS current
                      DESCRIPTION
                             "This is Average current Iavg.  In primary mode,
							  the numerical value in the register of the meter
							  is equal to the real physical value.
                              Secondary Mode Relationship : I=Rx * (CT1/CT2)
                              Type:         float"
                      ::= { currentMetering 4 }   

neutralCurrnet        OBJECT-TYPE
        		      SYNTAX Integer32
                      ACCESS read-only
                      STATUS current
                      DESCRIPTION
                             "This is Neutral current In.  In primary mode,
							  the numerical value in the register of the meter
							  is equal to the real physical value.
                              Secondary Mode Relationship : I=Rx * (CT1/CT2)
                              Type:         float"
                      ::= { currentMetering 5 }   
                      
--  the power GROUP (realTimeMetering.4)  
phaseAPower           OBJECT-TYPE
        		      SYNTAX Integer32
                      ACCESS read-only
                      STATUS current
                      DESCRIPTION
                             "This is Phase A power Pa.  In primary mode,
							  the numerical value in the register of the meter
							  is equal to the real physical value.
                              Secondary Mode Relationship : P=Rx*(PT1/PT2)*(CT1/CT2)
                              Type:         float"
                      ::= { power 1 }

phaseBPower           OBJECT-TYPE
        		      SYNTAX Integer32
                      ACCESS read-only
                      STATUS current
                      DESCRIPTION
                             "This is Phase B power Pb.  In primary mode,
							  the numerical value in the register of the meter
							  is equal to the real physical value.
                              Secondary Mode Relationship : P=Rx*(PT1/PT2)*(CT1/CT2)
                              Type:         float"
                      ::= { power 2 }

phaseCPower           OBJECT-TYPE
        		      SYNTAX Integer32
                      ACCESS read-only
                      STATUS current
                      DESCRIPTION
                             "This is Phase C power Pc. In primary mode,
							  the numerical value in the register of the meter
							  is equal to the real physical value.
                              Secondary Mode Relationship : P=Rx*(PT1/PT2)*(CT1/CT2)
                              Type:         float"
                      ::= { power 3 }

systemPower           OBJECT-TYPE
        		      SYNTAX Integer32
                      ACCESS read-only
                      STATUS current
                      DESCRIPTION
                             "This is System power Psum.  In primary mode,
							  the numerical value in the register of the meter
							  is equal to the real physical value.
                              Secondary Mode Relationship : P=Rx*(PT1/PT2)*(CT1/CT2)
                              Type:         float"
                      ::= { power 4 }  
                      
--  the reactivePower GROUP (realTimeMetering.5)  
phaseAReactivePower   OBJECT-TYPE
        		      SYNTAX Integer32
                      ACCESS read-only
                      STATUS current
                      DESCRIPTION
                             "This is Phase A reactive power Qa. In primary mode,
							  the numerical value in the register of the meter
							  is equal to the real physical value.
                              Secondary Mode Relationship : Q=Rx*(PT1/PT2)*(CT1/CT2)
                              Type:         float"
                      ::= { reactivePower 1 }

phaseBReactivePower   OBJECT-TYPE
        		      SYNTAX Integer32
                      ACCESS read-only
                      STATUS current
                      DESCRIPTION
                             "This is Phase B reactive power Qb.  In primary mode,
							  the numerical value in the register of the meter
							  is equal to the real physical value.
                              Secondary Mode Relationship : Q=Rx*(PT1/PT2)*(CT1/CT2)
                              Type:         float"
                      ::= { reactivePower 2 }

phaseCReactivePower   OBJECT-TYPE
        		      SYNTAX Integer32
                      ACCESS read-only
                      STATUS current
                      DESCRIPTION
                             "This is Phase C reactive power Qc.  In primary mode,
							  the numerical value in the register of the meter
							  is equal to the real physical value.
                              Secondary Mode Relationship : Q=Rx*(PT1/PT2)*(CT1/CT2)
                              Type:         float"
                      ::= { reactivePower 3 }

systemReactivePower   OBJECT-TYPE
        		      SYNTAX Integer32
                      ACCESS read-only
                      STATUS current
                      DESCRIPTION
                             "This is System reactive power Qsum.  In primary mode,
							  the numerical value in the register of the meter
							  is equal to the real physical value.
                              Secondary Mode Relationship : Q=Rx*(PT1/PT2)*(CT1/CT2)
                              Type:         float"
                      ::= { reactivePower 4 }

--  the apparentPower GROUP (realTimeMetering.6)  
phaseAApparentPower   OBJECT-TYPE
        		      SYNTAX Integer32
                      ACCESS read-only
                      STATUS current
                      DESCRIPTION
                             "This is Phase A apparent power Sa.  In primary mode,
							  the numerical value in the register of the meter
							  is equal to the real physical value.
                              Secondary Mode Relationship : S=Rx*(PT1/PT2)*(CT1/CT2)
                              Type:         float"
                      ::= { apparentPower 1 }

phaseBApparentPower   OBJECT-TYPE
        		      SYNTAX Integer32
                      ACCESS read-only
                      STATUS current
                      DESCRIPTION
                             "This is Phase B apparent power Sb.  In primary mode,
							  the numerical value in the register of the meter
							  is equal to the real physical value.
                              Secondary Mode Relationship : S=Rx*(PT1/PT2)*(CT1/CT2)
                              Type:         float"
                      ::= { apparentPower 2 }

phaseCApparentPower   OBJECT-TYPE
        		      SYNTAX Integer32
                      ACCESS read-only
                      STATUS current
                      DESCRIPTION
                             "This is Phase C apparent power Sc.  In primary mode,
							  the numerical value in the register of the meter
							  is equal to the real physical value.
                              Secondary Mode Relationship : S=Rx*(PT1/PT2)*(CT1/CT2)
                              Type:         float"
                      ::= { apparentPower 3 }

systemApparentPower   OBJECT-TYPE
        		      SYNTAX Integer32
                      ACCESS read-only
                      STATUS current
                      DESCRIPTION
                             "This is System apparent power Ssum.  In primary mode,
							  the numerical value in the register of the meter
							  is equal to the real physical value.
                              Secondary Mode Relationship : S=Rx*(PT1/PT2)*(CT1/CT2)
                              Type:         float"
                      ::= { apparentPower 4 }

--  the powerFactor GROUP (realTimeMetering.7)
phaseAPowerFactor     OBJECT-TYPE
        		      SYNTAX Integer32
                      ACCESS read-only
                      STATUS current
                      DESCRIPTION
                             "This is Phase A power factor PFa.  In primary mode,
							  the numerical value in the register of the meter
							  is equal to the real physical value.
                              Secondary Mode Relationship : PF = Rx
                              Type:         float"
                      ::= { powerFactor 1 }
  
phaseBPowerFactor     OBJECT-TYPE
        		      SYNTAX Integer32
                      ACCESS read-only
                      STATUS current
                      DESCRIPTION
                             "This is Phase B power factor PFb.  In primary mode,
							  the numerical value in the register of the meter
							  is equal to the real physical value.
                              Secondary Mode Relationship : PF = Rx
                              Type:         float"
                      ::= { powerFactor 2 }

phaseCPowerFactor     OBJECT-TYPE
        		      SYNTAX Integer32
                      ACCESS read-only
                      STATUS current
                      DESCRIPTION
                             "This is Phase C power factor PFc.  In primary mode,
							  the numerical value in the register of the meter
							  is equal to the real physical value.
                              Secondary Mode Relationship : PF = Rx
                              Type:         float"
                      ::= { powerFactor 3 }

systemPowerFactor     OBJECT-TYPE
        		      SYNTAX Integer32
                      ACCESS read-only
                      STATUS current
                      DESCRIPTION
                             "This is System power factor PFsum. In primary mode,
							  the numerical value in the register of the meter
							  is equal to the real physical value.
                              Secondary Mode Relationship : PF = Rx
                              Type:         float"
                      ::= { powerFactor 4 }

--  the demand GROUP (realTimeMetering.8)  
powerDemand           OBJECT-TYPE
        		      SYNTAX Integer32
                      ACCESS read-only
                      STATUS current
                      DESCRIPTION
                             "This is Power demand.  In primary mode,
							  the numerical value in the register of the meter
							  is equal to the real physical value.
                              Secondary Mode Relationship : P=Rx*(PT1/PT2)*(CT1/CT2)
                              Type:         float"
                      ::= { demand 1 }

reactivePowerDemand   OBJECT-TYPE
        		      SYNTAX Integer32
                      ACCESS read-only
                      STATUS current
                      DESCRIPTION
                             "This is Reactive power demand.  In primary mode,
							  the numerical value in the register of the meter
							  is equal to the real physical value.
                              Secondary Mode Relationship : P=Rx*(PT1/PT2)*(CT1/CT2)
                              Type:         float"
                      ::= { demand 2 }

apparentPowerDemand   OBJECT-TYPE
        		      SYNTAX Integer32
                      ACCESS read-only
                      STATUS current
                      DESCRIPTION
                             "This is Apparent power demand.  In primary mode,
							  the numerical value in the register of the meter
							  is equal to the real physical value.
                              Secondary Mode Relationship : P=Rx*(PT1/PT2)*(CT1/CT2)
                              Type:         float"
                      ::= { demand 3 }  
                      
phaseACurrentDemand   OBJECT-TYPE
        		      SYNTAX Integer32
                      ACCESS read-only
                      STATUS current
                      DESCRIPTION
                             "This is Phase A current demand.  In primary mode,
							  the numerical value in the register of the meter
							  is equal to the real physical value.
                              Secondary Mode Relationship : I=Rx*(CT1/CT2)
                              Type:         float"
                      ::= { demand 4 }  
                      
phaseBCurrentDemand   OBJECT-TYPE
        		      SYNTAX Integer32
                      ACCESS read-only
                      STATUS current
                      DESCRIPTION
                             "This is Phase B current demand.  In primary mode,
							  the numerical value in the register of the meter
							  is equal to the real physical value.
                              Secondary Mode Relationship : I=Rx*(CT1/CT2)
                              Type:         float"
                      ::= { demand 5 }

phaseCCurrentDemand   OBJECT-TYPE
        		      SYNTAX Integer32
                      ACCESS read-only
                      STATUS current
                      DESCRIPTION
                             "This is Phase C current demand.  In primary mode,
							  the numerical value in the register of the meter
							  is equal to the real physical value.
                              Secondary Mode Relationship : I=Rx*(CT1/CT2)
                              Type:         float"
                      ::= { demand 6 }      
                      
--  the other  realTimeMetering
frequency             OBJECT-TYPE
        	      	  SYNTAX Integer32
                      ACCESS read-only
                      STATUS current
                      DESCRIPTION
                             "This is Frequency. In primary mode,
							  the numerical value in the register of the meter
							  is equal to the real physical value.
                              Secondary Mode Relationship : F = Rx
                              Type:         float"
                      ::= { realTimeMetering 9 }

loadFeature           OBJECT-TYPE
        	      	  SYNTAX Integer32
                      ACCESS read-only
                      STATUS current
                      DESCRIPTION
                             "This is Load characteristic(L/C/R).
                              76.0/67.0/82.0(ASCII)
                              Type:         float"
                      ::= { realTimeMetering 10 }


-- ******************************************************************
--  energy
-- ******************************************************************
importEnergy          OBJECT-TYPE
        	      	  SYNTAX Integer32
                      ACCESS read-only
                      STATUS current
                      DESCRIPTION
                             "This is Energy IMP.It can be set as primary energy or 
                             secondary energy according to user. Relationship between numerical
                             value in the register and the real physical value is
                             Ep=Rx/10(primary), Ep=Rx/1000(secondary)"
                      ::= { energy  1 }

exportEnergy          OBJECT-TYPE
        	      	  SYNTAX Integer32
                      ACCESS read-only
                      STATUS current
                      DESCRIPTION
                             "This is Energy EXP.It can be set as primary energy or 
                             secondary energy according to user. Relationship between numerical
                             value in the register and the real physical value is
                             Ep=Rx/10(primary), Ep=Rx/1000(secondary)"
                      ::= { energy  2 }

totalEnergy          OBJECT-TYPE
        	      	  SYNTAX Integer32
                      ACCESS read-only
                      STATUS current
                      DESCRIPTION
                             "This is Energy TOTAL.It can be set as primary energy or 
                             secondary energy according to user. Relationship between numerical
                             value in the register and the real physical value is
                             Ep=Rx/10(primary), Ep=Rx/1000(secondary)"
                      ::= { energy  3 }

netEnergy             OBJECT-TYPE
        	      	  SYNTAX Integer32
                      ACCESS read-only
                      STATUS current
                      DESCRIPTION
                             "This is Energy NET. It can be set as primary energy or 
                             secondary energy according to user. Relationship between numerical
                             value in the register and the real physical value is
                             Ep=Rx/10(primary), Ep=Rx/1000(secondary)"
                      ::= { energy  4 }

importReactiveEnergy  OBJECT-TYPE
        	      	  SYNTAX Integer32
                      ACCESS read-only
                      STATUS current
                      DESCRIPTION
                             "This is Reactive energy IMP. It can be set as primary energy or 
                             secondary energy according to user. Relationship between numerical
                             value in the register and the real physical value is
                             Eq=Rx/10(primary), Eq=Rx/1000(secondary)"
                      ::= { energy  5 }

exportReactiveEnergy  OBJECT-TYPE
        	      	  SYNTAX Integer32
                      ACCESS read-only
                      STATUS current
                      DESCRIPTION
                             "This is Reactive energy EXP. It can be set as primary energy or 
                             secondary energy according to user. Relationship between numerical
                             value in the register and the real physical value is
                             Eq=Rx/10(primary), Eq=Rx/1000(secondary)"
                      ::= { energy  6 }

totalReactiveEnergy   OBJECT-TYPE
        	      	  SYNTAX Integer32
                      ACCESS read-only
                      STATUS current
                      DESCRIPTION
                             "This is Reactive energy TOTAL.It can be set as primary energy or 
                             secondary energy according to user. Relationship between numerical
                             value in the register and the real physical value is
                             Eq=Rx/10(primary), Eq=Rx/1000(secondary)"
                      ::= { energy  7 }

netReactiveEnergy     OBJECT-TYPE
        	      	  SYNTAX Integer32
                      ACCESS read-only
                      STATUS current
                      DESCRIPTION
                             "This is Reactive energy NET.It can be set as primary energy or 
                             secondary energy according to user. Relationship between numerical
                             value in the register and the real physical value is
                             Eq=Rx/10(primary), Eq=Rx/1000(secondary)"
                      ::= { energy  8 }

apparentEnergy        OBJECT-TYPE
        	      	  SYNTAX Integer32
                      ACCESS read-only
                      STATUS current
                      DESCRIPTION
                             "This is Apparent energy.It can be set as primary energy or 
                             secondary energy according to user. Relationship between numerical
                             value in the register and the real physical value is
                             Es=Rx/10(primary), Es=Rx/1000(secondary)"
                      ::= { energy  9 }

-- ******************************************************************
--  powerQuality
-- ****************************************************************** 
--  the unbalanceFactor GROUP (powerQuality.1)  
voltageUnbalanceFactor OBJECT-TYPE
        	      	  SYNTAX Integer32
                      ACCESS read-only
                      STATUS current
                      DESCRIPTION
                             "This is Voltage unbalance factor Uunbl.In primary mode,
							  the numerical value in the register of the meter
							  is equal to the real physical value.
                              Secondary Mode Relationship: Unbalance = Rx * 100%
                              Type:         float"
                      ::= { unbalanceFactor  1 }

currentUnbalanceFactor OBJECT-TYPE
        	      	  SYNTAX Integer32
                      ACCESS read-only
                      STATUS current
                      DESCRIPTION
                             "This is Current unbalance factor I_unbl.In primary mode,
							  the numerical value in the register of the meter
							  is equal to the real physical value.
                              Secondary Mode Relationship: Unbalance = Rx * 100%
                              Type:         float"
                      ::= { unbalanceFactor  2 }

--  the sequence GROUP (powerQuality.2) 
positiveSequenceRealPartOfU OBJECT-TYPE
        	      	        SYNTAX Integer32
                            ACCESS read-only
                            STATUS current
                            DESCRIPTION
                                   "This is positive sequence real part of UA.
                                    Relationship(Primary&Secondary Mode): U=Rx*(PT1/PT2)/10
                                    Range:       -32768~32767"
                            ::= { sequence  1 }

positiveSequenceComplexPartOfU OBJECT-TYPE
        	      	        SYNTAX Integer32
                            ACCESS read-only
                            STATUS current
                            DESCRIPTION
                                   "This is positive sequence complex part of UA.
                                    Relationship(Primary&Secondary Mode): U=Rx*(PT1/PT2)/10
                                    Range:       -32768~32767"
                            ::= { sequence  2 }

negativeSequenceRealPartOfU OBJECT-TYPE
        	      	        SYNTAX Integer32
                            ACCESS read-only
                            STATUS current
                            DESCRIPTION
                                   "This is negative sequence real part of UA.
                                    Relationship(Primary&Secondary Mode): U=Rx*(PT1/PT2)/10
                                    Range:       -32768~32767"
                            ::= { sequence  3 }

negativeSequenceComplexPartOfU OBJECT-TYPE
        	      	        SYNTAX Integer32
                            ACCESS read-only
                            STATUS current
                            DESCRIPTION
                                   "This is negative sequence complex part of UA.
                                    Relationship(Primary&Secondary Mode): U=Rx*(PT1/PT2)/10
                                    Range:       -32768~32767"
                            ::= { sequence  4 }

zeroSequenceRealPartOfU     OBJECT-TYPE
        	      	        SYNTAX Integer32
                            ACCESS read-only
                            STATUS current
                            DESCRIPTION
                                   "This is zero sequence real part of UA.
                                    Relationship(Primary&Secondary Mode): U=Rx*(PT1/PT2)/10
                                    Range:       -32768~32767"
                            ::= { sequence  5 }

zeroSequenceComplexPartOfU  OBJECT-TYPE
        	      	        SYNTAX Integer32
                            ACCESS read-only
                            STATUS current
                            DESCRIPTION
                                   "This is zero sequence complex part of UA.
                                    Relationship(Primary&Secondary Mode): U=Rx*(PT1/PT2)/10
                                    Range:       -32768~32767"
                            ::= { sequence  6 }

positiveSequenceRealPartOfI OBJECT-TYPE
        	      	        SYNTAX Integer32
                            ACCESS read-only
                            STATUS current
                            DESCRIPTION
                                   "This is positive sequence real part of IA.
                                    Relationship(Primary&Secondary Mode): I=Rx*(CT1/CT2)/1000
                                    Range:       -32768~32767"
                            ::= { sequence  7 }

positiveSequenceComplexPartOfI OBJECT-TYPE
        	      	        SYNTAX Integer32
                            ACCESS read-only
                            STATUS current
                            DESCRIPTION
                                   "This is positive sequence complex part of IA.
                                    Relationship(Primary&Secondary Mode): I=Rx*(CT1/CT2)/1000
                                    Range:       -32768~32767"
                            ::= { sequence  8 }

negativeSequenceRealPartOfI OBJECT-TYPE
        	      	        SYNTAX Integer32
                            ACCESS read-only
                            STATUS current
                            DESCRIPTION
                                   "This is negative sequence real part of IA.
                                    Relationship(Primary&Secondary Mode): I=Rx*(CT1/CT2)/1000
                                    Range:       -32768~32767"
                            ::= { sequence  9 }

negativeSequenceComplexPartOfI OBJECT-TYPE
        	      	        SYNTAX Integer32
                            ACCESS read-only
                            STATUS current
                            DESCRIPTION
                                   "This is negative sequence complex part of IA.
                                    Relationship(Primary&Secondary Mode): I=Rx*(CT1/CT2)/1000
                                    Range:       -32768~32767"
                            ::= { sequence  10 }

zeroSequenceRealPartOfI     OBJECT-TYPE
        	      	        SYNTAX Integer32
                            ACCESS read-only
                            STATUS current
                            DESCRIPTION
                                   "This is zero sequence real part of IA.
                                    Relationship(Primary&Secondary Mode): I=Rx*(CT1/CT2)/1000
                                    Range:       -32768~32767"
                            ::= { sequence  11 }

zeroSequenceComplexPartOfI  OBJECT-TYPE
        	      	        SYNTAX Integer32
                            ACCESS read-only
                            STATUS current
                            DESCRIPTION
                                   "This is zero sequence complex part of IA.
                                    Relationship(Primary&Secondary Mode): I=Rx*(CT1/CT2)/1000
                                    Range:       -32768~32767"
                            ::= { sequence  12 }

--  the phaseAngle GROUP (powerQuality.3) 
phaseAngleUbUa              OBJECT-TYPE
        	      	        SYNTAX Integer32
                            ACCESS read-only
                            STATUS current
                            DESCRIPTION
                                   "This is phase angle of V2 to V1.
                                    Relationship(Primary&Secondary Mode): Phase angle=Rx/10
                                    Range:       0~3600"
                            ::= { phaseAngle  1 }

phaseAngleUcUa              OBJECT-TYPE
        	      	        SYNTAX Integer32
                            ACCESS read-only
                            STATUS current
                            DESCRIPTION
                                   "This is phase angle of V3 to V1.
                                    Relationship(Primary&Secondary Mode): Phase angle=Rx/10
                                    Range:       0~3600"
                            ::= { phaseAngle  2 }

phaseAngleIaUa              OBJECT-TYPE
        	      	        SYNTAX Integer32
                            ACCESS read-only
                            STATUS current
                            DESCRIPTION
                                   "This is phase angle of I1 to V1.
                                    Relationship(Primary&Secondary Mode): Phase angle=Rx/10
                                    Range:       0~3600"
                            ::= { phaseAngle  3 }

phaseAngleIbUa              OBJECT-TYPE
        	      	        SYNTAX Integer32
                            ACCESS read-only
                            STATUS current
                            DESCRIPTION
                                   "This is phase angle of I2 to V1.
                                    Relationship(Primary&Secondary Mode): Phase angle=Rx/10
                                    Range:       0~3600"
                            ::= { phaseAngle  4 }

phaseAngleIcUa              OBJECT-TYPE
        	      	        SYNTAX Integer32
                            ACCESS read-only
                            STATUS current
                            DESCRIPTION
                                   "This is phase angle of I3 to V1.
                                    Relationship(Primary&Secondary Mode): Phase angle=Rx/10
                                    Range:       0~3600"
                            ::= { phaseAngle  5 }

phaseAngleUbcUab            OBJECT-TYPE
        	      	        SYNTAX Integer32
                            ACCESS read-only
                            STATUS current
                            DESCRIPTION
                                   "This is phase angle of V23 to V12.
                                    Relationship(Primary&Secondary Mode): Phase angle=Rx/10
                                    Range:       0~3600"
                            ::= { phaseAngle  6 }

phaseAngleIaUab             OBJECT-TYPE
        	      	        SYNTAX Integer32
                            ACCESS read-only
                            STATUS current
                            DESCRIPTION
                                   "This is phase angle of I1 to V12.
                                    Relationship(Primary&Secondary Mode): Phase angle=Rx/10
                                    Range:       0~3600"
                            ::= { phaseAngle  7 }

phaseAngleIbUab             OBJECT-TYPE
        	      	        SYNTAX Integer32
                            ACCESS read-only
                            STATUS current
                            DESCRIPTION
                                   "This is phase angle of I2 to V12.
                                    Relationship(Primary&Secondary Mode): Phase angle=Rx/10
                                    Range:       0~3600"
                            ::= { phaseAngle  8 }

phaseAngleIcUab             OBJECT-TYPE
        	      	        SYNTAX Integer32
                            ACCESS read-only
                            STATUS current
                            DESCRIPTION
                                   "This is phase angle of I3 to V12.
                                    Relationship(Primary&Secondary Mode): Phase angle=Rx/10
                                    Range:       0~3600"
                            ::= { phaseAngle  9 }

--  the thd GROUP (powerQuality.4) 
thdUa                  OBJECT-TYPE
        	      	   SYNTAX Integer32
                       ACCESS read-only
                       STATUS current
                       DESCRIPTION
                             "This is THD_V1 of V1(V12).
                             Relationship(Primary&Secondary Mode): THD=(Rx/10000)* 100%
                             Range:       0~10000"
                       ::= { thd  1 }

thdUb                  OBJECT-TYPE
        	      	   SYNTAX Integer32
                       ACCESS read-only
                       STATUS current
                       DESCRIPTION
                             "This is THD_V1 of V2(V31).
                             Relationship(Primary&Secondary Mode): THD=(Rx/10000)* 100%
                             Range:       0~10000"
                       ::= { thd  2 }

thdUc                  OBJECT-TYPE
        	      	   SYNTAX Integer32
                       ACCESS read-only
                       STATUS current
                       DESCRIPTION
                             "This is THD_V1 of V3(V23).
                             Relationship(Primary&Secondary Mode): THD=(Rx/10000)* 100%
                             Range:       0~10000"
                       ::= { thd  3 }

averageThdV            OBJECT-TYPE
        	      	   SYNTAX Integer32
                       ACCESS read-only
                       STATUS current
                       DESCRIPTION
                             "This is Average THD_V.
                             Relationship(Primary&Secondary Mode): THD=(Rx/10000)* 100%
                             Range:       0~10000"
                       ::= { thd  4 }

thdIa                  OBJECT-TYPE
        	      	   SYNTAX Integer32
                       ACCESS read-only
                       STATUS current
                       DESCRIPTION
                             "This is THD_I1.
                             Relationship(Primary&Secondary Mode): THD=(Rx/10000)* 100%
                             Range:       0~10000"
                       ::= { thd  5 }
                       
thdIb                  OBJECT-TYPE
        	      	   SYNTAX Integer32
                       ACCESS read-only
                       STATUS current
                       DESCRIPTION
                             "This is THD_I2.
                             Relationship(Primary&Secondary Mode): THD=(Rx/10000)* 100%
                             Range:       0~10000"
                       ::= { thd  6 }

thdIc                  OBJECT-TYPE
        	      	   SYNTAX Integer32
                       ACCESS read-only
                       STATUS current
                       DESCRIPTION
                             "This is THD_I3.
                             Relationship(Primary&Secondary Mode): THD=(Rx/10000)* 100%
                             Range:       0~10000"
                       ::= { thd  7 }

averageThdI            OBJECT-TYPE
        	      	   SYNTAX Integer32
                       ACCESS read-only
                       STATUS current
                       DESCRIPTION
                             "This is THD_I3.
                             Relationship(Primary&Secondary Mode): THD=(Rx/10000)* 100%
                             Range:       0~10000"
                       ::= { thd  8 }

oddHDUa                OBJECT-TYPE
        	      	   SYNTAX Integer32
                       ACCESS read-only
                       STATUS current
                       DESCRIPTION
                             "This is Odd HD of V1(V12).
                             Relationship(Primary&Secondary Mode): HDo=(Rx/10000)*100%
                             Range:       0~10000"
                       ::= { thd  9 }

oddHDUb                OBJECT-TYPE
        	      	   SYNTAX Integer32
                       ACCESS read-only
                       STATUS current
                       DESCRIPTION
                             "This is Odd HD of V2(V31).
                             Relationship(Primary&Secondary Mode): HDo=(Rx/10000)*100%
                             Range:       0~10000"
                       ::= { thd  10 }

oddHDUc                OBJECT-TYPE
        	      	   SYNTAX Integer32
                       ACCESS read-only
                       STATUS current
                       DESCRIPTION
                             "This is Odd HD of V3(V23).
                             Relationship(Primary&Secondary Mode): HDo=(Rx/10000)*100%
                             Range:       0~10000"
                       ::= { thd  11 }

oddHDIa                OBJECT-TYPE
        	      	   SYNTAX Integer32
                       ACCESS read-only
                       STATUS current
                       DESCRIPTION
                             "This is Odd HD of I1.
                             Relationship(Primary&Secondary Mode): HDo=(Rx/10000)*100%
                             Range:       0~10000"
                       ::= { thd  12 }

oddHDIb                OBJECT-TYPE
        	      	   SYNTAX Integer32
                       ACCESS read-only
                       STATUS current
                       DESCRIPTION
                             "This is Odd HD of I2.
                             Relationship(Primary&Secondary Mode): HDo=(Rx/10000)*100%
                             Range:       0~10000"
                       ::= { thd  13 }

oddHDIc                OBJECT-TYPE
        	      	   SYNTAX Integer32
                       ACCESS read-only
                       STATUS current
                       DESCRIPTION
                             "This is Odd HD of I3.
                             Relationship(Primary&Secondary Mode): HDo=(Rx/10000)*100%
                             Range:       0~10000"
                       ::= { thd  14 }

evenHDUa               OBJECT-TYPE
        	      	   SYNTAX Integer32
                       ACCESS read-only
                       STATUS current
                       DESCRIPTION
                             "This is even HD of V1(V12).
                             Relationship(Primary&Secondary Mode): HDe=(Rx/10000)*100%
                             Range:       0~10000"
                       ::= { thd  15 }

evenHDUb               OBJECT-TYPE
        	      	   SYNTAX Integer32
                       ACCESS read-only
                       STATUS current
                       DESCRIPTION
                             "This is even HD of V2(V31).
                             Relationship(Primary&Secondary Mode): HDe=(Rx/10000)*100%
                             Range:       0~10000"
                       ::= { thd  16 }

evenHDUc               OBJECT-TYPE
        	      	   SYNTAX Integer32
                       ACCESS read-only
                       STATUS current
                       DESCRIPTION
                             "This is even HD of V3(V23).
                             Relationship(Primary&Secondary Mode): HDe=(Rx/10000)*100%
                             Range:       0~10000"
                       ::= { thd  17 }

evenHDIa               OBJECT-TYPE
        	      	   SYNTAX Integer32
                       ACCESS read-only
                       STATUS current
                       DESCRIPTION
                             "This is even HD of I1.
                             Relationship(Primary&Secondary Mode): HDe=(Rx/10000)*100%
                             Range:       0~10000"
                       ::= { thd  18 }
                       
evenHDIb               OBJECT-TYPE
        	      	   SYNTAX Integer32
                       ACCESS read-only
                       STATUS current
                       DESCRIPTION
                             "This is even HD of I2.
                             Relationship(Primary&Secondary Mode): HDe=(Rx/10000)*100%
                             Range:       0~10000"
                       ::= { thd  19 }

evenHDIc               OBJECT-TYPE
        	      	   SYNTAX Integer32
                       ACCESS read-only
                       STATUS current
                       DESCRIPTION
                             "This is even HD of I3.
                             Relationship(Primary&Secondary Mode): HDe=(Rx/10000)*100%
                             Range:       0~10000"
                       ::= { thd  20 }

--  the crestFactor GROUP (powerQuality.5)
creastFactorUa         OBJECT-TYPE
        	      	   SYNTAX Integer32
                       ACCESS read-only
                       STATUS current
                       DESCRIPTION
                             "This is Crest Factor of V1(V12).
                             Relationship(Primary&Secondary Mode): CF=Rx/1000
                             Range:       0~65535"
                       ::= { crestFactor  1 }

creastFactorUb         OBJECT-TYPE
        	      	   SYNTAX Integer32
                       ACCESS read-only
                       STATUS current
                       DESCRIPTION
                             "This is Crest Factor of V2(V31).
                             Relationship(Primary&Secondary Mode): CF=Rx/1000
                             Range:       0~65535"
                       ::= { crestFactor  2 }

creastFactorUc         OBJECT-TYPE
        	      	   SYNTAX Integer32
                       ACCESS read-only
                       STATUS current
                       DESCRIPTION
                             "This is Crest Factor of V3(V23).
                             Relationship(Primary&Secondary Mode): CF=Rx/1000
                             Range:       0~65535"
                       ::= { crestFactor  3 }

--  the thff GROUP (powerQuality.6)
thffUa                 OBJECT-TYPE
        	      	   SYNTAX Integer32
                       ACCESS read-only
                       STATUS current
                       DESCRIPTION
                             "This is THFF of V1(V12).
                             Relationship(Primary&Secondary Mode): THFF=(Rx/10000)*100%
                             Range:       0~10000"
                       ::= { thff  1 }

thffUb                 OBJECT-TYPE
        	      	   SYNTAX Integer32
                       ACCESS read-only
                       STATUS current
                       DESCRIPTION
                             "This is THFF of V2(V31).
                             Relationship(Primary&Secondary Mode): THFF=(Rx/10000)*100%
                             Range:       0~10000"
                       ::= { thff  2 }

thffUc                 OBJECT-TYPE
        	      	   SYNTAX Integer32
                       ACCESS read-only
                       STATUS current
                       DESCRIPTION
                             "This is THFF of V3(V23).
                             Relationship(Primary&Secondary Mode): THFF=(Rx/10000)*100%
                             Range:       0~10000"
                       ::= { thff  3 }

                 
--  the kFactor GROUP (powerQuality.7)
kFactorIa              OBJECT-TYPE
        	      	   SYNTAX Integer32
                       ACCESS read-only
                       STATUS current
                       DESCRIPTION
                             "This is K Factor of I1.
                             Relationship(Primary&Secondary Mode): KF=Rx/10
                             Range:       0~65535"
                       ::= { kFactor  1 }

kFactorIb              OBJECT-TYPE
        	      	   SYNTAX Integer32
                       ACCESS read-only
                       STATUS current
                       DESCRIPTION
                             "This is K Factor of I2.
                             Relationship(Primary&Secondary Mode): KF=Rx/10
                             Range:       0~65535"
                       ::= { kFactor  2 }

kFactorIc              OBJECT-TYPE
        	      	   SYNTAX Integer32
                       ACCESS read-only
                       STATUS current
                       DESCRIPTION
                             "This is K Factor of I3.
                             Relationship(Primary&Secondary Mode): KF=Rx/10
                             Range:       0~65535"
                       ::= { kFactor  3 }



-- ******************************************************************
--  maxAndMin
-- ******************************************************************
maxOfUa               OBJECT-TYPE
        	      	  SYNTAX Integer32
                      ACCESS read-only
                      STATUS current
                      DESCRIPTION
                             "This is MAX of V1.
                              Relationship(Primary&Secondary Mode): U=Rx *(PT1/PT2)/10
                              Range:        -32768~32767"
                      ::= { maxAndMin  1 }

maxTimeStampOfUa      OBJECT-TYPE
        	      	  SYNTAX DisplayString
                      ACCESS read-only
                      STATUS current
                      DESCRIPTION
                             "This is timestamp for MAX of V1.
                              Time Format: yyyy:mm:dd:hh:mm:ss"
                      ::= { maxAndMin  2 }

maxOfUb               OBJECT-TYPE
        	      	  SYNTAX Integer32
                      ACCESS read-only
                      STATUS current
                      DESCRIPTION
                             "This is MAX of V2.
                              Relationship(Primary&Secondary Mode): U=Rx *(PT1/PT2)/10
                              Range:        -32768~32767"
                      ::= { maxAndMin  3 }

maxTimeStampOfUb      OBJECT-TYPE
        	      	  SYNTAX DisplayString
                      ACCESS read-only
                      STATUS current
                      DESCRIPTION
                             "This is timestamp for MAX of V2.
                              Time Format: yyyy:mm:dd:hh:mm:ss"
                      ::= { maxAndMin  4 }

maxOfUc               OBJECT-TYPE
        	      	  SYNTAX Integer32
                      ACCESS read-only
                      STATUS current
                      DESCRIPTION
                             "This is MAX of V3.
                              Relationship(Primary&Secondary Mode): U=Rx *(PT1/PT2)/10
                              Range:        -32768~32767"
                      ::= { maxAndMin  5 }

maxTimeStampOfUc      OBJECT-TYPE
        	      	  SYNTAX DisplayString
                      ACCESS read-only
                      STATUS current
                      DESCRIPTION
                             "This is timestamp for MAX of V3.
                              Time Format: yyyy:mm:dd:hh:mm:ss"
                      ::= { maxAndMin  6 }

maxOfUab              OBJECT-TYPE
        	      	  SYNTAX Integer32
                      ACCESS read-only
                      STATUS current
                      DESCRIPTION
                             "This is MAX of V12.
                              Relationship(Primary&Secondary Mode): U=Rx *(PT1/PT2)/10
                              Range:        -32768~32767"
                      ::= { maxAndMin  7 }

maxTimeStampOfUab      OBJECT-TYPE
        	      	  SYNTAX DisplayString
                      ACCESS read-only
                      STATUS current
                      DESCRIPTION
                             "This is timestamp for MAX of V12.
                              Time Format: yyyy:mm:dd:hh:mm:ss"
                      ::= { maxAndMin  8 }

maxOfUbc              OBJECT-TYPE
        	      	  SYNTAX Integer32
                      ACCESS read-only
                      STATUS current
                      DESCRIPTION
                             "This is MAX of V23.
                              Relationship(Primary&Secondary Mode): U=Rx *(PT1/PT2)/10
                              Range:        -32768~32767"
                      ::= { maxAndMin  9 }

maxTimeStampOfUbc     OBJECT-TYPE
        	      	  SYNTAX DisplayString
                      ACCESS read-only
                      STATUS current
                      DESCRIPTION
                             "This is timestamp for MAX of V23.
                              Time Format: yyyy:mm:dd:hh:mm:ss"
                      ::= { maxAndMin  10 }

maxOfUca              OBJECT-TYPE
        	      	  SYNTAX Integer32
                      ACCESS read-only
                      STATUS current
                      DESCRIPTION
                             "This is MAX of V31.
                              Relationship(Primary&Secondary Mode): U=Rx *(PT1/PT2)/10
                              Range:        -32768~32767"
                      ::= { maxAndMin  11 }

maxTimeStampOfUca     OBJECT-TYPE
        	      	  SYNTAX DisplayString
                      ACCESS read-only
                      STATUS current
                      DESCRIPTION
                             "This is timestamp for MAX of V31.
                              Time Format: yyyy:mm:dd:hh:mm:ss"
                      ::= { maxAndMin  12 }

maxOfIa              OBJECT-TYPE
        	      	  SYNTAX Integer32
                      ACCESS read-only
                      STATUS current
                      DESCRIPTION
                             "This is MAX of I1.
                              Relationship(Primary&Secondary Mode): I=Rx *(CT1/CT2)/1000
                              Range:        -32768~32767"
                      ::= { maxAndMin  13 }

maxTimeStampOfIa      OBJECT-TYPE
        	      	  SYNTAX DisplayString
                      ACCESS read-only
                      STATUS current
                      DESCRIPTION
                             "This is timestamp for MAX of I1.
                              Time Format: yyyy:mm:dd:hh:mm:ss"
                      ::= { maxAndMin  14 }

maxOfIb              OBJECT-TYPE
        	      	  SYNTAX Integer32
                      ACCESS read-only
                      STATUS current
                      DESCRIPTION
                             "This is MAX of I2.
                              Relationship(Primary&Secondary Mode): I=Rx *(CT1/CT2)/1000
                              Range:        -32768~32767"
                      ::= { maxAndMin  15 }

maxTimeStampOfIb      OBJECT-TYPE
        	      	  SYNTAX DisplayString
                      ACCESS read-only
                      STATUS current
                      DESCRIPTION
                             "This is timestamp for MAX of I2.
                              Time Format: yyyy:mm:dd:hh:mm:ss"
                      ::= { maxAndMin  16 }

maxOfIc               OBJECT-TYPE
        	      	  SYNTAX Integer32
                      ACCESS read-only
                      STATUS current
                      DESCRIPTION
                             "This is MAX of I3.
                              Relationship(Primary&Secondary Mode): I=Rx *(CT1/CT2)/1000
                              Range:        -32768~32767"
                      ::= { maxAndMin  17 }

maxTimeStampOfIc      OBJECT-TYPE
        	      	  SYNTAX DisplayString
                      ACCESS read-only
                      STATUS current
                      DESCRIPTION
                             "This is timestamp for MAX of I3.
                              Time Format: yyyy:mm:dd:hh:mm:ss"
                      ::= { maxAndMin  18 }

maxOfSystemPower      OBJECT-TYPE
        	      	  SYNTAX Integer32
                      ACCESS read-only
                      STATUS current
                      DESCRIPTION
                             "This is MAX of system power.
                              Relationship(Primary&Secondary Mode): P=Rx *(PT1/PT2)*(CT1/CT2)
                              Range:        -32768~32767"
                      ::= { maxAndMin  19 }

maxTimeStampOfSystemPower   OBJECT-TYPE
        	      	  SYNTAX DisplayString
                      ACCESS read-only
                      STATUS current
                      DESCRIPTION
                             "This is timestamp for MAX of system power.
                              Time Format: yyyy:mm:dd:hh:mm:ss"
                      ::= { maxAndMin  20 }

maxOfSystemReactivePower   OBJECT-TYPE
        	      	       SYNTAX Integer32
                           ACCESS read-only
                           STATUS current
                           DESCRIPTION
                                  "This is MAX of system reactive power.
                                  Relationship(Primary&Secondary Mode): P=Rx *(PT1/PT2)*(CT1/CT2)
                                  Range:        -32768~32767"
                           ::= { maxAndMin  21 }

maxTimeStampOfSystemReactivePower   OBJECT-TYPE
        	      	       SYNTAX DisplayString
                           ACCESS read-only
                           STATUS current
                           DESCRIPTION
                                  "This is timestamp for MAX of system reactive power.
                                   Time Format: yyyy:mm:dd:hh:mm:ss"
                           ::= { maxAndMin  22 }

maxOfSystemApparentPower   OBJECT-TYPE
        	      	       SYNTAX Integer32
                           ACCESS read-only
                           STATUS current
                           DESCRIPTION
                                  "This is MAX of system Apparent power.
                                   Relationship(Primary&Secondary Mode): S=Rx *(PT1/PT2)*(CT1/CT2)
                                   Range:        -32768~32767"
                           ::= { maxAndMin  23 }

maxTimeStampOfSystemApparentPower   OBJECT-TYPE
        	      	       SYNTAX DisplayString
                           ACCESS read-only
                           STATUS current
                           DESCRIPTION
                                  "This is timestamp for MAX of system Apparent power.
                                   Time Format: yyyy:mm:dd:hh:mm:ss"
                           ::= { maxAndMin  24 }

maxOfPowerFactor           OBJECT-TYPE
        	      	       SYNTAX Integer32
                           ACCESS read-only
                           STATUS current
                           DESCRIPTION
                                  "This is MAX of power factor.
                                   Relationship(Primary&Secondary Mode): PF=Rx/1000
                                   Range:        -32768~32767"
                           ::= { maxAndMin  25 }

maxTimeStampOfPowerFactor  OBJECT-TYPE
        	      	       SYNTAX DisplayString
                           ACCESS read-only
                           STATUS current
                           DESCRIPTION
                                  "This is timestamp for MAX of power factor.
                                   Time Format: yyyy:mm:dd:hh:mm:ss"
                           ::= { maxAndMin  26 }
                        
maxOfFrequency             OBJECT-TYPE
        	      	       SYNTAX Integer32
                           ACCESS read-only
                           STATUS current
                           DESCRIPTION
                                  "This is MAX of Frequency.
                                   Relationship(Primary&Secondary Mode): F=Rx/100
                                   Range:        -32768~32767"
                           ::= { maxAndMin  27 }

maxTimeStampOfFrequency    OBJECT-TYPE
        	      	       SYNTAX DisplayString
                           ACCESS read-only
                           STATUS current
                           DESCRIPTION
                                  "This is timestamp for MAX of Frequency.
                                   Time Format: yyyy:mm:dd:hh:mm:ss"
                           ::= { maxAndMin  28 }

maxOfPowerDemand           OBJECT-TYPE
        	      	       SYNTAX Integer32
                           ACCESS read-only
                           STATUS current
                           DESCRIPTION
                                  "This is MAX of power demand.
                                   Relationship(Primary&Secondary Mode): P=Rx *(PT1/PT2)*(CT1/CT2)
                                   Range:        -32768~32767"
                           ::= { maxAndMin  29 }

maxTimeStampOfPowerDemand  OBJECT-TYPE
        	      	       SYNTAX DisplayString
                           ACCESS read-only
                           STATUS current
                           DESCRIPTION
                                  "This is timestamp for MAX of power demand.
                                   Time Format: yyyy:mm:dd:hh:mm:ss"
                           ::= { maxAndMin  30 }

maxOfReactivePowerDemand   OBJECT-TYPE
        	      	       SYNTAX Integer32
                           ACCESS read-only
                           STATUS current
                           DESCRIPTION
                                  "This is MAX of Reactive power demand.
                                   Relationship(Primary&Secondary Mode): Q=Rx *(PT1/PT2)*(CT1/CT2)
                                   Range:        -32768~32767"
                           ::= { maxAndMin  31 }

maxTimeStampOfReactivePowerDemand  OBJECT-TYPE
        	      	       SYNTAX DisplayString
                           ACCESS read-only
                           STATUS current
                           DESCRIPTION
                                  "This is timestamp for MAX of Reactive power demand.
                                   Time Format: yyyy:mm:dd:hh:mm:ss"
                           ::= { maxAndMin  32 }

maxOfApparentPowerDemand   OBJECT-TYPE
        	      	       SYNTAX Integer32
                           ACCESS read-only
                           STATUS current
                           DESCRIPTION
                                  "This is MAX of Apparent power demand.
                                   Relationship(Primary&Secondary Mode): S=Rx *(PT1/PT2)*(CT1/CT2)
                                   Range:        -32768~32767"
                           ::= { maxAndMin  33 }

maxTimeStampOfApparentPowerDemand  OBJECT-TYPE
        	      	       SYNTAX DisplayString
                           ACCESS read-only
                           STATUS current
                           DESCRIPTION
                                  "This is timestamp for MAX of Apparent power demand.
                                   Time Format: yyyy:mm:dd:hh:mm:ss"
                           ::= { maxAndMin  34 }

maxOfVoltageUnbalanceFactor OBJECT-TYPE
        	      	       SYNTAX Integer32
                           ACCESS read-only
                           STATUS current
                           DESCRIPTION
                                  "This is MAX of voltage unbalance factor.
                                   Relationship(Primary&Secondary Mode): Unbl=(Rx/1000)*100%
                                   Range:        -32768~32767"
                           ::= { maxAndMin  35 }

maxTimeStampOfVoltageUnbalanceFactor  OBJECT-TYPE
        	      	       SYNTAX DisplayString
                           ACCESS read-only
                           STATUS current
                           DESCRIPTION
                                  "This is timestamp for MAX of voltage unbalance factor.
                                   Time Format: yyyy:mm:dd:hh:mm:ss"
                           ::= { maxAndMin  36 } 
                           
maxOfCurrentUnbalanceFactor OBJECT-TYPE
        	      	       SYNTAX Integer32
                           ACCESS read-only
                           STATUS current
                           DESCRIPTION
                                  "This is MAX of current unbalance factor.
                                   Relationship(Primary&Secondary Mode): Unbl=(Rx/1000)*100%
                                   Range:        -32768~32767"
                           ::= { maxAndMin  37 }

maxTimeStampOfCurrentUnbalanceFactor  OBJECT-TYPE
        	      	       SYNTAX DisplayString
                           ACCESS read-only
                           STATUS current
                           DESCRIPTION
                                  "This is timestamp for MAX of voltage current factor.
                                   Time Format: yyyy:mm:dd:hh:mm:ss"
                           ::= { maxAndMin  38 }
                           
maxOfUaTHD                 OBJECT-TYPE
        	      	       SYNTAX Integer32
                           ACCESS read-only
                           STATUS current
                           DESCRIPTION
                                  "This is MAX of V1(V12) THD.
                                   Relationship(Primary&Secondary Mode): THD=(Rx/10000)*100%
                                   Range:        -32768~32767"
                           ::= { maxAndMin  39 }

maxTimeStampOfUaTHD        OBJECT-TYPE
        	      	       SYNTAX DisplayString
                           ACCESS read-only
                           STATUS current
                           DESCRIPTION
                                  "This is timestamp for MAX of V1(V12) THD.
                                   Time Format: yyyy:mm:dd:hh:mm:ss"
                           ::= { maxAndMin  40 }

maxOfUbTHD                 OBJECT-TYPE
        	      	       SYNTAX Integer32
                           ACCESS read-only
                           STATUS current
                           DESCRIPTION
                                  "This is MAX of V2(V31) THD.
                                   Relationship(Primary&Secondary Mode): THD=(Rx/10000)*100%
                                   Range:        -32768~32767"
                           ::= { maxAndMin  41 }

maxTimeStampOfUbTHD        OBJECT-TYPE
        	      	       SYNTAX DisplayString
                           ACCESS read-only
                           STATUS current
                           DESCRIPTION
                                  "This is timestamp for MAX of V2(V31) THD.
                                   Time Format: yyyy:mm:dd:hh:mm:ss"
                           ::= { maxAndMin  42 }

maxOfUcTHD                 OBJECT-TYPE
        	      	       SYNTAX Integer32
                           ACCESS read-only
                           STATUS current
                           DESCRIPTION
                                  "This is MAX of V3(V23) THD.
                                   Relationship(Primary&Secondary Mode): THD=(Rx/10000)*100%
                                   Range:        -32768~32767"
                           ::= { maxAndMin  43 }

maxTimeStampOfUcTHD        OBJECT-TYPE
        	      	       SYNTAX DisplayString
                           ACCESS read-only
                           STATUS current
                           DESCRIPTION
                                  "This is timestamp for MAX of V3(V23) THD.
                                   Time Format: yyyy:mm:dd:hh:mm:ss"
                           ::= { maxAndMin  44 }

maxOfIaTHD                 OBJECT-TYPE
        	      	       SYNTAX Integer32
                           ACCESS read-only
                           STATUS current
                           DESCRIPTION
                                  "This is MAX of I1 THD.
                                   Relationship(Primary&Secondary Mode): THD=(Rx/10000)*100%
                                   Range:        -32768~32767"
                           ::= { maxAndMin  45 }

maxTimeStampOfIaTHD        OBJECT-TYPE
        	      	       SYNTAX DisplayString
                           ACCESS read-only
                           STATUS current
                           DESCRIPTION
                                  "This is timestamp for MAX of I1 THD.
                                   Time Format: yyyy:mm:dd:hh:mm:ss"
                           ::= { maxAndMin  46 }

maxOfIbTHD                 OBJECT-TYPE
        	      	       SYNTAX Integer32
                           ACCESS read-only
                           STATUS current
                           DESCRIPTION
                                  "This is MAX of I2 THD.
                                   Relationship(Primary&Secondary Mode): THD=(Rx/10000)*100%
                                   Range:        -32768~32767"
                           ::= { maxAndMin  47 }

maxTimeStampOfIbTHD        OBJECT-TYPE
        	      	       SYNTAX DisplayString
                           ACCESS read-only
                           STATUS current
                           DESCRIPTION
                                  "This is timestamp for MAX of I2 THD.
                                   Time Format: yyyy:mm:dd:hh:mm:ss"
                           ::= { maxAndMin  48 }
                           
 maxOfIcTHD                 OBJECT-TYPE
        	      	       SYNTAX Integer32
                           ACCESS read-only
                           STATUS current
                           DESCRIPTION
                                  "This is MAX of I3 THD.
                                   Relationship(Primary&Secondary Mode): THD=(Rx/10000)*100%
                                   Range:        -32768~32767"
                           ::= { maxAndMin  49 }

maxTimeStampOfIcTHD        OBJECT-TYPE
        	      	       SYNTAX DisplayString
                           ACCESS read-only
                           STATUS current
                           DESCRIPTION
                                  "This is timestamp for MAX of I3 THD.
                                   Time Format: yyyy:mm:dd:hh:mm:ss"
                           ::= { maxAndMin  50 }

minOfUa               OBJECT-TYPE
        	      	  SYNTAX Integer32
                      ACCESS read-only
                      STATUS current
                      DESCRIPTION
                             "This is MIN of V1.
                              Relationship(Primary&Secondary Mode): U=Rx *(PT1/PT2)/10
                              Range:        -32768~32767"
                      ::= { maxAndMin  51 }

minTimeStampOfUa      OBJECT-TYPE
        	      	  SYNTAX DisplayString
                      ACCESS read-only
                      STATUS current
                      DESCRIPTION
                             "This is timestamp for MIN of V1.
                              Time Format: yyyy:mm:dd:hh:mm:ss"
                      ::= { maxAndMin  52 }

minOfUb               OBJECT-TYPE
        	      	  SYNTAX Integer32
                      ACCESS read-only
                      STATUS current
                      DESCRIPTION
                             "This is MIN of V2.
                              Relationship(Primary&Secondary Mode): U=Rx *(PT1/PT2)/10
                              Range:        -32768~32767"
                      ::= { maxAndMin  53 }

minTimeStampOfUb      OBJECT-TYPE
        	      	  SYNTAX DisplayString
                      ACCESS read-only
                      STATUS current
                      DESCRIPTION
                             "This is timestamp for MIN of V2.
                              Time Format: yyyy:mm:dd:hh:mm:ss"
                      ::= { maxAndMin  54 }

minOfUc               OBJECT-TYPE
        	      	  SYNTAX Integer32
                      ACCESS read-only
                      STATUS current
                      DESCRIPTION
                             "This is MIN of V3.
                              Relationship(Primary&Secondary Mode): U=Rx *(PT1/PT2)/10
                              Range:        -32768~32767"
                      ::= { maxAndMin  55 }

minTimeStampOfUc      OBJECT-TYPE
        	      	  SYNTAX DisplayString
                      ACCESS read-only
                      STATUS current
                      DESCRIPTION
                             "This is timestamp for MIN of V3.
                              Time Format: yyyy:mm:dd:hh:mm:ss"
                      ::= { maxAndMin  56 }

minOfUab              OBJECT-TYPE
        	      	  SYNTAX Integer32
                      ACCESS read-only
                      STATUS current
                      DESCRIPTION
                             "This is MIN of V12.
                              Relationship(Primary&Secondary Mode): U=Rx *(PT1/PT2)/10
                              Range:        -32768~32767"
                      ::= { maxAndMin  57 }

minTimeStampOfUab      OBJECT-TYPE
        	      	  SYNTAX DisplayString
                      ACCESS read-only
                      STATUS current
                      DESCRIPTION
                             "This is timestamp for MIN of V12.
                              Time Format: yyyy:mm:dd:hh:mm:ss"
                      ::= { maxAndMin  58 }

minOfUbc              OBJECT-TYPE
        	      	  SYNTAX Integer32
                      ACCESS read-only
                      STATUS current
                      DESCRIPTION
                             "This is MIN of V23.
                              Relationship(Primary&Secondary Mode): U=Rx *(PT1/PT2)/10
                              Range:        -32768~32767"
                      ::= { maxAndMin  59 }

minTimeStampOfUbc     OBJECT-TYPE
        	      	  SYNTAX DisplayString
                      ACCESS read-only
                      STATUS current
                      DESCRIPTION
                             "This is timestamp for MIN of V23.
                              Time Format: yyyy:mm:dd:hh:mm:ss"
                      ::= { maxAndMin  60 }

minOfUca              OBJECT-TYPE
        	      	  SYNTAX Integer32
                      ACCESS read-only
                      STATUS current
                      DESCRIPTION
                             "This is MIN of V31.
                              Relationship(Primary&Secondary Mode): U=Rx *(PT1/PT2)/10
                              Range:        -32768~32767"
                      ::= { maxAndMin  61 }

minTimeStampOfUca     OBJECT-TYPE
        	      	  SYNTAX DisplayString
                      ACCESS read-only
                      STATUS current
                      DESCRIPTION
                             "This is timestamp for MIN of V31.
                              Time Format: yyyy:mm:dd:hh:mm:ss"
                      ::= { maxAndMin  62 }

minOfIa              OBJECT-TYPE
        	      	  SYNTAX Integer32
                      ACCESS read-only
                      STATUS current
                      DESCRIPTION
                             "This is MIN of I1.
                              Relationship(Primary&Secondary Mode): I=Rx *(CT1/CT2)/1000
                              Range:        -32768~32767"
                      ::= { maxAndMin  63 }

minTimeStampOfIa      OBJECT-TYPE
        	      	  SYNTAX DisplayString
                      ACCESS read-only
                      STATUS current
                      DESCRIPTION
                             "This is timestamp for MIN of I1.
                              Time Format: yyyy:mm:dd:hh:mm:ss"
                      ::= { maxAndMin  64 }

minOfIb              OBJECT-TYPE
        	      	  SYNTAX Integer32
                      ACCESS read-only
                      STATUS current
                      DESCRIPTION
                             "This is MIN of I2.
                              Relationship(Primary&Secondary Mode): I=Rx *(CT1/CT2)/1000
                              Range:        -32768~32767"
                      ::= { maxAndMin  65 }

minTimeStampOfIb      OBJECT-TYPE
        	      	  SYNTAX DisplayString
                      ACCESS read-only
                      STATUS current
                      DESCRIPTION
                             "This is timestamp for MIN of I2.
                              Time Format: yyyy:mm:dd:hh:mm:ss"
                      ::= { maxAndMin  66 }

minOfIc               OBJECT-TYPE
        	      	  SYNTAX Integer32
                      ACCESS read-only
                      STATUS current
                      DESCRIPTION
                             "This is MIN of I3.
                              Relationship(Primary&Secondary Mode): I=Rx *(CT1/CT2)/1000
                              Range:        -32768~32767"
                      ::= { maxAndMin  67 }

minTimeStampOfIc      OBJECT-TYPE
        	      	  SYNTAX DisplayString
                      ACCESS read-only
                      STATUS current
                      DESCRIPTION
                             "This is timestamp for MIN of I3.
                              Time Format: yyyy:mm:dd:hh:mm:ss"
                      ::= { maxAndMin  68 }

minOfSystemPower      OBJECT-TYPE
        	      	  SYNTAX Integer32
                      ACCESS read-only
                      STATUS current
                      DESCRIPTION
                             "This is MIN of system power.
                              Relationship(Primary&Secondary Mode): P=Rx *(PT1/PT2)*(CT1/CT2)
                              Range:        -32768~32767"
                      ::= { maxAndMin  69 }

minTimeStampOfSystemPower   OBJECT-TYPE
        	      	  SYNTAX DisplayString
                      ACCESS read-only
                      STATUS current
                      DESCRIPTION
                             "This is timestamp for MIN of system power.
                              Time Format: yyyy:mm:dd:hh:mm:ss"
                      ::= { maxAndMin  70 }

minOfSystemReactivePower   OBJECT-TYPE
        	      	       SYNTAX Integer32
                           ACCESS read-only
                           STATUS current
                           DESCRIPTION
                                  "This is MIN of system reactive power.
                                  Relationship(Primary&Secondary Mode): P=Rx *(PT1/PT2)*(CT1/CT2)
                                  Range:        -32768~32767"
                           ::= { maxAndMin  71 }

minTimeStampOfSystemReactivePower   OBJECT-TYPE
        	      	       SYNTAX DisplayString
                           ACCESS read-only
                           STATUS current
                           DESCRIPTION
                                  "This is timestamp for MIN of system reactive power.
                                   Time Format: yyyy:mm:dd:hh:mm:ss"
                           ::= { maxAndMin  72 }

minOfSystemApparentPower   OBJECT-TYPE
        	      	       SYNTAX Integer32
                           ACCESS read-only
                           STATUS current
                           DESCRIPTION
                                  "This is MIN of system Apparent power.
                                   Relationship(Primary&Secondary Mode): S=Rx *(PT1/PT2)*(CT1/CT2)
                                   Range:        -32768~32767"
                           ::= { maxAndMin  73 }

minTimeStampOfSystemApparentPower   OBJECT-TYPE
        	      	       SYNTAX DisplayString
                           ACCESS read-only
                           STATUS current
                           DESCRIPTION
                                  "This is timestamp for MIN of system Apparent power.
                                   Time Format: yyyy:mm:dd:hh:mm:ss"
                           ::= { maxAndMin  74 }

minOfPowerFactor           OBJECT-TYPE
        	      	       SYNTAX Integer32
                           ACCESS read-only
                           STATUS current
                           DESCRIPTION
                                  "This is MIN of power factor.
                                   Relationship(Primary&Secondary Mode): PF=Rx/1000
                                   Range:        -32768~32767"
                           ::= { maxAndMin  75 }

minTimeStampOfPowerFactor  OBJECT-TYPE
        	      	       SYNTAX DisplayString
                           ACCESS read-only
                           STATUS current
                           DESCRIPTION
                                  "This is timestamp for MIN of power factor.
                                   Time Format: yyyy:mm:dd:hh:mm:ss"
                           ::= { maxAndMin  76 }
                        
minOfFrequency             OBJECT-TYPE
        	      	       SYNTAX Integer32
                           ACCESS read-only
                           STATUS current
                           DESCRIPTION
                                  "This is MIN of Frequency.
                                   Relationship(Primary&Secondary Mode): F=Rx/100
                                   Range:        -32768~32767"
                           ::= { maxAndMin  77 }

minTimeStampOfFrequency    OBJECT-TYPE
        	      	       SYNTAX DisplayString
                           ACCESS read-only
                           STATUS current
                           DESCRIPTION
                                  "This is timestamp for MIN of Frequency.
                                   Time Format: yyyy:mm:dd:hh:mm:ss"
                           ::= { maxAndMin  78 }

minOfPowerDemand           OBJECT-TYPE
        	      	       SYNTAX Integer32
                           ACCESS read-only
                           STATUS current
                           DESCRIPTION
                                  "This is MIN of power demand.
                                   Relationship(Primary&Secondary Mode): P=Rx *(PT1/PT2)*(CT1/CT2)
                                   Range:        -32768~32767"
                           ::= { maxAndMin  79 }

minTimeStampOfPowerDemand  OBJECT-TYPE
        	      	       SYNTAX DisplayString
                           ACCESS read-only
                           STATUS current
                           DESCRIPTION
                                  "This is timestamp for MIN of power demand.
                                   Time Format: yyyy:mm:dd:hh:mm:ss"
                           ::= { maxAndMin  80 }

minOfReactivePowerDemand   OBJECT-TYPE
        	      	       SYNTAX Integer32
                           ACCESS read-only
                           STATUS current
                           DESCRIPTION
                                  "This is MIN of Reactive power demand.
                                   Relationship(Primary&Secondary Mode): Q=Rx *(PT1/PT2)*(CT1/CT2)
                                   Range:        -32768~32767"
                           ::= { maxAndMin  81 }

minTimeStampOfReactivePowerDemand  OBJECT-TYPE
        	      	       SYNTAX DisplayString
                           ACCESS read-only
                           STATUS current
                           DESCRIPTION
                                  "This is timestamp for MIN of Reactive power demand.
                                   Time Format: yyyy:mm:dd:hh:mm:ss"
                           ::= { maxAndMin  82 }

minOfApparentPowerDemand   OBJECT-TYPE
        	      	       SYNTAX Integer32
                           ACCESS read-only
                           STATUS current
                           DESCRIPTION
                                  "This is MIN of Apparent power demand.
                                   Relationship(Primary&Secondary Mode): S=Rx *(PT1/PT2)*(CT1/CT2)
                                   Range:        -32768~32767"
                           ::= { maxAndMin  83 }

minTimeStampOfApparentPowerDemand  OBJECT-TYPE
        	      	       SYNTAX DisplayString
                           ACCESS read-only
                           STATUS current
                           DESCRIPTION
                                  "This is timestamp for MIN of Apparent power demand.
                                   Time Format: yyyy:mm:dd:hh:mm:ss"
                           ::= { maxAndMin  84 }

minOfVoltageUnbalanceFactor OBJECT-TYPE
        	      	       SYNTAX Integer32
                           ACCESS read-only
                           STATUS current
                           DESCRIPTION
                                  "This is MIN of voltage unbalance factor.
                                   Relationship(Primary&Secondary Mode): Unbl=(Rx/1000)*100%
                                   Range:        -32768~32767"
                           ::= { maxAndMin  85 }

minTimeStampOfVoltageUnbalanceFactor  OBJECT-TYPE
        	      	       SYNTAX DisplayString
                           ACCESS read-only
                           STATUS current
                           DESCRIPTION
                                  "This is timestamp for MIN of voltage unbalance factor.
                                   Time Format: yyyy:mm:dd:hh:mm:ss"
                           ::= { maxAndMin  86 } 
                           
minOfCurrentUnbalanceFactor OBJECT-TYPE
        	      	       SYNTAX Integer32
                           ACCESS read-only
                           STATUS current
                           DESCRIPTION
                                  "This is MIN of current unbalance factor.
                                   Relationship(Primary&Secondary Mode): Unbl=(Rx/1000)*100%
                                   Range:        -32768~32767"
                           ::= { maxAndMin  87 }

minTimeStampOfCurrentUnbalanceFactor  OBJECT-TYPE
        	      	       SYNTAX DisplayString
                           ACCESS read-only
                           STATUS current
                           DESCRIPTION
                                  "This is timestamp for MIN of voltage current factor.
                                   Time Format: yyyy:mm:dd:hh:mm:ss"
                           ::= { maxAndMin  88 }
                           
minOfUaTHD                 OBJECT-TYPE
        	      	       SYNTAX Integer32
                           ACCESS read-only
                           STATUS current
                           DESCRIPTION
                                  "This is MIN of V1(V12) THD.
                                   Relationship(Primary&Secondary Mode): THD=(Rx/10000)*100%
                                   Range:        -32768~32767"
                           ::= { maxAndMin  89 }

minTimeStampOfUaTHD        OBJECT-TYPE
        	      	       SYNTAX DisplayString
                           ACCESS read-only
                           STATUS current
                           DESCRIPTION
                                  "This is timestamp for MIN of V1(V12) THD.
                                   Time Format: yyyy:mm:dd:hh:mm:ss"
                           ::= { maxAndMin  90 }

minOfUbTHD                 OBJECT-TYPE
        	      	       SYNTAX Integer32
                           ACCESS read-only
                           STATUS current
                           DESCRIPTION
                                  "This is MIN of V2(V31) THD.
                                   Relationship(Primary&Secondary Mode): THD=(Rx/10000)*100%
                                   Range:        -32768~32767"
                           ::= { maxAndMin  91 }

minTimeStampOfUbTHD        OBJECT-TYPE
        	      	       SYNTAX DisplayString
                           ACCESS read-only
                           STATUS current
                           DESCRIPTION
                                  "This is timestamp for MIN of V2(V31) THD.
                                   Time Format: yyyy:mm:dd:hh:mm:ss"
                           ::= { maxAndMin  92 }

minOfUcTHD                 OBJECT-TYPE
        	      	       SYNTAX Integer32
                           ACCESS read-only
                           STATUS current
                           DESCRIPTION
                                  "This is MIN of V3(V23) THD.
                                   Relationship(Primary&Secondary Mode): THD=(Rx/10000)*100%
                                   Range:        -32768~32767"
                           ::= { maxAndMin  93 }

minTimeStampOfUcTHD        OBJECT-TYPE
        	      	       SYNTAX DisplayString
                           ACCESS read-only
                           STATUS current
                           DESCRIPTION
                                  "This is timestamp for MIN of V3(V23) THD.
                                   Time Format: yyyy:mm:dd:hh:mm:ss"
                           ::= { maxAndMin  94 }

minOfIaTHD                 OBJECT-TYPE
        	      	       SYNTAX Integer32
                           ACCESS read-only
                           STATUS current
                           DESCRIPTION
                                  "This is MIN of I1 THD.
                                   Relationship(Primary&Secondary Mode): THD=(Rx/10000)*100%
                                   Range:        -32768~32767"
                           ::= { maxAndMin  95 }

minTimeStampOfIaTHD        OBJECT-TYPE
        	      	       SYNTAX DisplayString
                           ACCESS read-only
                           STATUS current
                           DESCRIPTION
                                  "This is timestamp for MIN of I1 THD.
                                   Time Format: yyyy:mm:dd:hh:mm:ss"
                           ::= { maxAndMin  96 }

minOfIbTHD                 OBJECT-TYPE
        	      	       SYNTAX Integer32
                           ACCESS read-only
                           STATUS current
                           DESCRIPTION
                                  "This is MIN of I2 THD.
                                   Relationship(Primary&Secondary Mode): THD=(Rx/10000)*100%
                                   Range:        -32768~32767"
                           ::= { maxAndMin  97 }

minTimeStampOfIbTHD        OBJECT-TYPE
        	      	       SYNTAX DisplayString
                           ACCESS read-only
                           STATUS current
                           DESCRIPTION
                                  "This is timestamp for MIN of I2 THD.
                                   Time Format: yyyy:mm:dd:hh:mm:ss"
                           ::= { maxAndMin  98 }
                           
minOfIcTHD                 OBJECT-TYPE
        	      	       SYNTAX Integer32
                           ACCESS read-only
                           STATUS current
                           DESCRIPTION
                                  "This is MIN of I3 THD.
                                   Relationship(Primary&Secondary Mode): THD=(Rx/10000)*100%
                                   Range:        -32768~32767"
                           ::= { maxAndMin  99 }

minTimeStampOfIcTHD        OBJECT-TYPE
        	      	       SYNTAX DisplayString
                           ACCESS read-only
                           STATUS current
                           DESCRIPTION
                                  "This is timestamp for MIN of I3 THD.
                                   Time Format: yyyy:mm:dd:hh:mm:ss"
                           ::= { maxAndMin  100 } 
                                                                                                              
-- ******************************************************************
--  ioStatus
-- ******************************************************************
--  the ioDIStatus GROUP(ioStatus.1)      
io11_DI1_Type       OBJECT-TYPE
        	        SYNTAX Integer32
        	        ACCESS read-only
                    STATUS current
                    DESCRIPTION
                            "This is DI1 Type of IO11.
                            Range:   0: DI,1: pulse counter"
                    ::= { ioDIStatus  1 } 

io11_DI1_Status     OBJECT-TYPE
        	      	SYNTAX Integer32
        	      	ACCESS read-only
                    STATUS current
                    DESCRIPTION
                           "This is DI1 Status of IO11, which is available when io11_DI1_Type is 0. 
                           Range:   1=ON,0=OFF"
                    ::= { ioDIStatus  2 } 

io11_DI1_Counter    OBJECT-TYPE
        	      	SYNTAX Counter32
        	      	ACCESS read-only
                    STATUS current
                    DESCRIPTION
                           "This is DI1 Counter of IO11, which is available when io11_DI1_Type is 1. 
                           Range:   0~4294967295"
                    ::= { ioDIStatus  3 } 

io11_DI2_Type       OBJECT-TYPE
        	        SYNTAX Integer32
        	        ACCESS read-only
                    STATUS current
                    DESCRIPTION
                            "This is DI2 Type of IO11.
                            Range:   0: DI,1: pulse counter"
                    ::= { ioDIStatus  4 } 

io11_DI2_Status     OBJECT-TYPE
        	      	SYNTAX Integer32
        	      	ACCESS read-only
                    STATUS current
                    DESCRIPTION
                           "This is DI2 Status of IO11, which is available when io11_DI2_Type is 0. 
                           Range:   1=ON,0=OFF"
                    ::= { ioDIStatus  5 } 

io11_DI2_Counter    OBJECT-TYPE
        	      	SYNTAX Counter32
        	      	ACCESS read-only
                    STATUS current
                    DESCRIPTION
                           "This is DI2 Counter of IO11, which is available when io11_DI2_Type is 1. 
                           Range:   0~4294967295"
                    ::= { ioDIStatus  6 }

io11_DI3_Type       OBJECT-TYPE
        	        SYNTAX Integer32
        	        ACCESS read-only
                    STATUS current
                    DESCRIPTION
                            "This is DI3 Type of IO11.
                            Range:   0: DI,1: pulse counter"
                    ::= { ioDIStatus  7 } 

io11_DI3_Status     OBJECT-TYPE
        	      	SYNTAX Integer32
        	      	ACCESS read-only
                    STATUS current
                    DESCRIPTION
                           "This is DI3 Status of IO11, which is available when io11_DI3_Type is 0. 
                           Range:   1=ON,0=OFF"
                    ::= { ioDIStatus  8 } 

io11_DI3_Counter    OBJECT-TYPE
        	      	SYNTAX Counter32
        	      	ACCESS read-only
                    STATUS current
                    DESCRIPTION
                           "This is DI3 Counter of IO11, which is available when io11_DI3_Type is 1. 
                           Range:   0~4294967295"
                    ::= { ioDIStatus  9 }

io11_DI4_Type       OBJECT-TYPE
        	        SYNTAX Integer32
        	        ACCESS read-only
                    STATUS current
                    DESCRIPTION
                            "This is DI4 Type of IO11.
                            Range:   0: DI,1: pulse counter"
                    ::= { ioDIStatus  10 } 

io11_DI4_Status     OBJECT-TYPE
        	      	SYNTAX Integer32
        	      	ACCESS read-only
                    STATUS current
                    DESCRIPTION
                           "This is DI4 Status of IO11, which is available when io11_DI4_Type is 0. 
                           Range:   1=ON,0=OFF"
                    ::= { ioDIStatus  11 } 

io11_DI4_Counter    OBJECT-TYPE
        	      	SYNTAX Counter32
        	      	ACCESS read-only
                    STATUS current
                    DESCRIPTION
                           "This is DI4 Counter of IO11, which is available when io11_DI4_Type is 1. 
                           Range:   0~4294967295"
                    ::= { ioDIStatus  12 }

io11_DI5_Type       OBJECT-TYPE
        	        SYNTAX Integer32
        	        ACCESS read-only
                    STATUS current
                    DESCRIPTION
                            "This is DI5 Type of IO11.
                            Range:   0: DI,1: pulse counter"
                    ::= { ioDIStatus  13 } 

io11_DI5_Status     OBJECT-TYPE
        	      	SYNTAX Integer32
        	      	ACCESS read-only
                    STATUS current
                    DESCRIPTION
                           "This is DI5 Status of IO11, which is available when io11_DI5_Type is 0. 
                           Range:   1=ON,0=OFF"
                    ::= { ioDIStatus  14 } 

io11_DI5_Counter    OBJECT-TYPE
        	      	SYNTAX Counter32
        	      	ACCESS read-only
                    STATUS current
                    DESCRIPTION
                           "This is DI5 Counter of IO11, which is available when io11_DI5_Type is 1. 
                           Range:   0~4294967295"
                    ::= { ioDIStatus  15 }

io11_DI6_Type       OBJECT-TYPE
        	        SYNTAX Integer32
        	        ACCESS read-only
                    STATUS current
                    DESCRIPTION
                            "This is DI6 Type of IO11.
                            Range:   0: DI,1: pulse counter"
                    ::= { ioDIStatus  16 } 

io11_DI6_Status     OBJECT-TYPE
        	      	SYNTAX Integer32
        	      	ACCESS read-only
                    STATUS current
                    DESCRIPTION
                           "This is DI6 Status of IO11, which is available when io11_DI6_Type is 0. 
                           Range:   1=ON,0=OFF"
                    ::= { ioDIStatus  17 } 

io11_DI6_Counter    OBJECT-TYPE
        	      	SYNTAX Counter32
        	      	ACCESS read-only
                    STATUS current
                    DESCRIPTION
                           "This is DI6 Counter of IO11, which is available when io11_DI6_Type is 1. 
                           Range:   0~4294967295"
                    ::= { ioDIStatus  18 }

io21_DI7_Type       OBJECT-TYPE
        	        SYNTAX Integer32
        	        ACCESS read-only
                    STATUS current
                    DESCRIPTION
                            "This is DI7 Type of IO21.
                            Range:   0: DI,1: pulse counter"
                    ::= { ioDIStatus  19 } 

io21_DI7_Status     OBJECT-TYPE
        	      	SYNTAX Integer32
        	      	ACCESS read-only
                    STATUS current
                    DESCRIPTION
                           "This is DI7 Status of IO21, which is available when io21_DI7_Type is 0. 
                           Range:   1=ON,0=OFF"
                    ::= { ioDIStatus  20 } 

io21_DI7_Counter    OBJECT-TYPE
        	      	SYNTAX Counter32
        	      	ACCESS read-only
                    STATUS current
                    DESCRIPTION
                           "This is DI7 Counter of IO21, which is available when io21_DI7_Type is 1. 
                           Range:   0~4294967295"
                    ::= { ioDIStatus  21 }

io21_DI8_Type       OBJECT-TYPE
        	        SYNTAX Integer32
        	        ACCESS read-only
                    STATUS current
                    DESCRIPTION
                            "This is DI8 Type of IO21.
                            Range:   0: DI,1: pulse counter"
                    ::= { ioDIStatus  22 } 

io21_DI8_Status     OBJECT-TYPE
        	      	SYNTAX Integer32
        	      	ACCESS read-only
                    STATUS current
                    DESCRIPTION
                           "This is DI8 Status of IO21, which is available when io21_DI8_Type is 0. 
                           Range:   1=ON,0=OFF"
                    ::= { ioDIStatus  23 } 

io21_DI8_Counter    OBJECT-TYPE
        	      	SYNTAX Counter32
        	      	ACCESS read-only
                    STATUS current
                    DESCRIPTION
                           "This is DI8 Counter of IO21, which is available when io21_DI8_Type is 1. 
                           Range:   0~4294967295"
                    ::= { ioDIStatus  24 }

io21_DI9_Type       OBJECT-TYPE
        	        SYNTAX Integer32
        	        ACCESS read-only
                    STATUS current
                    DESCRIPTION
                            "This is DI9 Type of IO21.
                            Range:   0: DI,1: pulse counter"
                    ::= { ioDIStatus  25 } 

io21_DI9_Status     OBJECT-TYPE
        	      	SYNTAX Integer32
        	      	ACCESS read-only
                    STATUS current
                    DESCRIPTION
                           "This is DI9 Status of IO21, which is available when io21_DI9_Type is 0. 
                           Range:   1=ON,0=OFF"
                    ::= { ioDIStatus  26 } 

io21_DI9_Counter    OBJECT-TYPE
        	      	SYNTAX Counter32
        	      	ACCESS read-only
                    STATUS current
                    DESCRIPTION
                           "This is DI9 Counter of IO21, which is available when io21_DI9_Type is 1. 
                           Range:   0~4294967295"
                    ::= { ioDIStatus  27 }

io21_DI10_Type       OBJECT-TYPE
        	        SYNTAX Integer32
        	        ACCESS read-only
                    STATUS current
                    DESCRIPTION
                            "This is DI10 Type of IO21.
                            Range:   0: DI,1: pulse counter"
                    ::= { ioDIStatus  28 } 

io21_DI10_Status     OBJECT-TYPE
        	      	SYNTAX Integer32
        	      	ACCESS read-only
                    STATUS current
                    DESCRIPTION
                           "This is DI10 Status of IO21, which is available when io21_DI10_Type is 0. 
                           Range:   1=ON,0=OFF"
                    ::= { ioDIStatus  29 } 

io21_DI10_Counter    OBJECT-TYPE
        	      	SYNTAX Counter32
        	      	ACCESS read-only
                    STATUS current
                    DESCRIPTION
                           "This is DI10 Counter of IO21, which is available when io21_DI10_Type is 1. 
                           Range:   0~4294967295"
                    ::= { ioDIStatus  30 }

io31_DI11_Type       OBJECT-TYPE
        	        SYNTAX Integer32
        	        ACCESS read-only
                    STATUS current
                    DESCRIPTION
                            "This is DI11 Type of IO31.
                            Range:   0: DI,1: pulse counter"
                    ::= { ioDIStatus  31 } 

io31_DI11_Status     OBJECT-TYPE
        	      	SYNTAX Integer32
        	      	ACCESS read-only
                    STATUS current
                    DESCRIPTION
                           "This is DI11 Status of IO31, which is available when io31_DI11_Type is 0. 
                           Range:   1=ON,0=OFF"
                    ::= { ioDIStatus  32 } 

io31_DI11_Counter    OBJECT-TYPE
        	      	SYNTAX Counter32
        	      	ACCESS read-only
                    STATUS current
                    DESCRIPTION
                           "This is DI11 Counter of IO31, which is available when io31_DI11_Type is 1. 
                           Range:   0~4294967295"
                    ::= { ioDIStatus  33 }

io31_DI12_Type       OBJECT-TYPE
        	        SYNTAX Integer32
        	        ACCESS read-only
                    STATUS current
                    DESCRIPTION
                            "This is DI12 Type of IO31.
                            Range:   0: DI,1: pulse counter"
                    ::= { ioDIStatus  34 } 

io31_DI12_Status     OBJECT-TYPE
        	      	SYNTAX Integer32
        	      	ACCESS read-only
                    STATUS current
                    DESCRIPTION
                           "This is DI12 Status of IO31, which is available when io31_DI12_Type is 0. 
                           Range:   1=ON,0=OFF"
                    ::= { ioDIStatus  35 } 

io31_DI12_Counter    OBJECT-TYPE
        	      	SYNTAX Counter32
        	      	ACCESS read-only
                    STATUS current
                    DESCRIPTION
                           "This is DI12 Counter of IO31, which is available when io31_DI12_Type is 1. 
                           Range:   0~4294967295"
                    ::= { ioDIStatus  36 }

io31_DI13_Type       OBJECT-TYPE
        	        SYNTAX Integer32
        	        ACCESS read-only
                    STATUS current
                    DESCRIPTION
                            "This is DI13 Type of IO31.
                            Range:   0: DI,1: pulse counter"
                    ::= { ioDIStatus  37 } 

io31_DI13_Status     OBJECT-TYPE
        	      	SYNTAX Integer32
        	      	ACCESS read-only
                    STATUS current
                    DESCRIPTION
                           "This is DI13 Status of IO31, which is available when io31_DI13_Type is 0. 
                           Range:   1=ON,0=OFF"
                    ::= { ioDIStatus  38 } 

io31_DI13_Counter    OBJECT-TYPE
        	      	SYNTAX Counter32
        	      	ACCESS read-only
                    STATUS current
                    DESCRIPTION
                           "This is DI13 Counter of IO31, which is available when io31_DI13_Type is 1. 
                           Range:   0~4294967295"
                    ::= { ioDIStatus  39 }

io31_DI14_Type       OBJECT-TYPE
        	        SYNTAX Integer32
        	        ACCESS read-only
                    STATUS current
                    DESCRIPTION
                            "This is DI14 Type of IO31.
                            Range:   0: DI,1: pulse counter"
                    ::= { ioDIStatus  40 } 

io31_DI14_Status     OBJECT-TYPE
        	      	SYNTAX Integer32
        	      	ACCESS read-only
                    STATUS current
                    DESCRIPTION
                           "This is DI14 Status of IO31, which is available when io31_DI14_Type is 0. 
                           Range:   1=ON,0=OFF"
                    ::= { ioDIStatus  41 } 

io31_DI14_Counter    OBJECT-TYPE
        	      	SYNTAX Counter32
        	      	ACCESS read-only
                    STATUS current
                    DESCRIPTION
                           "This is DI14 Counter of IO31, which is available when io31_DI14_Type is 1. 
                           Range:   0~4294967295"
                    ::= { ioDIStatus  42 }

io12_DI15_Type       OBJECT-TYPE
        	        SYNTAX Integer32
        	        ACCESS read-only
                    STATUS current
                    DESCRIPTION
                            "This is DI15 Type of IO12.
                            Range:   0: DI,1: pulse counter"
                    ::= { ioDIStatus  43 } 

io12_DI15_Status     OBJECT-TYPE
        	      	SYNTAX Integer32
        	      	ACCESS read-only
                    STATUS current
                    DESCRIPTION
                           "This is DI15 Status of IO12, which is available when io12_DI15_Type is 0. 
                           Range:   1=ON,0=OFF"
                    ::= { ioDIStatus  44 } 

io12_DI15_Counter    OBJECT-TYPE
        	      	SYNTAX Counter32
        	      	ACCESS read-only
                    STATUS current
                    DESCRIPTION
                           "This is DI15 Counter of IO12, which is available when io12_DI15_Type is 1. 
                           Range:   0~4294967295"
                    ::= { ioDIStatus  45 }

io12_DI16_Type       OBJECT-TYPE
        	        SYNTAX Integer32
        	        ACCESS read-only
                    STATUS current
                    DESCRIPTION
                            "This is DI16 Type of IO12.
                            Range:   0: DI,1: pulse counter"
                    ::= { ioDIStatus  46 } 

io12_DI16_Status     OBJECT-TYPE
        	      	SYNTAX Integer32
        	      	ACCESS read-only
                    STATUS current
                    DESCRIPTION
                           "This is DI16 Status of IO12, which is available when io12_DI16_Type is 0. 
                           Range:   1=ON,0=OFF"
                    ::= { ioDIStatus  47 } 

io12_DI16_Counter    OBJECT-TYPE
        	      	SYNTAX Counter32
        	      	ACCESS read-only
                    STATUS current
                    DESCRIPTION
                           "This is DI16 Counter of IO12, which is available when io12_DI16_Type is 1. 
                           Range:   0~4294967295"
                    ::= { ioDIStatus  48 }

io12_DI17_Type       OBJECT-TYPE
        	        SYNTAX Integer32
        	        ACCESS read-only
                    STATUS current
                    DESCRIPTION
                            "This is DI17 Type of IO12.
                            Range:   0: DI,1: pulse counter"
                    ::= { ioDIStatus  49 } 

io12_DI17_Status     OBJECT-TYPE
        	      	SYNTAX Integer32
        	      	ACCESS read-only
                    STATUS current
                    DESCRIPTION
                           "This is DI17 Status of IO12, which is available when io12_DI17_Type is 0. 
                           Range:   1=ON,0=OFF"
                    ::= { ioDIStatus  50 } 

io12_DI17_Counter    OBJECT-TYPE
        	      	SYNTAX Counter32
        	      	ACCESS read-only
                    STATUS current
                    DESCRIPTION
                           "This is DI17 Counter of IO12, which is available when io12_DI17_Type is 1. 
                           Range:   0~4294967295"
                    ::= { ioDIStatus  51 }

io12_DI18_Type       OBJECT-TYPE
        	        SYNTAX Integer32
        	        ACCESS read-only
                    STATUS current
                    DESCRIPTION
                            "This is DI18 Type of IO12.
                            Range:   0: DI,1: pulse counter"
                    ::= { ioDIStatus  52 } 

io12_DI18_Status     OBJECT-TYPE
        	      	SYNTAX Integer32
        	      	ACCESS read-only
                    STATUS current
                    DESCRIPTION
                           "This is DI18 Status of IO12, which is available when io12_DI18_Type is 0. 
                           Range:   1=ON,0=OFF"
                    ::= { ioDIStatus  53 } 

io12_DI18_Counter    OBJECT-TYPE
        	      	SYNTAX Counter32
        	      	ACCESS read-only
                    STATUS current
                    DESCRIPTION
                           "This is DI18 Counter of IO12, which is available when io12_DI18_Type is 1. 
                           Range:   0~4294967295"
                    ::= { ioDIStatus  54 }

io12_DI19_Type       OBJECT-TYPE
        	        SYNTAX Integer32
        	        ACCESS read-only
                    STATUS current
                    DESCRIPTION
                            "This is DI19 Type of IO12.
                            Range:   0: DI,1: pulse counter"
                    ::= { ioDIStatus  55 } 

io12_DI19_Status     OBJECT-TYPE
        	      	SYNTAX Integer32
        	      	ACCESS read-only
                    STATUS current
                    DESCRIPTION
                           "This is DI19 Status of IO12, which is available when io12_DI19_Type is 0. 
                           Range:   1=ON,0=OFF"
                    ::= { ioDIStatus  56 } 

io12_DI19_Counter    OBJECT-TYPE
        	      	SYNTAX Counter32
        	      	ACCESS read-only
                    STATUS current
                    DESCRIPTION
                           "This is DI19 Counter of IO12, which is available when io12_DI19_Type is 1. 
                           Range:   0~4294967295"
                    ::= { ioDIStatus  57 }

io12_DI20_Type       OBJECT-TYPE
        	        SYNTAX Integer32
        	        ACCESS read-only
                    STATUS current
                    DESCRIPTION
                            "This is DI20 Type of IO12.
                            Range:   0: DI,1: pulse counter"
                    ::= { ioDIStatus  58 } 

io12_DI20_Status     OBJECT-TYPE
        	      	SYNTAX Integer32
        	      	ACCESS read-only
                    STATUS current
                    DESCRIPTION
                           "This is DI20 Status of IO12, which is available when io12_DI20_Type is 0. 
                           Range:   1=ON,0=OFF"
                    ::= { ioDIStatus  59 } 

io12_DI20_Counter    OBJECT-TYPE
        	      	SYNTAX Counter32
        	      	ACCESS read-only
                    STATUS current
                    DESCRIPTION
                           "This is DI20 Counter of IO12, which is available when io12_DI20_Type is 1. 
                           Range:   0~4294967295"
                    ::= { ioDIStatus  60 }

io22_DI21_Type       OBJECT-TYPE
        	        SYNTAX Integer32
        	        ACCESS read-only
                    STATUS current
                    DESCRIPTION
                            "This is DI21 Type of IO22.
                            Range:   0: DI,1: pulse counter"
                    ::= { ioDIStatus  61 } 

io22_DI21_Status     OBJECT-TYPE
        	      	SYNTAX Integer32
        	      	ACCESS read-only
                    STATUS current
                    DESCRIPTION
                           "This is DI21 Status of IO22, which is available when io22_DI21_Type is 0. 
                           Range:   1=ON,0=OFF"
                    ::= { ioDIStatus  62 } 

io22_DI21_Counter    OBJECT-TYPE
        	      	SYNTAX Counter32
        	      	ACCESS read-only
                    STATUS current
                    DESCRIPTION
                           "This is DI21 Counter of IO22, which is available when io22_DI21_Type is 1. 
                           Range:   0~4294967295"
                    ::= { ioDIStatus  63 }

io22_DI22_Type       OBJECT-TYPE
        	        SYNTAX Integer32
        	        ACCESS read-only
                    STATUS current
                    DESCRIPTION
                            "This is DI22 Type of IO22.
                            Range:   0: DI,1: pulse counter"
                    ::= { ioDIStatus  64 } 

io22_DI22_Status     OBJECT-TYPE
        	      	SYNTAX Integer32
        	      	ACCESS read-only
                    STATUS current
                    DESCRIPTION
                           "This is DI22 Status of IO22, which is available when io22_DI22_Type is 0. 
                           Range:   1=ON,0=OFF"
                    ::= { ioDIStatus  65 } 

io22_DI22_Counter    OBJECT-TYPE
        	      	SYNTAX Counter32
        	      	ACCESS read-only
                    STATUS current
                    DESCRIPTION
                           "This is DI22 Counter of IO22, which is available when io22_DI22_Type is 1. 
                           Range:   0~4294967295"
                    ::= { ioDIStatus  66 }

io22_DI23_Type       OBJECT-TYPE
        	        SYNTAX Integer32
        	        ACCESS read-only
                    STATUS current
                    DESCRIPTION
                            "This is DI23 Type of IO22.
                            Range:   0: DI,1: pulse counter"
                    ::= { ioDIStatus  67 } 

io22_DI23_Status     OBJECT-TYPE
        	      	SYNTAX Integer32
        	      	ACCESS read-only
                    STATUS current
                    DESCRIPTION
                           "This is DI23 Status of IO22, which is available when io22_DI23_Type is 0. 
                           Range:   1=ON,0=OFF"
                    ::= { ioDIStatus  68 } 

io22_DI23_Counter    OBJECT-TYPE
        	      	SYNTAX Counter32
        	      	ACCESS read-only
                    STATUS current
                    DESCRIPTION
                           "This is DI23 Counter of IO22, which is available when io22_DI23_Type is 1. 
                           Range:   0~4294967295"
                    ::= { ioDIStatus  69 }

io22_DI24_Type       OBJECT-TYPE
        	        SYNTAX Integer32
        	        ACCESS read-only
                    STATUS current
                    DESCRIPTION
                            "This is DI24 Type of IO22.
                            Range:   0: DI,1: pulse counter"
                    ::= { ioDIStatus  70 } 

io22_DI24_Status     OBJECT-TYPE
        	      	SYNTAX Integer32
        	      	ACCESS read-only
                    STATUS current
                    DESCRIPTION
                           "This is DI24 Status of IO22, which is available when io22_DI24_Type is 0. 
                           Range:   1=ON,0=OFF"
                    ::= { ioDIStatus  71 } 

io22_DI24_Counter    OBJECT-TYPE
        	      	SYNTAX Counter32
        	      	ACCESS read-only
                    STATUS current
                    DESCRIPTION
                           "This is DI24 Counter of IO22, which is available when io22_DI24_Type is 1. 
                           Range:   0~4294967295"
                    ::= { ioDIStatus  72 }
io32_DI25_Type       OBJECT-TYPE
        	        SYNTAX Integer32
        	        ACCESS read-only
                    STATUS current
                    DESCRIPTION
                            "This is DI25 Type of IO32.
                            Range:   0: DI,1: pulse counter"
                    ::= { ioDIStatus  73 } 

io32_DI25_Status     OBJECT-TYPE
        	      	SYNTAX Integer32
        	      	ACCESS read-only
                    STATUS current
                    DESCRIPTION
                           "This is DI25 Status of IO32, which is available when io22_DI25_Type is 0. 
                           Range:   1=ON,0=OFF"
                    ::= { ioDIStatus  74 } 

io32_DI25_Counter    OBJECT-TYPE
        	      	SYNTAX Counter32
        	      	ACCESS read-only
                    STATUS current
                    DESCRIPTION
                           "This is DI25 Counter of IO32, which is available when io22_DI25_Type is 1. 
                           Range:   0~4294967295"
                    ::= { ioDIStatus  75 }

io32_DI26_Type       OBJECT-TYPE
        	        SYNTAX Integer32
        	        ACCESS read-only
                    STATUS current
                    DESCRIPTION
                            "This is DI26 Type of IO32.
                            Range:   0: DI,1: pulse counter"
                    ::= { ioDIStatus  76 } 

io32_DI26_Status     OBJECT-TYPE
        	      	SYNTAX Integer32
        	      	ACCESS read-only
                    STATUS current
                    DESCRIPTION
                           "This is DI26 Status of IO32, which is available when io22_DI26_Type is 0. 
                           Range:   1=ON,0=OFF"
                    ::= { ioDIStatus  77 } 

io32_DI26_Counter    OBJECT-TYPE
        	      	SYNTAX Counter32
        	      	ACCESS read-only
                    STATUS current
                    DESCRIPTION
                           "This is DI26 Counter of IO32, which is available when io22_DI26_Type is 1. 
                           Range:   0~4294967295"
                    ::= { ioDIStatus  78 }

io32_DI27_Type       OBJECT-TYPE
        	        SYNTAX Integer32
        	        ACCESS read-only
                    STATUS current
                    DESCRIPTION
                            "This is DI27 Type of IO32.
                            Range:   0: DI,1: pulse counter"
                    ::= { ioDIStatus  79 } 

io32_DI27_Status     OBJECT-TYPE
        	      	SYNTAX Integer32
        	      	ACCESS read-only
                    STATUS current
                    DESCRIPTION
                           "This is DI27 Status of IO32, which is available when io22_DI27_Type is 0. 
                           Range:   1=ON,0=OFF"
                    ::= { ioDIStatus  80 } 

io32_DI27_Counter    OBJECT-TYPE
        	      	SYNTAX Counter32
        	      	ACCESS read-only
                    STATUS current
                    DESCRIPTION
                           "This is DI27 Counter of IO32, which is available when io22_DI27_Type is 1. 
                           Range:   0~4294967295"
                    ::= { ioDIStatus  81 }

io32_DI28_Type       OBJECT-TYPE
        	        SYNTAX Integer32
        	        ACCESS read-only
                    STATUS current
                    DESCRIPTION
                            "This is DI28 Type of IO32.
                            Range:   0: DI,1: pulse counter"
                    ::= { ioDIStatus  82 } 

io32_DI28_Status     OBJECT-TYPE
        	      	SYNTAX Integer32
        	      	ACCESS read-only
                    STATUS current
                    DESCRIPTION
                           "This is DI28 Status of IO32, which is available when io22_DI28_Type is 0. 
                           Range:   1=ON,0=OFF"
                    ::= { ioDIStatus  83 } 

io32_DI28_Counter    OBJECT-TYPE
        	      	SYNTAX Counter32
        	      	ACCESS read-only
                    STATUS current
                    DESCRIPTION
                           "This is DI28 Counter of IO32, which is available when io22_DI28_Type is 1. 
                           Range:   0~4294967295"
                    ::= { ioDIStatus  84 }
                                         
--  the ioAIStatus GROUP(ioStatus.2)   
io22_AI1            OBJECT-TYPE
        	      	SYNTAX Integer32
        	      	ACCESS read-only
                    STATUS current
                    DESCRIPTION
                           "This is AI1 sampling value of IO22. 
                           Range:   0~4095"
                    ::= { ioAIStatus  1 } 

io22_AI2            OBJECT-TYPE
        	      	SYNTAX Integer32
        	      	ACCESS read-only
                    STATUS current
                    DESCRIPTION
                           "This is AI2 sampling value of IO22. 
                           Range:   0~4095"
                    ::= { ioAIStatus  2 } 

io32_AI3            OBJECT-TYPE
        	      	SYNTAX Integer32
        	      	ACCESS read-only
                    STATUS current
                    DESCRIPTION
                           "This is AI3 sampling value of IO32. 
                           Range:   0~4095"
                    ::= { ioAIStatus  3 }
                     
io32_AI4            OBJECT-TYPE
        	      	SYNTAX Integer32
        	      	ACCESS read-only
                    STATUS current
                    DESCRIPTION
                           "This is AI4 sampling value of IO32. 
                           Range:   0~4095"
                    ::= { ioAIStatus  4 } 

--  the ioAOStatus GROUP(ioStatus.3)   
io21_AO1            OBJECT-TYPE
        	      	SYNTAX Integer32
        	      	ACCESS read-only
                    STATUS current
                    DESCRIPTION
                           "This is AO1 sampling value of IO21. 
                           Type:  float"
                    ::= { ioAOStatus  1 } 

io21_AO2            OBJECT-TYPE
        	      	SYNTAX Integer32
        	      	ACCESS read-only
                    STATUS current
                    DESCRIPTION
                           "This is AO2 sampling value of IO21. 
                           Type:  float"
                    ::= { ioAOStatus  2 } 

io22_AO3            OBJECT-TYPE
        	      	SYNTAX Integer32
        	      	ACCESS read-only
                    STATUS current
                    DESCRIPTION
                           "This is AO3 sampling value of IO22. 
                           Type:  float"
                    ::= { ioAOStatus  3 }
                     
io22_AO4            OBJECT-TYPE
        	      	SYNTAX Integer32
        	      	ACCESS read-only
                    STATUS current
                    DESCRIPTION
                           "This is AO4 sampling value of IO22. 
                           Type:  float"
                    ::= { ioAOStatus  4 } 

--  the ioRelayStatus GROUP(ioStatus.4)   
io11_relay1         OBJECT-TYPE
        	      	SYNTAX Integer32
        	      	ACCESS read-only
                    STATUS current
                    DESCRIPTION
                           "This is Relay 1 Status.
                           Range:  1=ON,0=OFF"
                    ::= { ioRelayStatus  1 } 
                    
io11_relay2         OBJECT-TYPE
        	      	SYNTAX Integer32
        	      	ACCESS read-only
                    STATUS current
                    DESCRIPTION
                           "This is Relay 2 Status.
                           Range:  1=ON,0=OFF"
                    ::= { ioRelayStatus  2 } 
                    
io31_relay3         OBJECT-TYPE
        	      	SYNTAX Integer32
        	      	ACCESS read-only
                    STATUS current
                    DESCRIPTION
                           "This is Relay 3 Status.
                           Range:  1=ON,0=OFF"
                    ::= { ioRelayStatus  3 } 
                    
io31_relay4         OBJECT-TYPE
        	      	SYNTAX Integer32
        	      	ACCESS read-only
                    STATUS current
                    DESCRIPTION
                           "This is Relay 4 Status.
                           Range:  1=ON,0=OFF"
                    ::= { ioRelayStatus  4 } 
                    
io12_relay5         OBJECT-TYPE
        	      	SYNTAX Integer32
        	      	ACCESS read-only
                    STATUS current
                    DESCRIPTION
                           "This is Relay 5 Status.
                           Range:  1=ON,0=OFF"
                    ::= { ioRelayStatus  5 }   

io12_relay6         OBJECT-TYPE
        	      	SYNTAX Integer32
        	      	ACCESS read-only
                    STATUS current
                    DESCRIPTION
                           "This is Relay 6 Status.
                           Range:  1=ON,0=OFF"
                    ::= { ioRelayStatus  6 }

io32_relay7         OBJECT-TYPE
        	      	SYNTAX Integer32
        	      	ACCESS read-only
                    STATUS current
                    DESCRIPTION
                           "This is Relay 7 Status.
                           Range:  1=ON,0=OFF"
                    ::= { ioRelayStatus  7 }

io32_relay8         OBJECT-TYPE
        	      	SYNTAX Integer32
        	      	ACCESS read-only
                    STATUS current
                    DESCRIPTION
                           "This is Relay 8 Status.
                           Range:  1=ON,0=OFF"
                    ::= { ioRelayStatus  8 }
                    
-- ******************************************************************
--  setting
-- ******************************************************************
voltageInputWiringType     OBJECT-TYPE
        	      	       SYNTAX Integer32
        	      	       ACCESS read-only
                           STATUS current
                           DESCRIPTION
                                  "This is Voltage input wiring type.
                                   Range:   0:3LN,1:2LN,2:2LL,3:3LL"
                           ::= { setting  2 } 

currentInputWiringType     OBJECT-TYPE
        	      	       SYNTAX Integer32
        	      	       ACCESS read-only
                           STATUS current
                           DESCRIPTION
                                  "This is current input wiring type.
                                   Range:   0:3CT,1:1CT,2:2CTL"
                           ::= { setting  3 } 

pt1                        OBJECT-TYPE
        	      	       SYNTAX Integer32
        	      	       ACCESS read-only
                           STATUS current
                           DESCRIPTION
                                  "This is PT1.
                                   Range:   50.0~500000.0"
                           ::= { setting  4 } 

pt2                        OBJECT-TYPE
        	      	       SYNTAX Integer32
        	      	       ACCESS read-only
                           STATUS current
                           DESCRIPTION
                                  "This is PT2.
                                   Range:   50.0~400.0"
                           ::= { setting  5 } 

ct1                        OBJECT-TYPE
        	      	       SYNTAX Integer32
        	      	       ACCESS read-only
                           STATUS current
                           DESCRIPTION
                                  "This is CT1.
                                   Range:   1~50000"
                           ::= { setting  6 } 

ct2                        OBJECT-TYPE
        	      	       SYNTAX Integer32
        	      	       ACCESS read-only
                           STATUS current
                           DESCRIPTION
                                  "This is CT2.
                                   Range:   1,5"
                           ::= { setting  7 } 

kWhPulseConstant           OBJECT-TYPE
        	      	       SYNTAX Integer32
        	      	       ACCESS read-only
                           STATUS current
                           DESCRIPTION
                                  "This is kWh pulse constant.
                                   Range:   1~6000"
                           ::= { setting  8 } 

kvarhPulseConstant         OBJECT-TYPE
        	      	       SYNTAX Integer32
        	      	       ACCESS read-only
                           STATUS current
                           DESCRIPTION
                                  "This is kvarh pulse constant.
                                   Range:   1~6000"
                           ::= { setting  9 } 

demandSlidWindowTime       OBJECT-TYPE
        	      	       SYNTAX Integer32
        	      	       ACCESS read-only
                           STATUS current
                           DESCRIPTION
                                  "This is kvarh pulse constant.
                                   Range:   1~6000"
                           ::= { setting  10 } 

demandCalculatingMode      OBJECT-TYPE
        	      	       SYNTAX Integer32
        	      	       ACCESS read-only
                           STATUS current
                           DESCRIPTION
                                  "This is Demand calculating mode.
                                   Range:   1:sliding window, 2:thermal"
                           ::= { setting  11 }
                           
currentIadirection         OBJECT-TYPE
        	      	       SYNTAX Integer32
        	      	       ACCESS read-only
                           STATUS current
                           DESCRIPTION
                                  "This is Current Ia direction.
                                   Range:  0: Positive 1: Negative"
                           ::= { setting  12 }

currentIbdirection         OBJECT-TYPE
        	      	       SYNTAX Integer32
        	      	       ACCESS read-only
                           STATUS current
                           DESCRIPTION
                                  "This is Current Ib direction.
                                   Range:  0: Positive 1: Negative"
                           ::= { setting  13 }

currentIcdirection         OBJECT-TYPE
        	      	       SYNTAX Integer32
        	      	       ACCESS read-only
                           STATUS current
                           DESCRIPTION
                                  "This is Current Ic direction.
                                   Range:  0: Positive 1: Negative"
                           ::= { setting  14 }

varAndPFConvention         OBJECT-TYPE
        	      	       SYNTAX Integer32
        	      	       ACCESS read-only
                           STATUS current
                           DESCRIPTION
                                  "This is VAR/PF convention.
                                   Range:  0: IEC, 1: IEEE"
                           ::= { setting  15 }

energyCalculatingMode      OBJECT-TYPE
        	      	       SYNTAX Integer32
        	      	       ACCESS read-only
                           STATUS current
                           DESCRIPTION
                                  "This is Energy calculating mode.
                                   Range:  0: fundamental 1: full-wave"
                           ::= { setting  16 }

reactivePowerMeasuringMode OBJECT-TYPE
        	      	       SYNTAX Integer32
        	      	       ACCESS read-only
                           STATUS current
                           DESCRIPTION
                                  "This is Reactive power measuring mode.
                                   Range:  0: real, 1: general"
                           ::= { setting  17 }

energyDisplayMode          OBJECT-TYPE
        	      	       SYNTAX Integer32
        	      	       ACCESS read-only
                           STATUS current
                           DESCRIPTION
                                  "This is Energy display mode.
                                   Range:  0: primary, 1: secondary"
                           ::= { setting  18 }

basicParameterMode         OBJECT-TYPE
        	      	       SYNTAX Integer32
        	      	       ACCESS read-only
                           STATUS current
                           DESCRIPTION
                                  "This is Basic parameter mode.
                                   Range:  0:secondary; 1:primary"
                           ::= { setting  19 }

runtime                    OBJECT-TYPE
        	      	       SYNTAX Integer32
        	      	       ACCESS read-only
                           STATUS current
                           DESCRIPTION
                                  "This is Run time.
                                   Relationship(Primary&Secondary Mode): T=Rx/100
                                   Range:        0~999999999"
                           ::= { setting  20 }

--  the expandedIOModulesConnectStatus GROUP (setting.1)
axmIO11Status              OBJECT-TYPE
        	      	       SYNTAX Integer32
        	      	       ACCESS read-only
                           STATUS current
                           DESCRIPTION
                                  "This is Expanded IO11 Modules connecting status.
                                   Range:  0: disconnected,1: connected"
                           ::= { expandedIOModulesConnectStatus  1 }

axmIO12Status              OBJECT-TYPE
        	      	       SYNTAX Integer32
        	      	       ACCESS read-only
                           STATUS current
                           DESCRIPTION
                                  "This is Expanded IO12 Modules connecting status.
                                   Range:  0: disconnected,1: connected"
                           ::= { expandedIOModulesConnectStatus  2 }

axmIO21Status              OBJECT-TYPE
        	      	       SYNTAX Integer32
        	      	       ACCESS read-only
                           STATUS current
                           DESCRIPTION
                                  "This is Expanded IO21 Modules connecting status.
                                   Range:  0: disconnected,1: connected"
                           ::= { expandedIOModulesConnectStatus  3 }

axmIO22Status              OBJECT-TYPE
        	      	       SYNTAX Integer32
        	      	       ACCESS read-only
                           STATUS current
                           DESCRIPTION
                                  "This is Expanded IO22 Modules connecting status.
                                   Range:  0: disconnected,1: connected"
                           ::= { expandedIOModulesConnectStatus  4 }

axmIO31Status              OBJECT-TYPE
        	      	       SYNTAX Integer32
        	      	       ACCESS read-only
                           STATUS current
                           DESCRIPTION
                                  "This is Expanded IO31 Modules connecting status.
                                   Range:  0: disconnected,1: connected"
                           ::= { expandedIOModulesConnectStatus  5 }

axmIO32Status              OBJECT-TYPE
        	      	       SYNTAX Integer32
        	      	       ACCESS read-only
                           STATUS current
                           DESCRIPTION
                                  "This is Expanded IO32 Modules connecting status.
                                   Range:  0: disconnected,1: connected"
                           ::= { expandedIOModulesConnectStatus  6 }

-- ******************************************************************
--  timeOfUse
-- ******************************************************************
--  the currentMonthTou GROUP (timeOfUse.1)
currentMonthEpImpSharp     OBJECT-TYPE
        	      	       SYNTAX Integer32
        	      	       ACCESS read-only
                           STATUS current
                           DESCRIPTION
                                  "This is current month TOU energy of Ep_imp(sharp).
                                   Range:        0~99999999.9"
                           ::= { currentMonthTou  1 }

currentMonthEpExpSharp     OBJECT-TYPE
        	      	       SYNTAX Integer32
        	      	       ACCESS read-only
                           STATUS current
                           DESCRIPTION
                                  "This is current month TOU energy of Ep_exp(sharp).
                                   Range:        0~99999999.9"
                           ::= { currentMonthTou  2 }

currentMonthEqImpSharp     OBJECT-TYPE
        	      	       SYNTAX Integer32
        	      	       ACCESS read-only
                           STATUS current
                           DESCRIPTION
                                  "This is current month TOU energy of Eq_imp(sharp).
                                   Range:        0~99999999.9"
                           ::= { currentMonthTou  3 }

currentMonthEqExpSharp     OBJECT-TYPE
        	      	       SYNTAX Integer32
        	      	       ACCESS read-only
                           STATUS current
                           DESCRIPTION
                                  "This is current month TOU energy of Eq_exp(sharp).
                                   Range:        0~99999999.9"
                           ::= { currentMonthTou  4 }


currentMonthEsSharp        OBJECT-TYPE
        	      	       SYNTAX Integer32
        	      	       ACCESS read-only
                           STATUS current
                           DESCRIPTION
                                  "This is current month TOU energy of Es(sharp).
                                   Range:        0~99999999.9"
                           ::= { currentMonthTou  5 }

currentMonthEpImpPeak      OBJECT-TYPE
        	      	       SYNTAX Integer32
        	      	       ACCESS read-only
                           STATUS current
                           DESCRIPTION
                                  "This is current month TOU energy of Ep_imp(Peak).
                                   Range:        0~99999999.9"
                           ::= { currentMonthTou  6 }

currentMonthEpExpPeak      OBJECT-TYPE
        	      	       SYNTAX Integer32
        	      	       ACCESS read-only
                           STATUS current
                           DESCRIPTION
                                  "This is current month TOU energy of Ep_exp(Peak).
                                   Range:        0~99999999.9"
                           ::= { currentMonthTou  7 }

currentMonthEqImpPeak      OBJECT-TYPE
        	      	       SYNTAX Integer32
        	      	       ACCESS read-only
                           STATUS current
                           DESCRIPTION
                                  "This is current month TOU energy of Eq_imp(Peak).
                                   Range:        0~99999999.9"
                           ::= { currentMonthTou  8 }

currentMonthEqExpPeak      OBJECT-TYPE
        	      	       SYNTAX Integer32
        	      	       ACCESS read-only
                           STATUS current
                           DESCRIPTION
                                  "This is current month TOU energy of Eq_exp(Peak).
                                   Range:        0~99999999.9"
                           ::= { currentMonthTou  9 }


currentMonthEsPeak         OBJECT-TYPE
        	      	       SYNTAX Integer32
        	      	       ACCESS read-only
                           STATUS current
                           DESCRIPTION
                                  "This is current month TOU energy of Es(Peak).
                                   Range:        0~99999999.9"
                           ::= { currentMonthTou  10 }

currentMonthEpImpValley    OBJECT-TYPE
        	      	       SYNTAX Integer32
        	      	       ACCESS read-only
                           STATUS current
                           DESCRIPTION
                                  "This is current month TOU energy of Ep_imp(valley).
                                   Range:        0~99999999.9"
                           ::= { currentMonthTou  11 }

currentMonthEpExpValley    OBJECT-TYPE
        	      	       SYNTAX Integer32
        	      	       ACCESS read-only
                           STATUS current
                           DESCRIPTION
                                  "This is current month TOU energy of Ep_exp(valley).
                                   Range:        0~99999999.9"
                           ::= { currentMonthTou  12 }

currentMonthEqImpValley    OBJECT-TYPE
        	      	       SYNTAX Integer32
        	      	       ACCESS read-only
                           STATUS current
                           DESCRIPTION
                                  "This is current month TOU energy of Eq_imp(valley).
                                   Range:        0~99999999.9"
                           ::= { currentMonthTou  13 }

currentMonthEqExpValley    OBJECT-TYPE
        	      	       SYNTAX Integer32
        	      	       ACCESS read-only
                           STATUS current
                           DESCRIPTION
                                  "This is current month TOU energy of Eq_exp(valley).
                                   Range:        0~99999999.9"
                           ::= { currentMonthTou  14 }


currentMonthEsValley       OBJECT-TYPE
        	      	       SYNTAX Integer32
        	      	       ACCESS read-only
                           STATUS current
                           DESCRIPTION
                                  "This is current month TOU energy of Es(valley).
                                   Range:        0~99999999.9"
                           ::= { currentMonthTou  15 }

currentMonthEpImpNormal    OBJECT-TYPE
        	      	       SYNTAX Integer32
        	      	       ACCESS read-only
                           STATUS current
                           DESCRIPTION
                                  "This is current month TOU energy of Ep_imp(normal).
                                   Range:        0~99999999.9"
                           ::= { currentMonthTou  16 }

currentMonthEpExpNormal    OBJECT-TYPE
        	      	       SYNTAX Integer32
        	      	       ACCESS read-only
                           STATUS current
                           DESCRIPTION
                                  "This is current month TOU energy of Ep_exp(normal).
                                   Range:        0~99999999.9"
                           ::= { currentMonthTou  17 }

currentMonthEqImpNormal    OBJECT-TYPE
        	      	       SYNTAX Integer32
        	      	       ACCESS read-only
                           STATUS current
                           DESCRIPTION
                                  "This is current month TOU energy of Eq_imp(normal).
                                   Range:        0~99999999.9"
                           ::= { currentMonthTou  18 }

currentMonthEqExpNormal    OBJECT-TYPE
        	      	       SYNTAX Integer32
        	      	       ACCESS read-only
                           STATUS current
                           DESCRIPTION
                                  "This is current month TOU energy of Eq_exp(normal).
                                   Range:        0~99999999.9"
                           ::= { currentMonthTou  19 }


currentMonthEsNormal       OBJECT-TYPE
        	      	       SYNTAX Integer32
        	      	       ACCESS read-only
                           STATUS current
                           DESCRIPTION
                                  "This is current month TOU energy of Es(normal).
                                   Range:        0~99999999.9"
                           ::= { currentMonthTou  20 }

currentMonthEpImpSum       OBJECT-TYPE
        	      	       SYNTAX Integer32
        	      	       ACCESS read-only
                           STATUS current
                           DESCRIPTION
                                  "This is current month TOU energy of Ep_imp(sum).
                                   Range:        0~99999999.9"
                           ::= { currentMonthTou  21 }

currentMonthEpExpSum       OBJECT-TYPE
        	      	       SYNTAX Integer32
        	      	       ACCESS read-only
                           STATUS current
                           DESCRIPTION
                                  "This is current month TOU energy of Ep_exp(sum).
                                   Range:        0~99999999.9"
                           ::= { currentMonthTou  22 }

currentMonthEqImpSum       OBJECT-TYPE
        	      	       SYNTAX Integer32
        	      	       ACCESS read-only
                           STATUS current
                           DESCRIPTION
                                  "This is current month TOU energy of Eq_imp(sum).
                                   Range:        0~99999999.9"
                           ::= { currentMonthTou  23 }

currentMonthEqExpSum       OBJECT-TYPE
        	      	       SYNTAX Integer32
        	      	       ACCESS read-only
                           STATUS current
                           DESCRIPTION
                                  "This is current month TOU energy of Eq_exp(sum).
                                   Range:        0~99999999.9"
                           ::= { currentMonthTou  24 }


currentMonthEsSum          OBJECT-TYPE
        	      	       SYNTAX Integer32
        	      	       ACCESS read-only
                           STATUS current
                           DESCRIPTION
                                  "This is current month TOU energy of Es(sum).
                                   Range:        0~99999999.9"
                           ::= { currentMonthTou  25 }

--  the lastMonthTou GROUP (timeOfUse.2)
lastMonthEpImpSharp        OBJECT-TYPE
        	      	       SYNTAX Integer32
        	      	       ACCESS read-only
                           STATUS current
                           DESCRIPTION
                                  "This is last month TOU energy of Ep_imp(sharp).
                                   Range:        0~99999999.9"
                           ::= { lastMonthTou  1 }

lastMonthEpExpSharp        OBJECT-TYPE
        	      	       SYNTAX Integer32
        	      	       ACCESS read-only
                           STATUS current
                           DESCRIPTION
                                  "This is last month TOU energy of Ep_exp(sharp).
                                   Range:        0~99999999.9"
                           ::= { lastMonthTou  2 }

lastMonthEqImpSharp        OBJECT-TYPE
        	      	       SYNTAX Integer32
        	      	       ACCESS read-only
                           STATUS current
                           DESCRIPTION
                                  "This is last month TOU energy of Eq_imp(sharp).
                                   Range:        0~99999999.9"
                           ::= { lastMonthTou  3 }

lastMonthEqExpSharp        OBJECT-TYPE
        	      	       SYNTAX Integer32
        	      	       ACCESS read-only
                           STATUS current
                           DESCRIPTION
                                  "This is last month TOU energy of Eq_exp(sharp).
                                   Range:        0~99999999.9"
                           ::= { lastMonthTou  4 }


lastMonthEsSharp           OBJECT-TYPE
        	      	       SYNTAX Integer32
        	      	       ACCESS read-only
                           STATUS current
                           DESCRIPTION
                                  "This is last month TOU energy of Es(sharp).
                                   Range:        0~99999999.9"
                           ::= { lastMonthTou  5 }

lastMonthEpImpPeak         OBJECT-TYPE
        	      	       SYNTAX Integer32
        	      	       ACCESS read-only
                           STATUS current
                           DESCRIPTION
                                  "This is last month TOU energy of Ep_imp(Peak).
                                   Range:        0~99999999.9"
                           ::= { lastMonthTou  6 }

lastMonthEpExpPeak         OBJECT-TYPE
        	      	       SYNTAX Integer32
        	      	       ACCESS read-only
                           STATUS current
                           DESCRIPTION
                                  "This is last month TOU energy of Ep_exp(Peak).
                                   Range:        0~99999999.9"
                           ::= { lastMonthTou  7 }

lastMonthEqImpPeak         OBJECT-TYPE
        	      	       SYNTAX Integer32
        	      	       ACCESS read-only
                           STATUS current
                           DESCRIPTION
                                  "This is last month TOU energy of Eq_imp(Peak).
                                   Range:        0~99999999.9"
                           ::= { lastMonthTou  8 }

lastMonthEqExpPeak         OBJECT-TYPE
        	      	       SYNTAX Integer32
        	      	       ACCESS read-only
                           STATUS current
                           DESCRIPTION
                                  "This is last month TOU energy of Eq_exp(Peak).
                                   Range:        0~99999999.9"
                           ::= { lastMonthTou  9 }


lastMonthEsPeak            OBJECT-TYPE
        	      	       SYNTAX Integer32
        	      	       ACCESS read-only
                           STATUS current
                           DESCRIPTION
                                  "This is last month TOU energy of Es(Peak).
                                   Range:        0~99999999.9"
                           ::= { lastMonthTou  10 }

lastMonthEpImpValley       OBJECT-TYPE
        	      	       SYNTAX Integer32
        	      	       ACCESS read-only
                           STATUS current
                           DESCRIPTION
                                  "This is last month TOU energy of Ep_imp(valley).
                                   Range:        0~99999999.9"
                           ::= { lastMonthTou  11 }

lastMonthEpExpValley       OBJECT-TYPE
        	      	       SYNTAX Integer32
        	      	       ACCESS read-only
                           STATUS current
                           DESCRIPTION
                                  "This is last month TOU energy of Ep_exp(valley).
                                   Range:        0~99999999.9"
                           ::= { lastMonthTou  12 }

lastMonthEqImpValley       OBJECT-TYPE
        	      	       SYNTAX Integer32
        	      	       ACCESS read-only
                           STATUS current
                           DESCRIPTION
                                  "This is last month TOU energy of Eq_imp(valley).
                                   Range:        0~99999999.9"
                           ::= { lastMonthTou  13 }

lastMonthEqExpValley       OBJECT-TYPE
        	      	       SYNTAX Integer32
        	      	       ACCESS read-only
                           STATUS current
                           DESCRIPTION
                                  "This is last month TOU energy of Eq_exp(valley).
                                   Range:        0~99999999.9"
                           ::= { lastMonthTou  14 }


lastMonthEsValley          OBJECT-TYPE
        	      	       SYNTAX Integer32
        	      	       ACCESS read-only
                           STATUS current
                           DESCRIPTION
                                  "This is last month TOU energy of Es(valley).
                                   Range:        0~99999999.9"
                           ::= { lastMonthTou  15 }

lastMonthEpImpNormal       OBJECT-TYPE
        	      	       SYNTAX Integer32
        	      	       ACCESS read-only
                           STATUS current
                           DESCRIPTION
                                  "This is last month TOU energy of Ep_imp(normal).
                                   Range:        0~99999999.9"
                           ::= { lastMonthTou  16 }

lastMonthEpExpNormal       OBJECT-TYPE
        	      	       SYNTAX Integer32
        	      	       ACCESS read-only
                           STATUS current
                           DESCRIPTION
                                  "This is last month TOU energy of Ep_exp(normal).
                                   Range:        0~99999999.9"
                           ::= { lastMonthTou  17 }

lastMonthEqImpNormal       OBJECT-TYPE
        	      	       SYNTAX Integer32
        	      	       ACCESS read-only
                           STATUS current
                           DESCRIPTION
                                  "This is last month TOU energy of Eq_imp(normal).
                                   Range:        0~99999999.9"
                           ::= { lastMonthTou  18 }

lastMonthEqExpNormal       OBJECT-TYPE
        	      	       SYNTAX Integer32
        	      	       ACCESS read-only
                           STATUS current
                           DESCRIPTION
                                  "This is last month TOU energy of Eq_exp(normal).
                                   Range:        0~99999999.9"
                           ::= { lastMonthTou  19 }


lastMonthEsNormal          OBJECT-TYPE
        	      	       SYNTAX Integer32
        	      	       ACCESS read-only
                           STATUS current
                           DESCRIPTION
                                  "This is last month TOU energy of Es(normal).
                                   Range:        0~99999999.9"
                           ::= { lastMonthTou  20 }

lastMonthEpImpSum          OBJECT-TYPE
        	      	       SYNTAX Integer32
        	      	       ACCESS read-only
                           STATUS current
                           DESCRIPTION
                                  "This is last month TOU energy of Ep_imp(sum).
                                   Range:        0~99999999.9"
                           ::= { lastMonthTou  21 }

lastMonthEpExpSum          OBJECT-TYPE
        	      	       SYNTAX Integer32
        	      	       ACCESS read-only
                           STATUS current
                           DESCRIPTION
                                  "This is last month TOU energy of Ep_exp(sum).
                                   Range:        0~99999999.9"
                           ::= { lastMonthTou  22 }

lastMonthEqImpSum          OBJECT-TYPE
        	      	       SYNTAX Integer32
        	      	       ACCESS read-only
                           STATUS current
                           DESCRIPTION
                                  "This is last month TOU energy of Eq_imp(sum).
                                   Range:        0~99999999.9"
                           ::= { lastMonthTou  23 }

lastMonthEqExpSum          OBJECT-TYPE
        	      	       SYNTAX Integer32
        	      	       ACCESS read-only
                           STATUS current
                           DESCRIPTION
                                  "This is last month TOU energy of Eq_exp(sum).
                                   Range:        0~99999999.9"
                           ::= { lastMonthTou  24 }


lastMonthEsSum             OBJECT-TYPE
        	      	       SYNTAX Integer32
        	      	       ACCESS read-only
                           STATUS current
                           DESCRIPTION
                                  "This is last month TOU energy of Es(sum).
                                   Range:        0~99999999.9"
                           ::= { lastMonthTou  25 }  
                           
-- ******************************************************************
--  traps
-- ******************************************************************    
--  the ioStatusTraps GROUP(traps.2) 

io11DI1StatusChanged TRAP-TYPE
	ENTERPRISE ioStatusTraps
	VARIABLES { io11_DI1_Status }
    DESCRIPTION
		"Warning : DI1 Status of IO11 has changed !"
     ::= 20 
     
io11DI2StatusChanged TRAP-TYPE
	ENTERPRISE ioStatusTraps
	VARIABLES { io11_DI2_Status }
    DESCRIPTION
		"Warning : DI2 Status of IO11 has changed !"
     ::= 21
     
io11DI3StatusChanged TRAP-TYPE
	ENTERPRISE ioStatusTraps
	VARIABLES { io11_DI3_Status }
    DESCRIPTION
		"Warning : DI3 Status of IO11 has changed !"
     ::= 22
     
io11DI4StatusChanged TRAP-TYPE
	ENTERPRISE ioStatusTraps
	VARIABLES { io11_DI4_Status }
    DESCRIPTION
		"Warning : DI4 Status of IO11 has changed !"
     ::= 23

io11DI5StatusChanged TRAP-TYPE
	ENTERPRISE ioStatusTraps
	VARIABLES { io11_DI5_Status }
    DESCRIPTION
		"Warning : DI5 Status of IO11 has changed !"
     ::= 24

io11DI6StatusChanged TRAP-TYPE
	ENTERPRISE ioStatusTraps
	VARIABLES { io11_DI6_Status }
    DESCRIPTION
		"Warning : DI6 Status of IO11 has changed !"
     ::= 25

io21DI7StatusChanged TRAP-TYPE
	ENTERPRISE ioStatusTraps
	VARIABLES { io21_DI7_Status }
    DESCRIPTION
		"Warning : DI7 Status of IO21 has changed !"
     ::= 26

io21DI8StatusChanged TRAP-TYPE
	ENTERPRISE ioStatusTraps
	VARIABLES { io21_DI8_Status }
    DESCRIPTION
		"Warning : DI8 Status of IO21 has changed !"
     ::= 27

io21DI9StatusChanged TRAP-TYPE
	ENTERPRISE ioStatusTraps
	VARIABLES { io21_DI9_Status }
    DESCRIPTION
		"Warning : DI9 Status of IO21 has changed !"
     ::= 28

io21DI10StatusChanged TRAP-TYPE
	ENTERPRISE ioStatusTraps
	VARIABLES { io21_DI10_Status }
    DESCRIPTION
		"Warning : DI10 Status of IO21 has changed !"
     ::= 29 
     
io31DI11StatusChanged TRAP-TYPE
	ENTERPRISE ioStatusTraps
	VARIABLES { io31_DI11_Status }
    DESCRIPTION
		"Warning : DI11 Status of IO31 has changed !"
     ::= 30

io31DI12StatusChanged TRAP-TYPE
	ENTERPRISE ioStatusTraps
	VARIABLES { io31_DI12_Status }
    DESCRIPTION
		"Warning : DI12 Status of IO31 has changed !"
     ::= 31

io31DI13StatusChanged TRAP-TYPE
	ENTERPRISE ioStatusTraps
	VARIABLES { io31_DI13_Status }
    DESCRIPTION
		"Warning : DI13 Status of IO31 has changed !"
     ::= 32
io31DI14StatusChanged TRAP-TYPE
	ENTERPRISE ioStatusTraps
	VARIABLES { io31_DI14_Status }
    DESCRIPTION
		"Warning : DI14 Status of IO31 has changed !"
     ::= 33
             
END
