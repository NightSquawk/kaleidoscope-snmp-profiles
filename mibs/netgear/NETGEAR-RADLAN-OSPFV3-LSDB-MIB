NETGEAR-RADLAN-OSPFV3-LSDB-MIB DEFINITIONS ::= BEGIN

-- Title:                RADLAN OSPFv3 LSDB
--                       OSPFv3 LSA Database Private MIB
-- Version:              0.00
-- Date:                 17 Feb 2012

IMPORTS
    MODULE-IDENTITY, OBJECT-TYPE, Counter32, Gauge32,
        Integer32, Unsigned32, IpAddress
        FROM SNMPv2-SMI
    TEXTUAL-CONVENTION, TruthValue, RowStatus, TimeStamp
        FROM SNMPv2-TC
    InetAddressType, InetAddress, InetAddressPrefixLength,
    InetAddressIPv6
        FROM INET-ADDRESS-MIB
    rlOspfv3
        FROM NETGEAR-RADLAN-OSPFV3-MIB
    RlOspfProcessID
        FROM NETGEAR-RADLAN-OSPF-MIB
    AreaID, RouterID
        FROM OSPF-MIB
    rnd                                      FROM NETGEAR-RADLAN-MIB
    mib-2                                    FROM RFC1213-MIB;


rlOspfv3Lsdb MODULE-IDENTITY
        LAST-UPDATED "201105041700Z" -- Wed Feb 17 17:00:00 PST 2012
        ORGANIZATION "Radlan Computer Communications Ltd."
        CONTACT-INFO
             "radlan.com"
        DESCRIPTION
             "The private MIB module definition for OSPF LSA Database MIB."
        REVISION "201105041700Z"
        DESCRIPTION
             "Initial version of this MIB."
    ::= { rnd 222 }

------------------------------------------------------------------------------
--  OSPFv3 Link State Database
------------------------------------------------------------------------------


------------------------------------------------------------------------------
--  OSPFv3 Router LSA Table
------------------------------------------------------------------------------

rlOspfv3RouterLsaTable OBJECT-TYPE
    SYNTAX      SEQUENCE OF RlOspfv3RouterLsaEntry
    MAX-ACCESS  not-accessible
    STATUS      current
    DESCRIPTION
        "Router Link State Advertisement."
    ::= { rlOspfv3Lsdb 1 }


rlOspfv3RouterLsaEntry OBJECT-TYPE
    SYNTAX      RlOspfv3RouterLsaEntry
    MAX-ACCESS  not-accessible
    STATUS      current
    DESCRIPTION
    "A single entry from Router LSA."
    INDEX { rlOspfv3RouterLsaProcessId, rlOspfv3RouterLsaAreaId, rlOspfv3RouterLsaLsid,
            rlOspfv3RouterLsaRouterId, rlOspfv3RouterLsaIdx }
       ::= { rlOspfv3RouterLsaTable 1 }

RlOspfv3RouterLsaEntry ::=
    SEQUENCE {
        rlOspfv3RouterLsaProcessId
            RlOspfProcessID,
        rlOspfv3RouterLsaAreaId
            AreaID,
        rlOspfv3RouterLsaLsid
            IpAddress,
        rlOspfv3RouterLsaRouterId
            RouterID,
        rlOspfv3RouterLsaIdx
            Unsigned32,
        rlOspfv3RouterLsaCount
            Unsigned32,
        rlOspfv3RouterLsaSequence
            Integer32,
        rlOspfv3RouterLsaAge
            Integer32,
        rlOspfv3RouterLsaChecksum
            Integer32,
        rlOspfv3RouterLsaLength
            Unsigned32,
        rlOspfv3RouterLsaBitW
            INTEGER,
        rlOspfv3RouterLsaBitV
            INTEGER,
        rlOspfv3RouterLsaBitE
            INTEGER,
        rlOspfv3RouterLsaBitB
            INTEGER,
        rlOspfv3RouterLsaOptions
            Unsigned32,
        rlOspfv3RouterLsaType
            INTEGER,
        rlOspfv3RouterLsaMetric
            Unsigned32,
        rlOspfv3RouterLsaInterfaceID
            Unsigned32,
        rlOspfv3RouterLsaNeighborInterfaceID
            Unsigned32,
        rlOspfv3RouterLsaNeighborRouterID
            RouterID
}

rlOspfv3RouterLsaProcessId OBJECT-TYPE
      SYNTAX   RlOspfProcessID
      MAX-ACCESS   read-only
      STATUS   current
      DESCRIPTION
         "A 32-bit integer uniquely identifying an OSPFv3 process."
    ::= { rlOspfv3RouterLsaEntry 1 }

rlOspfv3RouterLsaAreaId OBJECT-TYPE
    SYNTAX      AreaID
    MAX-ACCESS  read-only
    STATUS      current
    DESCRIPTION
       "The 32 bit identifier of the Area  from  which
        the LSA was received."
    REFERENCE
       "OSPFv3 Version 2, Appendix C.2 Area parameters"
  ::= { rlOspfv3RouterLsaEntry 2 }

rlOspfv3RouterLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPFv3 Version 2, Section 12.1.4 Link State ID"
  ::= { rlOspfv3RouterLsaEntry 3 }

rlOspfv3RouterLsaRouterId OBJECT-TYPE
    SYNTAX      RouterID
    MAX-ACCESS  read-only
    STATUS      current
    DESCRIPTION
       "The 32 bit number that uniquely identifies the
        originating router in the Autonomous System."
    REFERENCE
       "OSPFv3 Version 2, Appendix C.1 Global parameters"
  ::= { rlOspfv3RouterLsaEntry 4 }

rlOspfv3RouterLsaIdx OBJECT-TYPE
    SYNTAX      Unsigned32 (1.. 65535)
    MAX-ACCESS  read-only
    STATUS      current
    DESCRIPTION
       "The index is a unsigned 32-bit integer.
        It is used as sequence number of entry
        in the LSA and relevant only for Router
        or Network LSA which can contain
        unlimited number of entries."
  ::= { rlOspfv3RouterLsaEntry 5 }

rlOspfv3RouterLsaCount OBJECT-TYPE
    SYNTAX      Unsigned32 (1.. 65535)
    MAX-ACCESS  read-only
    STATUS      current
    DESCRIPTION
       "Number of entries containg is the LSA."
  ::= { rlOspfv3RouterLsaEntry 6 }

rlOspfv3RouterLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPFv3 Version 2, Section 12.1.6 LS sequence number"
  ::= { rlOspfv3RouterLsaEntry 7 }


rlOspfv3RouterLsaAge OBJECT-TYPE
    SYNTAX      Integer32    -- Should be 0..MaxAge
    MAX-ACCESS  read-only
    STATUS      current
    DESCRIPTION
       "This field is the age of the link state
        advertisement in seconds."
       REFERENCE
          "OSPFv3 Version 2, Section 12.1.1 LS age"
  ::= { rlOspfv3RouterLsaEntry 8 }

rlOspfv3RouterLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPFv3 Version 2, Section 12.1.7 LS checksum"
  ::= { rlOspfv3RouterLsaEntry 9 }

rlOspfv3RouterLsaLength OBJECT-TYPE
    SYNTAX      Unsigned32
    MAX-ACCESS  read-only
    STATUS      current
    DESCRIPTION
       "The lenth in bytes of the LSA.
        This includes the 20 byte LSA header."
  ::= { rlOspfv3RouterLsaEntry 10 }

rlOspfv3RouterLsaBitW OBJECT-TYPE
    SYNTAX INTEGER {
        off(1),
        on(2)
    }
    MAX-ACCESS   read-only
    STATUS      current
    DESCRIPTION
       "When set, the router is a wild-card multicast receiver.
        When running MOSPF, these routers receive all multicast datagrams,
        regardless of destination."
  ::= { rlOspfv3RouterLsaEntry 11 }

rlOspfv3RouterLsaBitV OBJECT-TYPE
    SYNTAX INTEGER {
        off(1),
        on(2)
    }
    MAX-ACCESS   read-only
    STATUS      current
    DESCRIPTION
       "When set, the router is an endpoint
        of one or more fully adjacent virtual
        links having the described area as Transit
        area (V is for virtual link endpoint)."
  ::= { rlOspfv3RouterLsaEntry 12 }

rlOspfv3RouterLsaBitE OBJECT-TYPE
    SYNTAX INTEGER {
        off(1),
        on(2)
    }
    MAX-ACCESS   read-only
        STATUS   current
    DESCRIPTION
       "When set, the router is an AS
        boundary router (E is for external)."
  ::= { rlOspfv3RouterLsaEntry 13 }

rlOspfv3RouterLsaBitB OBJECT-TYPE
    SYNTAX INTEGER {
        off(1),
        on(2)
    }
    MAX-ACCESS   read-only
    STATUS      current
    DESCRIPTION
       "When set, the router is an area
        border router (B is for border)."
  ::= { rlOspfv3RouterLsaEntry 14 }

rlOspfv3RouterLsaOptions OBJECT-TYPE
    SYNTAX      Unsigned32
    MAX-ACCESS  read-only
    STATUS      current
    DESCRIPTION
       "The optional capabilities supported by the router.
        Through this mechanism routers of differing capabilities can be
        mixed within an OSPF routing domain."
  ::= { rlOspfv3RouterLsaEntry 15 }

rlOspfv3RouterLsaType OBJECT-TYPE
    SYNTAX INTEGER {
        pointToPoint(1),
        transitNetwork(2),
        stubNetwork(3),
        virtualLink(4)
    }
    MAX-ACCESS   read-only
        STATUS   current
    DESCRIPTION
       "A quick description of the router link."
  ::= { rlOspfv3RouterLsaEntry 16 }

rlOspfv3RouterLsaMetric OBJECT-TYPE
    SYNTAX      Unsigned32
    MAX-ACCESS  read-only
    STATUS      current
    DESCRIPTION
       "The cost of using this router link."
  ::= { rlOspfv3RouterLsaEntry 17 }

rlOspfv3RouterLsaInterfaceID OBJECT-TYPE
    SYNTAX      Unsigned32
    MAX-ACCESS  read-only
    STATUS      current
    DESCRIPTION
       "The Interface ID assigned to the interface being described."
  ::= { rlOspfv3RouterLsaEntry 18 }

rlOspfv3RouterLsaNeighborInterfaceID OBJECT-TYPE
    SYNTAX      Unsigned32
    MAX-ACCESS  read-only
    STATUS      current
    DESCRIPTION
       "The Interface ID the neighbor router (or the attached link's
        Designated Router, for Type 2 interfaces) has been advertising
        in hello packets sent on the attached link."
  ::= { rlOspfv3RouterLsaEntry 19 }

rlOspfv3RouterLsaNeighborRouterID OBJECT-TYPE
    SYNTAX      RouterID
    MAX-ACCESS  read-only
    STATUS      current
    DESCRIPTION
       "The Router ID the neighbor router (or the attached link's
      Designated Router, for Type 2 interfaces)."
  ::= { rlOspfv3RouterLsaEntry 20 }


------------------------------------------------------------------------------
--  OSPFv3 Network LSA Table
------------------------------------------------------------------------------

rlOspfv3NetworkLsaTable OBJECT-TYPE
    SYNTAX      SEQUENCE OF RlOspfv3NetworkLsaEntry
    MAX-ACCESS  not-accessible
    STATUS      current
    DESCRIPTION
        "Network Link State Advertisement."
    ::= { rlOspfv3Lsdb 2 }

rlOspfv3NetworkLsaEntry OBJECT-TYPE
    SYNTAX      RlOspfv3NetworkLsaEntry
    MAX-ACCESS  not-accessible
    STATUS      current
    DESCRIPTION
    "A single entry from Network LSA."
    INDEX { rlOspfv3NetworkLsaProcessId, rlOspfv3NetworkLsaAreaId, rlOspfv3NetworkLsaLsid,
            rlOspfv3NetworkLsaRouterId, rlOspfv3NetworkLsaIdx }
       ::= { rlOspfv3NetworkLsaTable 1 }

RlOspfv3NetworkLsaEntry ::=
    SEQUENCE {
        rlOspfv3NetworkLsaProcessId
            RlOspfProcessID,
        rlOspfv3NetworkLsaAreaId
            AreaID,
        rlOspfv3NetworkLsaLsid
            IpAddress,
        rlOspfv3NetworkLsaRouterId
            RouterID,
        rlOspfv3NetworkLsaIdx
            Unsigned32,
        rlOspfv3NetworkLsaCount
            Unsigned32,
        rlOspfv3NetworkLsaSequence
            Integer32,
        rlOspfv3NetworkLsaAge
            Integer32,
        rlOspfv3NetworkLsaChecksum
            Integer32,
        rlOspfv3NetworkLsaLength
            Unsigned32,
        rlOspfv3NetworkLsaOptions
            Unsigned32,
        rlOspfv3NetworkLsaAttRouter
            RouterID
}

rlOspfv3NetworkLsaProcessId OBJECT-TYPE
      SYNTAX   RlOspfProcessID
      MAX-ACCESS   read-only
      STATUS   current
      DESCRIPTION
         "A 32-bit integer uniquely identifying an OSPFv3 process."
    ::= { rlOspfv3NetworkLsaEntry 1 }

rlOspfv3NetworkLsaAreaId OBJECT-TYPE
    SYNTAX      AreaID
    MAX-ACCESS  read-only
    STATUS      current
    DESCRIPTION
       "The 32 bit identifier of the Area  from  which
        the LSA was received."
    REFERENCE
       "OSPFv3 Version 2, Appendix C.2 Area parameters"
  ::= { rlOspfv3NetworkLsaEntry 2 }

rlOspfv3NetworkLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPFv3 Version 2, Section 12.1.4 Link State ID"
  ::= { rlOspfv3NetworkLsaEntry 3 }

rlOspfv3NetworkLsaRouterId OBJECT-TYPE
    SYNTAX      RouterID
    MAX-ACCESS  read-only
    STATUS      current
    DESCRIPTION
       "The 32 bit number that uniquely identifies the
        originating router in the Autonomous System."
    REFERENCE
       "OSPFv3 Version 2, Appendix C.1 Global parameters"
  ::= { rlOspfv3NetworkLsaEntry 4 }

rlOspfv3NetworkLsaIdx OBJECT-TYPE
    SYNTAX      Unsigned32 (1.. 65535)
    MAX-ACCESS  read-only
    STATUS      current
    DESCRIPTION
       "The index is a unsigned 32-bit integer.
        It is used as sequence number of entry
        in the LSA and relevant only for Router
        or Network LSA which can contain
        unlimited number of entries."
  ::= { rlOspfv3NetworkLsaEntry 5 }

rlOspfv3NetworkLsaCount OBJECT-TYPE
    SYNTAX      Unsigned32 (1.. 65535)
    MAX-ACCESS  read-only
    STATUS      current
    DESCRIPTION
       "Number of entries containg is the LSA."
  ::= { rlOspfv3NetworkLsaEntry 6 }

rlOspfv3NetworkLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPFv3 Version 2, Section 12.1.6 LS sequence number"
  ::= { rlOspfv3NetworkLsaEntry 7 }


rlOspfv3NetworkLsaAge OBJECT-TYPE
    SYNTAX      Integer32    -- Should be 0..MaxAge
    MAX-ACCESS  read-only
    STATUS      current
    DESCRIPTION
       "This field is the age of the link state
        advertisement in seconds."
       REFERENCE
          "OSPFv3 Version 2, Section 12.1.1 LS age"
  ::= { rlOspfv3NetworkLsaEntry 8 }

rlOspfv3NetworkLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPFv3 Version 2, Section 12.1.7 LS checksum"
  ::= { rlOspfv3NetworkLsaEntry 9 }

rlOspfv3NetworkLsaLength OBJECT-TYPE
    SYNTAX      Unsigned32
    MAX-ACCESS  read-only
    STATUS      current
    DESCRIPTION
       "The lenth in bytes of the LSA.
        This includes the 20 byte LSA header."
  ::= { rlOspfv3NetworkLsaEntry 10 }

rlOspfv3NetworkLsaOptions OBJECT-TYPE
    SYNTAX      Unsigned32
    MAX-ACCESS  read-only
    STATUS      current
    DESCRIPTION
       "The optional capabilities supported by the router.
        Through this mechanism routers of differing capabilities can be
        mixed within an OSPF routing domain."
  ::= { rlOspfv3NetworkLsaEntry 11 }

rlOspfv3NetworkLsaAttRouter OBJECT-TYPE
    SYNTAX      RouterID
    MAX-ACCESS  read-only
    STATUS      current
    DESCRIPTION
       "The Router IDs of each of the routers attached
        to the link."
  ::= { rlOspfv3NetworkLsaEntry 12 }


------------------------------------------------------------------------------
--  OSPFv3 Inter-Area-Prefix LSA Table
------------------------------------------------------------------------------

rlOspfv3InterAreaPrefixLsaTable OBJECT-TYPE
    SYNTAX      SEQUENCE OF RlOspfv3InterAreaPrefixLsaEntry
    MAX-ACCESS  not-accessible
    STATUS      current
    DESCRIPTION
        "Inter Area Prefix Link State Advertisement."
    ::= { rlOspfv3Lsdb 3 }

rlOspfv3InterAreaPrefixLsaEntry OBJECT-TYPE
    SYNTAX      RlOspfv3InterAreaPrefixLsaEntry
    MAX-ACCESS  not-accessible
    STATUS      current
    DESCRIPTION
    "A single entry from Network LSA."
    INDEX { rlOspfv3InterAreaPrefixLsaProcessId, rlOspfv3InterAreaPrefixLsaAreaId, rlOspfv3InterAreaPrefixLsaLsid,
            rlOspfv3InterAreaPrefixLsaRouterId }
       ::= { rlOspfv3InterAreaPrefixLsaTable 1 }

RlOspfv3InterAreaPrefixLsaEntry ::=
    SEQUENCE {
        rlOspfv3InterAreaPrefixLsaProcessId
            RlOspfProcessID,
        rlOspfv3InterAreaPrefixLsaAreaId
            AreaID,
        rlOspfv3InterAreaPrefixLsaLsid
            IpAddress,
        rlOspfv3InterAreaPrefixLsaRouterId
            RouterID,
        rlOspfv3InterAreaPrefixLsaSequence
            Integer32,
        rlOspfv3InterAreaPrefixLsaAge
            Integer32,
        rlOspfv3InterAreaPrefixLsaChecksum
            Integer32,
        rlOspfv3InterAreaPrefixLsaLength
            Unsigned32,
        rlOspfv3InterAreaPrefixLsaMetric
            Unsigned32,
        rlOspfv3InterAreaPrefixLsaPrefixLength
            Unsigned32,
        rlOspfv3InterAreaPrefixLsaPrefixOptions
            Unsigned32,
        rlOspfv3InterAreaPrefixLsaAddressPrefix
            InetAddress
}

rlOspfv3InterAreaPrefixLsaProcessId OBJECT-TYPE
      SYNTAX   RlOspfProcessID
      MAX-ACCESS   read-only
      STATUS   current
      DESCRIPTION
         "A 32-bit integer uniquely identifying an OSPFv3 process."
    ::= { rlOspfv3InterAreaPrefixLsaEntry 1 }

rlOspfv3InterAreaPrefixLsaAreaId OBJECT-TYPE
    SYNTAX      AreaID
    MAX-ACCESS  read-only
    STATUS      current
    DESCRIPTION
       "The 32 bit identifier of the Area  from  which
        the LSA was received."
    REFERENCE
       "OSPFv3 Version 2, Appendix C.2 Area parameters"
  ::= { rlOspfv3InterAreaPrefixLsaEntry 2 }

rlOspfv3InterAreaPrefixLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPFv3 Version 2, Section 12.1.4 Link State ID"
  ::= { rlOspfv3InterAreaPrefixLsaEntry 3 }

rlOspfv3InterAreaPrefixLsaRouterId OBJECT-TYPE
    SYNTAX      RouterID
    MAX-ACCESS  read-only
    STATUS      current
    DESCRIPTION
       "The 32 bit number that uniquely identifies the
        originating router in the Autonomous System."
    REFERENCE
       "OSPFv3 Version 2, Appendix C.1 Global parameters"
  ::= { rlOspfv3InterAreaPrefixLsaEntry 4 }

rlOspfv3InterAreaPrefixLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPFv3 Version 2, Section 12.1.6 LS sequence number"
  ::= { rlOspfv3InterAreaPrefixLsaEntry 5 }


rlOspfv3InterAreaPrefixLsaAge OBJECT-TYPE
    SYNTAX      Integer32    -- Should be 0..MaxAge
    MAX-ACCESS  read-only
    STATUS      current
    DESCRIPTION
       "This field is the age of the link state
        advertisement in seconds."
       REFERENCE
          "OSPFv3 Version 2, Section 12.1.1 LS age"
  ::= { rlOspfv3InterAreaPrefixLsaEntry 6 }

rlOspfv3InterAreaPrefixLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPFv3 Version 2, Section 12.1.7 LS checksum"
  ::= { rlOspfv3InterAreaPrefixLsaEntry 7 }

rlOspfv3InterAreaPrefixLsaLength OBJECT-TYPE
    SYNTAX      Unsigned32
    MAX-ACCESS  read-only
    STATUS      current
    DESCRIPTION
       "The lenth in bytes of the LSA.
        This includes the 20 byte LSA header."
  ::= { rlOspfv3InterAreaPrefixLsaEntry 8 }

rlOspfv3InterAreaPrefixLsaMetric OBJECT-TYPE
    SYNTAX      Unsigned32
    MAX-ACCESS  read-only
    STATUS      current
    DESCRIPTION
       "The cost of this route.  Expressed in the same units as the
      interface costs in the router-LSAs."
  ::= { rlOspfv3InterAreaPrefixLsaEntry 9 }

rlOspfv3InterAreaPrefixLsaPrefixLength OBJECT-TYPE
    SYNTAX      Unsigned32
    MAX-ACCESS  read-only
    STATUS      current
    DESCRIPTION
       "IPv6 address prefix length."
  ::= { rlOspfv3InterAreaPrefixLsaEntry 10 }

rlOspfv3InterAreaPrefixLsaPrefixOptions OBJECT-TYPE
    SYNTAX      Unsigned32
    MAX-ACCESS  read-only
    STATUS      current
    DESCRIPTION
       "IPv6 address prefix options."
  ::= { rlOspfv3InterAreaPrefixLsaEntry 11 }

rlOspfv3InterAreaPrefixLsaAddressPrefix OBJECT-TYPE
    SYNTAX      InetAddress
    MAX-ACCESS  read-only
    STATUS      current
    DESCRIPTION
       "IPv6 address prefix - bit strings of length 128."
  ::= { rlOspfv3InterAreaPrefixLsaEntry 12 }

------------------------------------------------------------------------------
--  OSPFv3 Inter-Area-Router LSA Table
------------------------------------------------------------------------------

rlOspfv3InterAreaRouterLsaTable OBJECT-TYPE
    SYNTAX      SEQUENCE OF RlOspfv3InterAreaRouterLsaEntry
    MAX-ACCESS  not-accessible
    STATUS      current
    DESCRIPTION
        "Inter Area Router Link State Advertisement."
    ::= { rlOspfv3Lsdb 4 }

rlOspfv3InterAreaRouterLsaEntry OBJECT-TYPE
    SYNTAX      RlOspfv3InterAreaRouterLsaEntry
    MAX-ACCESS  not-accessible
    STATUS      current
    DESCRIPTION
    "A single entry from Network LSA."
    INDEX { rlOspfv3InterAreaRouterLsaProcessId, rlOspfv3InterAreaRouterLsaAreaId, rlOspfv3InterAreaRouterLsaLsid,
            rlOspfv3InterAreaRouterLsaRouterId }
       ::= { rlOspfv3InterAreaRouterLsaTable 1 }

RlOspfv3InterAreaRouterLsaEntry ::=
    SEQUENCE {
        rlOspfv3InterAreaRouterLsaProcessId
            RlOspfProcessID,
        rlOspfv3InterAreaRouterLsaAreaId
            AreaID,
        rlOspfv3InterAreaRouterLsaLsid
            IpAddress,
        rlOspfv3InterAreaRouterLsaRouterId
            RouterID,
        rlOspfv3InterAreaRouterLsaSequence
            Integer32,
        rlOspfv3InterAreaRouterLsaAge
            Integer32,
        rlOspfv3InterAreaRouterLsaChecksum
            Integer32,
        rlOspfv3InterAreaRouterLsaLength
            Unsigned32,
        rlOspfv3InterAreaRouterLsaOptions
            Unsigned32,
        rlOspfv3InterAreaRouterLsaMetric
            Unsigned32,
        rlOspfv3InterAreaRouterLsaDestinationRouterId
            RouterID
}

rlOspfv3InterAreaRouterLsaProcessId OBJECT-TYPE
      SYNTAX   RlOspfProcessID
      MAX-ACCESS   read-only
      STATUS   current
      DESCRIPTION
         "A 32-bit integer uniquely identifying an OSPFv3 process."
    ::= { rlOspfv3InterAreaRouterLsaEntry 1 }

rlOspfv3InterAreaRouterLsaAreaId OBJECT-TYPE
    SYNTAX      AreaID
    MAX-ACCESS  read-only
    STATUS      current
    DESCRIPTION
       "The 32 bit identifier of the Area  from  which
        the LSA was received."
    REFERENCE
       "OSPFv3 Version 2, Appendix C.2 Area parameters"
  ::= { rlOspfv3InterAreaRouterLsaEntry 2 }

rlOspfv3InterAreaRouterLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPFv3 Version 2, Section 12.1.4 Link State ID"
  ::= { rlOspfv3InterAreaRouterLsaEntry 3 }

rlOspfv3InterAreaRouterLsaRouterId OBJECT-TYPE
    SYNTAX      RouterID
    MAX-ACCESS  read-only
    STATUS      current
    DESCRIPTION
       "The 32 bit number that uniquely identifies the
        originating router in the Autonomous System."
    REFERENCE
       "OSPFv3 Version 2, Appendix C.1 Global parameters"
  ::= { rlOspfv3InterAreaRouterLsaEntry 4 }

rlOspfv3InterAreaRouterLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPFv3 Version 2, Section 12.1.6 LS sequence number"
  ::= { rlOspfv3InterAreaRouterLsaEntry 5 }


rlOspfv3InterAreaRouterLsaAge OBJECT-TYPE
    SYNTAX      Integer32    -- Should be 0..MaxAge
    MAX-ACCESS  read-only
    STATUS      current
    DESCRIPTION
       "This field is the age of the link state
        advertisement in seconds."
       REFERENCE
          "OSPFv3 Version 2, Section 12.1.1 LS age"
  ::= { rlOspfv3InterAreaRouterLsaEntry 6 }

rlOspfv3InterAreaRouterLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPFv3 Version 2, Section 12.1.7 LS checksum"
  ::= { rlOspfv3InterAreaRouterLsaEntry 7 }

rlOspfv3InterAreaRouterLsaLength OBJECT-TYPE
    SYNTAX      Unsigned32
    MAX-ACCESS  read-only
    STATUS      current
    DESCRIPTION
       "The lenth in bytes of the LSA.
        This includes the 20 byte LSA header."
  ::= { rlOspfv3InterAreaRouterLsaEntry 8 }

rlOspfv3InterAreaRouterLsaOptions OBJECT-TYPE
    SYNTAX      Unsigned32
    MAX-ACCESS  read-only
    STATUS      current
    DESCRIPTION
       "The optional capabilities supported by the router.
        Through this mechanism routers of differing capabilities can be
        mixed within an OSPF routing domain."
  ::= { rlOspfv3InterAreaRouterLsaEntry 9 }

rlOspfv3InterAreaRouterLsaMetric OBJECT-TYPE
    SYNTAX      Unsigned32
    MAX-ACCESS  read-only
    STATUS      current
    DESCRIPTION
       "The cost of this route.  Expressed in the same units as the
      interface costs in the router-LSAs."
  ::= { rlOspfv3InterAreaRouterLsaEntry 10 }

rlOspfv3InterAreaRouterLsaDestinationRouterId OBJECT-TYPE
    SYNTAX      RouterID
    MAX-ACCESS  read-only
    STATUS      current
    DESCRIPTION
       "The Router ID of the router being described by the LSA."
  ::= { rlOspfv3InterAreaRouterLsaEntry 11 }


------------------------------------------------------------------------------
--  OSPFv3 AS External LSA Table
------------------------------------------------------------------------------

rlOspfv3AsExternalLsaTable OBJECT-TYPE
    SYNTAX      SEQUENCE OF RlOspfv3AsExternalLsaEntry
    MAX-ACCESS  not-accessible
    STATUS      current
    DESCRIPTION
        "AS External Link State Advertisement."
    ::= { rlOspfv3Lsdb 5 }


rlOspfv3AsExternalLsaEntry OBJECT-TYPE
    SYNTAX      RlOspfv3AsExternalLsaEntry
    MAX-ACCESS  not-accessible
    STATUS      current
    DESCRIPTION
    "A single entry from Router LSA."
    INDEX { rlOspfv3AsExternalLsaProcessId, rlOspfv3AsExternalLsaAreaId, rlOspfv3AsExternalLsaLsid,
            rlOspfv3AsExternalLsaRouterId }
       ::= { rlOspfv3AsExternalLsaTable 1 }

RlOspfv3AsExternalLsaEntry ::=
    SEQUENCE {
        rlOspfv3AsExternalLsaProcessId
            RlOspfProcessID,
        rlOspfv3AsExternalLsaAreaId
            AreaID,
        rlOspfv3AsExternalLsaLsid
            IpAddress,
        rlOspfv3AsExternalLsaRouterId
            RouterID,
        rlOspfv3AsExternalLsaSequence
            Integer32,
        rlOspfv3AsExternalLsaAge
            Integer32,
        rlOspfv3AsExternalLsaChecksum
            Integer32,
        rlOspfv3AsExternalLsaLength
            Unsigned32,
        rlOspfv3AsExternalLsaBitE
            INTEGER,
        rlOspfv3AsExternalLsaBitF
            INTEGER,
        rlOspfv3AsExternalLsaBitT
            INTEGER,
        rlOspfv3AsExternalLsaMetric
            Unsigned32,
        rlOspfv3AsExternalLsaReferencedLsType
            Unsigned32,
        rlOspfv3AsExternalLsaPrefixLength
            Unsigned32,
        rlOspfv3AsExternalLsaPrefixOptions
            Unsigned32,
        rlOspfv3AsExternalLsaAddressPrefix
            InetAddress,
        rlOspfv3AsExternalLsaForwardingAddress
            InetAddress,
        rlOspfv3AsExternalLsaExternalRouteTag
            Unsigned32,
        rlOspfv3AsExternalLsaReferencedLinkStateId
            Unsigned32
}

rlOspfv3AsExternalLsaProcessId OBJECT-TYPE
      SYNTAX   RlOspfProcessID
      MAX-ACCESS   read-only
      STATUS   current
      DESCRIPTION
         "A 32-bit integer uniquely identifying an OSPFv3 process."
    ::= { rlOspfv3AsExternalLsaEntry 1 }

rlOspfv3AsExternalLsaAreaId OBJECT-TYPE
    SYNTAX      AreaID
    MAX-ACCESS  read-only
    STATUS      current
    DESCRIPTION
       "The 32 bit identifier of the Area  from  which
        the LSA was received."
    REFERENCE
       "OSPFv3 Version 2, Appendix C.2 Area parameters"
  ::= { rlOspfv3AsExternalLsaEntry 2 }

rlOspfv3AsExternalLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPFv3 Version 2, Section 12.1.4 Link State ID"
  ::= { rlOspfv3AsExternalLsaEntry 3 }

rlOspfv3AsExternalLsaRouterId OBJECT-TYPE
    SYNTAX      RouterID
    MAX-ACCESS  read-only
    STATUS      current
    DESCRIPTION
       "The 32 bit number that uniquely identifies the
        originating router in the Autonomous System."
    REFERENCE
       "OSPFv3 Version 2, Appendix C.1 Global parameters"
  ::= { rlOspfv3AsExternalLsaEntry 4 }

rlOspfv3AsExternalLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPFv3 Version 2, Section 12.1.6 LS sequence number"
  ::= { rlOspfv3AsExternalLsaEntry 5 }

rlOspfv3AsExternalLsaAge OBJECT-TYPE
    SYNTAX      Integer32    -- Should be 0..MaxAge
    MAX-ACCESS  read-only
    STATUS      current
    DESCRIPTION
       "This field is the age of the link state
        advertisement in seconds."
       REFERENCE
          "OSPFv3 Version 2, Section 12.1.1 LS age"
  ::= { rlOspfv3AsExternalLsaEntry 6 }

rlOspfv3AsExternalLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPFv3 Version 2, Section 12.1.7 LS checksum"
  ::= { rlOspfv3AsExternalLsaEntry 7 }

rlOspfv3AsExternalLsaLength OBJECT-TYPE
    SYNTAX      Unsigned32
    MAX-ACCESS  read-only
    STATUS      current
    DESCRIPTION
       "The lenth in bytes of the LSA.
        This includes the 20 byte LSA header."
  ::= { rlOspfv3AsExternalLsaEntry 8 }

rlOspfv3AsExternalLsaBitE OBJECT-TYPE
    SYNTAX INTEGER {
        off(1),
        on(2)
    }
    MAX-ACCESS   read-only
    STATUS      current
    DESCRIPTION
       "The type of external metric. If bit E is set, the metric
        specified is a Type 2 external metric."
  ::= { rlOspfv3AsExternalLsaEntry 9 }

rlOspfv3AsExternalLsaBitF OBJECT-TYPE
    SYNTAX INTEGER {
        off(1),
        on(2)
    }
    MAX-ACCESS   read-only
    STATUS      current
    DESCRIPTION
       "If set, a Forwarding Address has been included in the LSA."
  ::= { rlOspfv3AsExternalLsaEntry 10 }

rlOspfv3AsExternalLsaBitT OBJECT-TYPE
    SYNTAX INTEGER {
        off(1),
        on(2)
    }
    MAX-ACCESS   read-only
        STATUS   current
    DESCRIPTION
       "If set, an External Route Tag has been included in the LSA."
  ::= { rlOspfv3AsExternalLsaEntry 11 }

rlOspfv3AsExternalLsaMetric OBJECT-TYPE
    SYNTAX      Unsigned32
    MAX-ACCESS  read-only
    STATUS      current
    DESCRIPTION
       "The cost of this route.  Interpretation depends on the external
        type indication (bit E above)."
  ::= { rlOspfv3AsExternalLsaEntry 12 }

rlOspfv3AsExternalLsaReferencedLsType OBJECT-TYPE
    SYNTAX      Unsigned32
    MAX-ACCESS  read-only
    STATUS      current
    DESCRIPTION
       "If non-zero, an LSA with this LS type is to be associated with
        this LSA (see Referenced Link State ID below)."
  ::= { rlOspfv3AsExternalLsaEntry 13 }

rlOspfv3AsExternalLsaPrefixLength OBJECT-TYPE
    SYNTAX      Unsigned32
    MAX-ACCESS  read-only
    STATUS      current
    DESCRIPTION
       "IPv6 address prefix length."
  ::= { rlOspfv3AsExternalLsaEntry 14 }

rlOspfv3AsExternalLsaPrefixOptions OBJECT-TYPE
    SYNTAX      Unsigned32
    MAX-ACCESS  read-only
    STATUS      current
    DESCRIPTION
       "IPv6 address prefix options."
  ::= { rlOspfv3AsExternalLsaEntry 15 }

rlOspfv3AsExternalLsaAddressPrefix OBJECT-TYPE
    SYNTAX      InetAddress
    MAX-ACCESS  read-only
    STATUS      current
    DESCRIPTION
       "IPv6 address prefix - bit strings of length 128."
  ::= { rlOspfv3AsExternalLsaEntry 16 }

rlOspfv3AsExternalLsaForwardingAddress OBJECT-TYPE
    SYNTAX      InetAddress
    MAX-ACCESS  read-only
    STATUS      current
    DESCRIPTION
       "A fully qualified IPv6 address (128 bits).
        Included in the LSA if and only if bit F has been set."
  ::= { rlOspfv3AsExternalLsaEntry 17 }

rlOspfv3AsExternalLsaExternalRouteTag OBJECT-TYPE
    SYNTAX      Unsigned32
    MAX-ACCESS  read-only
    STATUS      current
    DESCRIPTION
       "A 32-bit field which may be used to communicate additional
        information between AS boundary routers."
  ::= { rlOspfv3AsExternalLsaEntry 18 }

rlOspfv3AsExternalLsaReferencedLinkStateId OBJECT-TYPE
    SYNTAX      Unsigned32
    MAX-ACCESS  read-only
    STATUS      current
    DESCRIPTION
       "Included if and only if Reference LS Type is non-zero."
  ::= { rlOspfv3AsExternalLsaEntry 19 }


------------------------------------------------------------------------------
--  OSPFv3 Link (Type 8) LSA Table
------------------------------------------------------------------------------

rlOspfv3LinkLsaTable OBJECT-TYPE
    SYNTAX      SEQUENCE OF RlOspfv3LinkLsaEntry
    MAX-ACCESS  not-accessible
    STATUS      current
    DESCRIPTION
        "Link (Type 8) Link State Advertisement."
    ::= { rlOspfv3Lsdb 6 }

rlOspfv3LinkLsaEntry OBJECT-TYPE
    SYNTAX      RlOspfv3LinkLsaEntry
    MAX-ACCESS  not-accessible
    STATUS      current
    DESCRIPTION
    "A single entry from Network LSA."
    INDEX { rlOspfv3LinkLsaProcessId, rlOspfv3LinkLsaIfIndex, rlOspfv3LinkLsaIfInstId, rlOspfv3LinkLsaLsid,
            rlOspfv3LinkLsaRouterId, rlOspfv3LinkLsaIdx }
       ::= { rlOspfv3LinkLsaTable 1 }

RlOspfv3LinkLsaEntry ::=
    SEQUENCE {
        rlOspfv3LinkLsaProcessId
            RlOspfProcessID,
        rlOspfv3LinkLsaIfIndex
            Unsigned32,
        rlOspfv3LinkLsaIfInstId
            Integer32,
        rlOspfv3LinkLsaLsid
            IpAddress,
        rlOspfv3LinkLsaRouterId
            RouterID,
        rlOspfv3LinkLsaIdx
            Unsigned32,
        rlOspfv3LinkLsaCount
            Unsigned32,
        rlOspfv3LinkLsaSequence
            Integer32,
        rlOspfv3LinkLsaAge
            Integer32,
        rlOspfv3LinkLsaChecksum
            Integer32,
        rlOspfv3LinkLsaLength
            Unsigned32,
        rlOspfv3LinkLsaRtrPri
            Unsigned32,
        rlOspfv3LinkLsaOptions
            Unsigned32,
        rlOspfv3LinkLsaLinkLocalInterfaceAddress
            InetAddress,
        rlOspfv3LinkLsaPrefixLength
            Unsigned32,
        rlOspfv3LinkLsaPrefixOptions
            Unsigned32,
        rlOspfv3LinkLsaAddressPrefix
            InetAddress
}

rlOspfv3LinkLsaProcessId OBJECT-TYPE
      SYNTAX   RlOspfProcessID
      MAX-ACCESS   read-only
      STATUS   current
      DESCRIPTION
         "A 32-bit integer uniquely identifying an OSPFv3 process."
    ::= { rlOspfv3LinkLsaEntry 1 }

rlOspfv3LinkLsaIfIndex OBJECT-TYPE
    SYNTAX         Unsigned32
    MAX-ACCESS     not-accessible
    STATUS         current
    DESCRIPTION
        "The identifier of the link from which the LSA
        was received."
    REFERENCE
        "OSPF Version 2, Appendix C.2 Area parameters"
    ::= { rlOspfv3LinkLsaEntry 2 }

rlOspfv3LinkLsaIfInstId OBJECT-TYPE
    SYNTAX          Integer32(0..255)
    MAX-ACCESS      not-accessible
    STATUS          current
    DESCRIPTION
        "OSPFv3 protocol instance ID specified in the OSPF header
        of the packet in which this LSA was received."
    ::= { rlOspfv3LinkLsaEntry 3 }

rlOspfv3LinkLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPFv3 Version 2, Section 12.1.4 Link State ID"
  ::= { rlOspfv3LinkLsaEntry 4 }

rlOspfv3LinkLsaRouterId OBJECT-TYPE
    SYNTAX      RouterID
    MAX-ACCESS  read-only
    STATUS      current
    DESCRIPTION
       "The 32 bit number that uniquely identifies the
        originating router in the Autonomous System."
    REFERENCE
       "OSPFv3 Version 2, Appendix C.1 Global parameters"
  ::= { rlOspfv3LinkLsaEntry 5 }

rlOspfv3LinkLsaIdx OBJECT-TYPE
    SYNTAX      Unsigned32 (1.. 65535)
    MAX-ACCESS  read-only
    STATUS      current
    DESCRIPTION
       "The index is a unsigned 32-bit integer.
        It is used as sequence number of entry
        in the LSA and relevant only for Router
        or Network LSA which can contain
        unlimited number of entries."
  ::= { rlOspfv3LinkLsaEntry 6 }

rlOspfv3LinkLsaCount OBJECT-TYPE
    SYNTAX      Unsigned32 (1.. 65535)
    MAX-ACCESS  read-only
    STATUS      current
    DESCRIPTION
       "Number of entries containg is the LSA."
  ::= { rlOspfv3LinkLsaEntry 7 }

rlOspfv3LinkLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPFv3 Version 2, Section 12.1.6 LS sequence number"
  ::= { rlOspfv3LinkLsaEntry 8 }


rlOspfv3LinkLsaAge OBJECT-TYPE
    SYNTAX      Integer32    -- Should be 0..MaxAge
    MAX-ACCESS  read-only
    STATUS      current
    DESCRIPTION
       "This field is the age of the link state
        advertisement in seconds."
       REFERENCE
          "OSPFv3 Version 2, Section 12.1.1 LS age"
  ::= { rlOspfv3LinkLsaEntry 9 }

rlOspfv3LinkLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPFv3 Version 2, Section 12.1.7 LS checksum"
  ::= { rlOspfv3LinkLsaEntry 10 }

rlOspfv3LinkLsaLength OBJECT-TYPE
    SYNTAX      Unsigned32
    MAX-ACCESS  read-only
    STATUS      current
    DESCRIPTION
       "The lenth in bytes of the LSA.
        This includes the 20 byte LSA header."
  ::= { rlOspfv3LinkLsaEntry 11 }

rlOspfv3LinkLsaRtrPri OBJECT-TYPE
    SYNTAX      Unsigned32
    MAX-ACCESS  read-only
    STATUS      current
    DESCRIPTION
       "The Router Priority of the interface attaching the originating
        router to the link."
  ::= { rlOspfv3LinkLsaEntry 12 }

rlOspfv3LinkLsaOptions OBJECT-TYPE
    SYNTAX      Unsigned32
    MAX-ACCESS  read-only
    STATUS      current
    DESCRIPTION
       "The optional capabilities supported by the router.
        Through this mechanism routers of differing capabilities can be
        mixed within an OSPF routing domain."
  ::= { rlOspfv3LinkLsaEntry 13 }

rlOspfv3LinkLsaLinkLocalInterfaceAddress OBJECT-TYPE
    SYNTAX      InetAddress
    MAX-ACCESS  read-only
    STATUS      current
    DESCRIPTION
       "Link Local Interface Address.
        The originating router's link-local interface address on the link."
  ::= { rlOspfv3LinkLsaEntry 14 }

rlOspfv3LinkLsaPrefixLength OBJECT-TYPE
    SYNTAX      Unsigned32
    MAX-ACCESS  read-only
    STATUS      current
    DESCRIPTION
       "IPv6 address prefix length."
  ::= { rlOspfv3LinkLsaEntry 15 }

rlOspfv3LinkLsaPrefixOptions OBJECT-TYPE
    SYNTAX      Unsigned32
    MAX-ACCESS  read-only
    STATUS      current
    DESCRIPTION
       "IPv6 address prefix options."
  ::= { rlOspfv3LinkLsaEntry 16 }

rlOspfv3LinkLsaAddressPrefix OBJECT-TYPE
    SYNTAX      InetAddress
    MAX-ACCESS  read-only
    STATUS      current
    DESCRIPTION
       "IPv6 address prefix - bit strings of length 128."
  ::= { rlOspfv3LinkLsaEntry 17 }


------------------------------------------------------------------------------
--  OSPFv3 Intra-Area-Prefix LSA Table
------------------------------------------------------------------------------

rlOspfv3IntraAreaPrefixLsaTable OBJECT-TYPE
    SYNTAX      SEQUENCE OF RlOspfv3IntraAreaPrefixLsaEntry
    MAX-ACCESS  not-accessible
    STATUS      current
    DESCRIPTION
        "Intra Area Prefix Link State Advertisement."
    ::= { rlOspfv3Lsdb 7 }

rlOspfv3IntraAreaPrefixLsaEntry OBJECT-TYPE
    SYNTAX      RlOspfv3IntraAreaPrefixLsaEntry
    MAX-ACCESS  not-accessible
    STATUS      current
    DESCRIPTION
    "A single entry from Network LSA."
    INDEX { rlOspfv3IntraAreaPrefixLsaProcessId, rlOspfv3IntraAreaPrefixLsaAreaId, rlOspfv3IntraAreaPrefixLsaLsid,
            rlOspfv3IntraAreaPrefixLsaRouterId, rlOspfv3IntraAreaPrefixLsaIdx }
       ::= { rlOspfv3IntraAreaPrefixLsaTable 1 }

RlOspfv3IntraAreaPrefixLsaEntry ::=
    SEQUENCE {
        rlOspfv3IntraAreaPrefixLsaProcessId
            RlOspfProcessID,
        rlOspfv3IntraAreaPrefixLsaAreaId
            AreaID,
        rlOspfv3IntraAreaPrefixLsaLsid
            IpAddress,
        rlOspfv3IntraAreaPrefixLsaRouterId
            RouterID,
        rlOspfv3IntraAreaPrefixLsaIdx
            Unsigned32,
        rlOspfv3IntraAreaPrefixLsaCount
            Unsigned32,
        rlOspfv3IntraAreaPrefixLsaSequence
            Integer32,
        rlOspfv3IntraAreaPrefixLsaAge
            Integer32,
        rlOspfv3IntraAreaPrefixLsaChecksum
            Integer32,
        rlOspfv3IntraAreaPrefixLsaLength
            Unsigned32,
        rlOspfv3IntraAreaPrefixLsaNumPrefixes
            Unsigned32,
        rlOspfv3IntraAreaPrefixLsaReferenceLsType
            Unsigned32,
        rlOspfv3IntraAreaPrefixLsaReferenceLsId
            Unsigned32,
        rlOspfv3IntraAreaPrefixLsaReferenceAdvRouter
            Unsigned32,
        rlOspfv3IntraAreaPrefixLsaMetric
            Unsigned32,
        rlOspfv3IntraAreaPrefixLsaPrefixLength
            Unsigned32,
        rlOspfv3IntraAreaPrefixLsaPrefixOptions
            Unsigned32,
        rlOspfv3IntraAreaPrefixLsaAddressPrefix
            InetAddress
}

rlOspfv3IntraAreaPrefixLsaProcessId OBJECT-TYPE
      SYNTAX   RlOspfProcessID
      MAX-ACCESS   read-only
      STATUS   current
      DESCRIPTION
         "A 32-bit integer uniquely identifying an OSPFv3 process."
    ::= { rlOspfv3IntraAreaPrefixLsaEntry 1 }

rlOspfv3IntraAreaPrefixLsaAreaId OBJECT-TYPE
    SYNTAX      AreaID
    MAX-ACCESS  read-only
    STATUS      current
    DESCRIPTION
       "The 32 bit identifier of the Area  from  which
        the LSA was received."
    REFERENCE
       "OSPFv3 Version 2, Appendix C.2 Area parameters"
  ::= { rlOspfv3IntraAreaPrefixLsaEntry 2 }

rlOspfv3IntraAreaPrefixLsaLsid OBJECT-TYPE
    SYNTAX      IpAddress
    MAX-ACCESS  read-only
    STATUS      current
    DESCRIPTION
       "The Link State ID is an LS Type Specific field
        containing either a Router ID or an IP Address;
        it identifies the piece of the  routing  domain
        that is being described by the advertisement."
    REFERENCE
       "OSPFv3 Version 2, Section 12.1.4 Link State ID"
  ::= { rlOspfv3IntraAreaPrefixLsaEntry 3 }

rlOspfv3IntraAreaPrefixLsaRouterId OBJECT-TYPE
    SYNTAX      RouterID
    MAX-ACCESS  read-only
    STATUS      current
    DESCRIPTION
       "The 32 bit number that uniquely identifies the
        originating router in the Autonomous System."
    REFERENCE
       "OSPFv3 Version 2, Appendix C.1 Global parameters"
  ::= { rlOspfv3IntraAreaPrefixLsaEntry 4 }

rlOspfv3IntraAreaPrefixLsaIdx OBJECT-TYPE
    SYNTAX      Unsigned32 (1.. 65535)
    MAX-ACCESS  read-only
    STATUS      current
    DESCRIPTION
       "The index is a unsigned 32-bit integer.
        It is used as sequence number of entry
        in the LSA and relevant only for Router
        or Network LSA which can contain
        unlimited number of entries."
  ::= { rlOspfv3IntraAreaPrefixLsaEntry 5 }

rlOspfv3IntraAreaPrefixLsaCount OBJECT-TYPE
    SYNTAX      Unsigned32 (1.. 65535)
    MAX-ACCESS  read-only
    STATUS      current
    DESCRIPTION
       "Number of entries containg is the LSA."
  ::= { rlOspfv3IntraAreaPrefixLsaEntry 6 }

rlOspfv3IntraAreaPrefixLsaSequence OBJECT-TYPE
    SYNTAX      Integer32
    MAX-ACCESS  read-only
    STATUS      current
    DESCRIPTION
       "The sequence number field is a signed  32-bit
        integer. It is used to detect old and duplicate
        link state advertisements. The space of sequence
        numbers is linearly ordered. The larger the
        sequence number the more recent the advertisement."
    REFERENCE
       "OSPFv3 Version 2, Section 12.1.6 LS sequence number"
  ::= { rlOspfv3IntraAreaPrefixLsaEntry 7 }


rlOspfv3IntraAreaPrefixLsaAge OBJECT-TYPE
    SYNTAX      Integer32    -- Should be 0..MaxAge
    MAX-ACCESS  read-only
    STATUS      current
    DESCRIPTION
       "This field is the age of the link state
        advertisement in seconds."
       REFERENCE
          "OSPFv3 Version 2, Section 12.1.1 LS age"
  ::= { rlOspfv3IntraAreaPrefixLsaEntry 8 }

rlOspfv3IntraAreaPrefixLsaChecksum OBJECT-TYPE
    SYNTAX      Integer32
    MAX-ACCESS  read-only
    STATUS      current
    DESCRIPTION
       "This field is the checksum of the complete contents
        of the advertisement, excepting the age field.
        The age field is excepted so that an advertisement's
        age can be incremented without updating the checksum.
        The checksum used is the same that is used for ISO
        connectionless datagrams; it is commonly referred
        to as the Fletcher checksum."
    REFERENCE
       "OSPFv3 Version 2, Section 12.1.7 LS checksum"
  ::= { rlOspfv3IntraAreaPrefixLsaEntry 9 }

rlOspfv3IntraAreaPrefixLsaLength OBJECT-TYPE
    SYNTAX      Unsigned32
    MAX-ACCESS  read-only
    STATUS      current
    DESCRIPTION
       "The lenth in bytes of the LSA.
        This includes the 20 byte LSA header."
  ::= { rlOspfv3IntraAreaPrefixLsaEntry 10 }

rlOspfv3IntraAreaPrefixLsaNumPrefixes OBJECT-TYPE
    SYNTAX      Unsigned32
    MAX-ACCESS  read-only
    STATUS      current
    DESCRIPTION
       "Number of IPv6 address prefixes contained in the LSA."
  ::= { rlOspfv3IntraAreaPrefixLsaEntry 11 }

rlOspfv3IntraAreaPrefixLsaReferenceLsType OBJECT-TYPE
    SYNTAX      Unsigned32
    MAX-ACCESS  read-only
    STATUS      current
    DESCRIPTION
       "Referenced LS Type:
        If the Referenced LS type is 1, the prefixes are associated with a router-LSA.
        If Referenced LS type is 2, the prefixes are associated with a network-LSA."
  ::= { rlOspfv3IntraAreaPrefixLsaEntry 12 }

rlOspfv3IntraAreaPrefixLsaReferenceLsId OBJECT-TYPE
    SYNTAX      Unsigned32
    MAX-ACCESS  read-only
    STATUS      current
    DESCRIPTION
       "Referenced Link State ID:
       If the prefixes are associated with a router-LSA, the Referenced Link State ID should be 0.
       If the prefixes are associated with a network-LSA, the Referenced Link State ID should be
       the Interface ID of the link's Designated Router."
  ::= { rlOspfv3IntraAreaPrefixLsaEntry 13 }

rlOspfv3IntraAreaPrefixLsaReferenceAdvRouter OBJECT-TYPE
    SYNTAX      Unsigned32
    MAX-ACCESS  read-only
    STATUS      current
    DESCRIPTION
       "Referenced Advertising Router: If the prefixes are associated with a router-LSA,
       the Referenced Advertising Router should be the originating router's Router ID.
       If the prefixes are associated with a network-LSA,
       Referenced Advertising Router should be the Designated Router's Router ID."
  ::= { rlOspfv3IntraAreaPrefixLsaEntry 14 }

rlOspfv3IntraAreaPrefixLsaMetric OBJECT-TYPE
    SYNTAX      Unsigned32
    MAX-ACCESS  read-only
    STATUS      current
    DESCRIPTION
       "The cost of this route.  Expressed in the same units as the
      interface costs in the router-LSAs."
  ::= { rlOspfv3IntraAreaPrefixLsaEntry 15 }

rlOspfv3IntraAreaPrefixLsaPrefixLength OBJECT-TYPE
    SYNTAX      Unsigned32
    MAX-ACCESS  read-only
    STATUS      current
    DESCRIPTION
       "IPv6 address prefix length."
  ::= { rlOspfv3IntraAreaPrefixLsaEntry 16 }

rlOspfv3IntraAreaPrefixLsaPrefixOptions OBJECT-TYPE
    SYNTAX      Unsigned32
    MAX-ACCESS  read-only
    STATUS      current
    DESCRIPTION
       "IPv6 address prefix options."
  ::= { rlOspfv3IntraAreaPrefixLsaEntry 17 }

rlOspfv3IntraAreaPrefixLsaAddressPrefix OBJECT-TYPE
    SYNTAX      InetAddress
    MAX-ACCESS  read-only
    STATUS      current
    DESCRIPTION
       "IPv6 address prefix - bit strings of length 128."
  ::= { rlOspfv3IntraAreaPrefixLsaEntry 18 }


END
