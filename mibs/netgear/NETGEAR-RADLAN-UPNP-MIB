NETGEAR-RADLAN-UPNP-MIB DEFINITIONS ::= BEGIN

IMPORTS
    rnd             FROM NETGEAR-RADLAN-MIB
    OBJECT-TYPE,
    MODULE-IDENTITY FROM SNMPv2-SMI
    TEXTUAL-CONVENTION, TruthValue, DisplayString
                    FROM SNMPv2-TC;


rlUPnP MODULE-IDENTITY
         LAST-UPDATED "200603260000Z"
         ORGANIZATION "Radlan Computer Communications Ltd."
         CONTACT-INFO
                "radlan.com"
         DESCRIPTION
                "The private MIB module definition for UPNP."
         REVISION "200603260000Z"
         DESCRIPTION
                "Initial revision."
        ::= { rnd 109 }

rlUPnPUniqueDeviceName OBJECT-TYPE
    SYNTAX      DisplayString
    MAX-ACCESS  read-only
    STATUS      current
    DESCRIPTION
        "The UDN (Unique Device Name) of the device."
    ::= {rlUPnP 1 }

rlUPnPEnabling OBJECT-TYPE
    SYNTAX      INTEGER {enabled(1), disabled(2)}
    MAX-ACCESS  read-write
    STATUS      current
    DESCRIPTION
        "Indicates whether UPNP is enabled or disabled in the current device.
         The default state is device-dependent."
    ::= {rlUPnP 2 }

END
