-- End - JUNIPER-WX-GLOBAL-MIB Module

-- ========================================================================
-- Start - JUNIPER-WX-STATUS-MIB Module

JUNIPER-WX-STATUS-MIB DEFINITIONS ::= BEGIN

IMPORTS
	DisplayString
		FROM SNMPv2-TC
	jnxWxGrpStatus
		FROM JUNIPER-WX-GLOBAL-MIB;

------------------------------
-- System Status Group --
------------------------------

jnxWxGrpStatusSys OBJECT-IDENTITY
    STATUS  current
    DESCRIPTION
      "This group contains WX system status information.
      "
    ::= { jnxWxGrpStatus 1 }

jnxWxGrpStatusSysModel OBJECT-TYPE
    SYNTAX INTEGER {
        wxc250(1),
        wxc500(2),
        wxc590(3),
        wxc1800(4),
        wxc2600(5),
        wxc3400(6),
        wxc7800(7),
        other(8)
      }
    MAX-ACCESS  read-only
    STATUS  current
    DESCRIPTION
      "The device model number.
      "
    ::= { jnxWxGrpStatusSys 1 }

jnxWxGrpStatusSysSwVersion OBJECT-TYPE
    SYNTAX      DisplayString (SIZE(0..64))
    MAX-ACCESS  read-only
    STATUS  current
    DESCRIPTION
      "The software version for this device.
      "
    ::= { jnxWxGrpStatusSys 2 }

jnxWxGrpStatusSysHwVersion OBJECT-TYPE
    SYNTAX      DisplayString (SIZE(0..64))
    MAX-ACCESS  read-only
    STATUS  current
    DESCRIPTION
      "The hardware version for this device.
      "
    ::= { jnxWxGrpStatusSys 3 }

------------------------------
-- Application Status Group --
------------------------------
jnxWxGrpStatusApp OBJECT-IDENTITY
    STATUS  current
    DESCRIPTION
      "This group contains application status information.
      "
    ::= { jnxWxGrpStatus 2 }

jnxWxGrpStatusAppMonCount OBJECT-TYPE
    SYNTAX  Integer32
    MAX-ACCESS  read-only
    STATUS  current
    DESCRIPTION
      "Number of applications currently being monitored.
      "
    ::= { jnxWxGrpStatusApp 1 }

jnxWxGrpStatusAppTable OBJECT-TYPE
    SYNTAX  SEQUENCE OF JnxWxGrpStatusAppEntry
    MAX-ACCESS  not-accessible
    STATUS  current
    DESCRIPTION
      "This table displays the application level status.
       It contains information for only the applications currently
       being monitored.
      "
    ::= { jnxWxGrpStatusApp 2 }

jnxWxGrpStatusAppEntry OBJECT-TYPE
    SYNTAX  JnxWxGrpStatusAppEntry
    MAX-ACCESS  not-accessible
    STATUS  current
    DESCRIPTION
      "A row in jnxWxGrpStatusAppTable.
      "
    INDEX   { jnxWxGrpStatusAppId }
    ::= { jnxWxGrpStatusAppTable 1 }

JnxWxGrpStatusAppEntry ::=
    SEQUENCE
    {
      jnxWxGrpStatusAppId
        Integer32,
      jnxWxGrpStatusAppName
        DisplayString,
      jnxWxGrpStatusAppType
        INTEGER
    }

jnxWxGrpStatusAppId OBJECT-TYPE
    SYNTAX  Integer32
    MAX-ACCESS not-accessible
    STATUS  current
    DESCRIPTION
      "The unique application ID.
      "
    ::= { jnxWxGrpStatusAppEntry 1 }

jnxWxGrpStatusAppName OBJECT-TYPE
    SYNTAX      DisplayString (SIZE(0..64))
    MAX-ACCESS  read-only
    STATUS  current
    DESCRIPTION
      "The application name.
      "
    ::= { jnxWxGrpStatusAppEntry 2 }

jnxWxGrpStatusAppType OBJECT-TYPE
    SYNTAX      INTEGER {
        default(1),
        ftp(2)
      }
    MAX-ACCESS  read-only
    STATUS  current
    DESCRIPTION
      "The application type.
      "
    ::= { jnxWxGrpStatusAppEntry 3 }

------------------------------
-- Remote WX Status Group --
------------------------------
jnxWxGrpStatusRemoteWx OBJECT-IDENTITY
    STATUS  current
    DESCRIPTION
      "This group contains remote WX status information.
      "
    ::= { jnxWxGrpStatus 3 }

jnxWxGrpStatusRemoteWxMonCount OBJECT-TYPE
    SYNTAX  Integer32
    MAX-ACCESS  read-only
    STATUS  current
    DESCRIPTION
      "Number of remote WXs currently being monitored.
      "
    ::= { jnxWxGrpStatusRemoteWx 1 }

jnxWxGrpStatusRemoteWxTable OBJECT-TYPE
    SYNTAX  SEQUENCE OF JnxWxGrpStatusRemoteWxEntry
    MAX-ACCESS  not-accessible
    STATUS  current
    DESCRIPTION
      "This table displays the application level status.
       It contains information for only the applications currently
       being monitored.
      "
    ::= { jnxWxGrpStatusRemoteWx 2 }

jnxWxGrpStatusRemoteWxEntry OBJECT-TYPE
    SYNTAX  JnxWxGrpStatusRemoteWxEntry
    MAX-ACCESS  not-accessible
    STATUS  current
    DESCRIPTION
      "A row in jnxWxGrpStatusRemoteWxTable.
      "
    INDEX   { jnxWxGrpStatusRemoteWxId }
    ::= { jnxWxGrpStatusRemoteWxTable 1 }

JnxWxGrpStatusRemoteWxEntry ::=
    SEQUENCE
    {
      jnxWxGrpStatusRemoteWxId
        Integer32,
      jnxWxGrpStatusRemoteWxName
        DisplayString,
      jnxWxGrpStatusRemoteWxType
        INTEGER
    }

jnxWxGrpStatusRemoteWxId OBJECT-TYPE
    SYNTAX  Integer32
    MAX-ACCESS not-accessible
    STATUS  current
    DESCRIPTION
      "The unique Remote WX ID.
      "
    ::= { jnxWxGrpStatusRemoteWxEntry 1 }

jnxWxGrpStatusRemoteWxName OBJECT-TYPE
    SYNTAX      DisplayString (SIZE(0..64))
    MAX-ACCESS  read-only
    STATUS  current
    DESCRIPTION
      "The remote WX name.
      "
    ::= { jnxWxGrpStatusRemoteWxEntry 2 }

jnxWxGrpStatusRemoteWxType OBJECT-TYPE
    SYNTAX      INTEGER {
        wx-device(1),
        wx-client(2),
        non-wx-device(3)
      }
    MAX-ACCESS  read-only
    STATUS  current
    DESCRIPTION
      "The remote WX type.
      "
    ::= { jnxWxGrpStatusRemoteWxEntry 3 }

END
