-- STE2.mib
-- MIB generated by MG-SOFT Visual MIB Builder 2023 (64-bit) Version 16.00  Build 1600
-- úterý, duben 18, 2023 at 16:17:12
--

	STE2-MIB DEFINITIONS ::= BEGIN
 
		IMPORTS
			OBJECT-TYPE			
				FROM RFC-1212			
			TRAP-TYPE			
				FROM RFC-1215			
			enterprises			
				FROM RFC1155-SMI			
			sysName, DisplayString			
				FROM RFC1213-MIB;
	
	
--
-- Type definitions
--
	
--  Type Definitions
-- 
		PositiveInteger ::= INTEGER (1..2147483647)

		OnOff ::= INTEGER
			{
			off(0),
			on(1)
			}

		IOName ::= DisplayString (SIZE (0..16))

		InputAlarmState ::= INTEGER
			{
			normal(0),
			alarm(1)
			}

		SensorName ::= DisplayString (SIZE (0..16))

		SensorState ::= INTEGER
			{
			invalid(0),
			normal(1),
			outofrangelo(2),
			outofrangehi(3),
			alarmlo(4),
			alarmhi(5)
			}

		SensorString ::= DisplayString (SIZE (0..10))

		SensorValue ::= INTEGER

		SensorSN ::= DisplayString (SIZE (0..16))

--  0x7FFF FFFF
		UnitType ::= INTEGER
			{
			none(0),
			celsius(1),
			fahrenheit(2),
			kelvin(3),
			percent(4)
			}

		SensorID ::= INTEGER

	
--
-- Node definitions
--
	
--  Node Definitions
-- 
		-- 1.3.6.1.4.1.21796
		hwgroup OBJECT IDENTIFIER ::= { enterprises 21796 }

		
		-- 1.3.6.1.4.1.21796.4
		x390 OBJECT IDENTIFIER ::= { hwgroup 4 }

		
		-- 1.3.6.1.4.1.21796.4.9
		ste2 OBJECT IDENTIFIER ::= { x390 9 }

		
--  Input Dry Contacts ----------------------------------------------------------
		-- 1.3.6.1.4.1.21796.4.9.1
		inpTable OBJECT-TYPE
			SYNTAX SEQUENCE OF InpEntry
			ACCESS not-accessible
			STATUS mandatory
			DESCRIPTION
				"A list of binary input entries."
			::= { ste2 1 }

		
		-- 1.3.6.1.4.1.21796.4.9.1.1
		inpEntry OBJECT-TYPE
			SYNTAX InpEntry
			ACCESS not-accessible
			STATUS mandatory
			DESCRIPTION
				"An entry containing information applicable
				to a particular binary input."
			INDEX { inpIndex }
			::= { inpTable 1 }

		
		InpEntry ::=
			SEQUENCE { 
				inpIndex
					PositiveInteger,
				inpValue
					OnOff,
				inpName
					IOName,
				inpAlarmState
					InputAlarmState
			 }

		-- 1.3.6.1.4.1.21796.4.9.1.1.1
		inpIndex OBJECT-TYPE
			SYNTAX PositiveInteger
			ACCESS read-only
			STATUS mandatory
			DESCRIPTION
				"The binary input index."
			::= { inpEntry 1 }

		
		-- 1.3.6.1.4.1.21796.4.9.1.1.2
		inpValue OBJECT-TYPE
			SYNTAX OnOff
			ACCESS read-only
			STATUS mandatory
			DESCRIPTION
				"The binary input value."
			::= { inpEntry 2 }

		
		-- 1.3.6.1.4.1.21796.4.9.1.1.3
		inpName OBJECT-TYPE
			SYNTAX IOName
			ACCESS read-only
			STATUS mandatory
			DESCRIPTION
				"The binary input name."
			::= { inpEntry 3 }

		
		-- 1.3.6.1.4.1.21796.4.9.1.1.4
		inpAlarmState OBJECT-TYPE
			SYNTAX InputAlarmState
			ACCESS read-only
			STATUS mandatory
			DESCRIPTION
				"The binary input alarm state."
			::= { inpEntry 4 }

		
--  Sensors ---------------------------------------------------------------------
		-- 1.3.6.1.4.1.21796.4.9.3
		sensTable OBJECT-TYPE
			SYNTAX SEQUENCE OF SensEntry
			ACCESS not-accessible
			STATUS mandatory
			DESCRIPTION
				"A list of sensor table entries. The number
				of entries corresponds with number of detected sensors."
			::= { ste2 3 }

		
		-- 1.3.6.1.4.1.21796.4.9.3.1
		sensEntry OBJECT-TYPE
			SYNTAX SensEntry
			ACCESS not-accessible
			STATUS mandatory
			DESCRIPTION
				"An entry containing information applicable to a
				particular sensor."
			INDEX { sensIndex }
			::= { sensTable 1 }

		
		SensEntry ::=
			SEQUENCE { 
				sensIndex
					PositiveInteger,
				sensName
					SensorName,
				sensState
					SensorState,
				sensString
					SensorString,
				sensValue
					SensorValue,
				sensSN
					SensorSN,
				sensUnit
					UnitType,
				sensID
					SensorID
			 }

		-- 1.3.6.1.4.1.21796.4.9.3.1.1
		sensIndex OBJECT-TYPE
			SYNTAX PositiveInteger
			ACCESS read-only
			STATUS mandatory
			DESCRIPTION
				"The sensor index."
			::= { sensEntry 1 }

		
		-- 1.3.6.1.4.1.21796.4.9.3.1.2
		sensName OBJECT-TYPE
			SYNTAX SensorName
			ACCESS read-only
			STATUS mandatory
			DESCRIPTION
				"The sensor name."
			::= { sensEntry 2 }

		
		-- 1.3.6.1.4.1.21796.4.9.3.1.3
		sensState OBJECT-TYPE
			SYNTAX SensorState
			ACCESS read-only
			STATUS mandatory
			DESCRIPTION
				"The sensor state."
			::= { sensEntry 3 }

		
		-- 1.3.6.1.4.1.21796.4.9.3.1.4
		sensString OBJECT-TYPE
			SYNTAX SensorString
			ACCESS read-only
			STATUS mandatory
			DESCRIPTION
				"The string representation of sensor value."
			::= { sensEntry 4 }

		
		-- 1.3.6.1.4.1.21796.4.9.3.1.5
		sensValue OBJECT-TYPE
			SYNTAX SensorValue
			ACCESS read-only
			STATUS mandatory
			DESCRIPTION
				"The integer (decimal * 10) representation
				of sensor value."
			::= { sensEntry 5 }

		
		-- 1.3.6.1.4.1.21796.4.9.3.1.6
		sensSN OBJECT-TYPE
			SYNTAX SensorSN
			ACCESS read-only
			STATUS mandatory
			DESCRIPTION
				"The sensor Serial number."
			::= { sensEntry 6 }

		
		-- 1.3.6.1.4.1.21796.4.9.3.1.7
		sensUnit OBJECT-TYPE
			SYNTAX UnitType
			ACCESS read-only
			STATUS mandatory
			DESCRIPTION
				"The sensor unit."
			::= { sensEntry 7 }

		
		-- 1.3.6.1.4.1.21796.4.9.3.1.8
		sensID OBJECT-TYPE
			SYNTAX SensorID
			ACCESS read-only
			STATUS mandatory
			DESCRIPTION
				"The sensor ID."
			::= { sensEntry 8 }

		
--  Application Info ------------------------------------------------------------
		-- 1.3.6.1.4.1.21796.4.9.70
		info OBJECT IDENTIFIER ::= { ste2 70 }

		
		-- 1.3.6.1.4.1.21796.4.9.70.1
		infoAddressMAC OBJECT-TYPE
			SYNTAX DisplayString (SIZE (0..17))
			ACCESS read-only
			STATUS mandatory
			DESCRIPTION
				"MAC address in text form.
				It is here to distinguish devices in trap messages."
			::= { info 1 }

		
	
--
-- Trap definitions
--
	
		ste2SensorToAlarm TRAP-TYPE 
			ENTERPRISE ste2
			VARIABLES { sysName, infoAddressMAC, sensIndex, sensID, sensName, 
				sensState, sensValue, sensUnit }
			DESCRIPTION 
				"Sensor n changed to Alarm state."
			::=  1

		ste2SensorToNormal TRAP-TYPE 
			ENTERPRISE ste2
			VARIABLES { sysName, infoAddressMAC, sensIndex, sensID, sensName, 
				sensState, sensValue, sensUnit }
			DESCRIPTION 
				"Sensor n changed to Normal state."
			::=  2

		ste2InputToAlarm TRAP-TYPE 
			ENTERPRISE ste2
			VARIABLES { sysName, infoAddressMAC, inpIndex, inpName, inpValue, 
				inpAlarmState }
			DESCRIPTION 
				"Input n changed to Alarm state."
			::=  3

		ste2InputToNormal TRAP-TYPE 
			ENTERPRISE ste2
			VARIABLES { sysName, infoAddressMAC, inpIndex, inpName, inpValue, 
				inpAlarmState }
			DESCRIPTION 
				"Input n changed to Alarm state."
			::=  4

		ste2SensorPeriodic TRAP-TYPE 
			ENTERPRISE ste2
			VARIABLES { sysName, infoAddressMAC, sensIndex, sensID, sensName, 
				sensState, sensValue, sensUnit }
			DESCRIPTION 
				"Sensor n Periodic Trap."
			::=  5

		ste2InputPeriodic TRAP-TYPE 
			ENTERPRISE ste2
			VARIABLES { sysName, infoAddressMAC, inpIndex, inpName, inpValue, 
				inpAlarmState }
			DESCRIPTION 
				"Input n Periodic Trap."
			::=  6

	
	END
