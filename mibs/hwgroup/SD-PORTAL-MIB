--
-- SD-PORTAL-MIB.mib
-- MIB generated by MG-SOFT Visual MIB Builder 2020 (64-bit) Version 14.00  Build 1400
-- Saturday, June 20, 2020 at 10:21:30
--

	SD-PORTAL-MIB DEFINITIONS ::= BEGIN
 
		IMPORTS
			OBJECT-TYPE			
				FROM RFC-1212			
			TRAP-TYPE			
				FROM RFC-1215			
			enterprises, Gauge			
				FROM RFC1155-SMI;
	
	
--
-- Type definitions
--
	
		OnOff ::= INTEGER
			{
			unknown(1),
			off(2),
			on(3),
			sensInv(4),
			devInv(5)
			}

		SensorType ::= INTEGER
			{
			unknown(1),
			binInput(2),
			binOutput(3),
			generic(4),
			counter(5),
			internal1(6),
			internal2(7)
			}

		SensorState ::= INTEGER
			{
			unknown(1),
			normal(2),
			sensInv(3),
			devInv(4),
			ofrLow(5),
			ofrHi(6),
			alarm(7)
			}

		Alias ::= OCTET STRING (SIZE (0..255))

		Name ::= OCTET STRING (SIZE (0..32))

		PositiveInteger ::= INTEGER (1..2147483647)

		InputAlarmSetup ::= INTEGER
			{
			inactive(1),
			activeOn(2),
			activeOff(3)
			}

		SensorUnit ::= OCTET STRING (SIZE (0..8))

		GaugeIdx ::= Gauge (1..4294967295)

		ValueTxt ::= OCTET STRING (SIZE (1..14))

		HWID ::= OCTET STRING (SIZE (1..25))

		HWaddress ::= OCTET STRING (SIZE (1..25))

		ExtUTCTime ::= OCTET STRING (SIZE (13 | 15))

		AlarmState ::= INTEGER

	
--
-- Node definitions
--
	
		-- 1.3.6.1.4.1.21796
		hwgroup OBJECT IDENTIFIER ::= { enterprises 21796 }

		
		-- 1.3.6.1.4.1.21796.5
		portal OBJECT IDENTIFIER ::= { hwgroup 5 }

		
		-- 1.3.6.1.4.1.21796.5.1
		sensdesk OBJECT IDENTIFIER ::= { portal 1 }

		
		-- 1.3.6.1.4.1.21796.5.1.1
		sdTraps OBJECT IDENTIFIER ::= { sensdesk 1 }

		
		-- 1.3.6.1.4.1.21796.5.1.2
		devTable OBJECT-TYPE
			SYNTAX SEQUENCE OF DevEntry
			ACCESS not-accessible
			STATUS mandatory
			DESCRIPTION
				"A list of device table entries. The number of entries corresponds with number of detected devices."
			::= { sensdesk 2 }

		
		-- 1.3.6.1.4.1.21796.5.1.2.1
		devEntry OBJECT-TYPE
			SYNTAX DevEntry
			ACCESS not-accessible
			STATUS mandatory
			DESCRIPTION
				"An entry containing information applicable to a particular devices."
			INDEX { devIndex }
			::= { devTable 1 }

		
		DevEntry ::=
			SEQUENCE { 
				devIndex
					GaugeIdx,
				devId
					PositiveInteger,
				devHW
					HWaddress,
				devName
					Name,
				devAlias
					Alias,
				devType
					INTEGER,
				devState
					SensorState,
				devDescription
					OCTET STRING,
				devLastRead
					ExtUTCTime
			 }

		-- 1.3.6.1.4.1.21796.5.1.2.1.1
		devIndex OBJECT-TYPE
			SYNTAX GaugeIdx
			ACCESS read-only
			STATUS mandatory
			DESCRIPTION
				"The device index."
			::= { devEntry 1 }

		
		-- 1.3.6.1.4.1.21796.5.1.2.1.2
		devId OBJECT-TYPE
			SYNTAX PositiveInteger
			ACCESS read-only
			STATUS mandatory
			DESCRIPTION
				"The device ID (in portal)."
			::= { devEntry 2 }

		
		-- 1.3.6.1.4.1.21796.5.1.2.1.3
		devHW OBJECT-TYPE
			SYNTAX HWaddress
			ACCESS read-only
			STATUS mandatory
			DESCRIPTION
				"HW address of device"
			::= { devEntry 3 }

		
		-- 1.3.6.1.4.1.21796.5.1.2.1.4
		devName OBJECT-TYPE
			SYNTAX Name
			ACCESS read-only
			STATUS mandatory
			DESCRIPTION
				"The device name (in device)."
			::= { devEntry 4 }

		
		-- 1.3.6.1.4.1.21796.5.1.2.1.5
		devAlias OBJECT-TYPE
			SYNTAX Alias
			ACCESS read-write
			STATUS mandatory
			DESCRIPTION
				"The device name (in portal)."
			::= { devEntry 5 }

		
		-- 1.3.6.1.4.1.21796.5.1.2.1.6
		devType OBJECT-TYPE
			SYNTAX INTEGER
			ACCESS read-only
			STATUS mandatory
			DESCRIPTION
				"The Type of device. "
			::= { devEntry 6 }

		
		-- 1.3.6.1.4.1.21796.5.1.2.1.7
		devState OBJECT-TYPE
			SYNTAX SensorState
			ACCESS read-only
			STATUS mandatory
			DESCRIPTION
				"The Type of device. "
			::= { devEntry 7 }

		
		-- 1.3.6.1.4.1.21796.5.1.2.1.8
		devDescription OBJECT-TYPE
			SYNTAX OCTET STRING (SIZE (0..255))
			ACCESS read-write
			STATUS mandatory
			DESCRIPTION
				"The device description."
			::= { devEntry 8 }

		
		-- 1.3.6.1.4.1.21796.5.1.2.1.9
		devLastRead OBJECT-TYPE
			SYNTAX ExtUTCTime
			ACCESS read-only
			STATUS mandatory
			DESCRIPTION
				"Time of last read success"
			::= { devEntry 9 }

		
		-- 1.3.6.1.4.1.21796.5.1.3
		sensTable OBJECT-TYPE
			SYNTAX SEQUENCE OF SensEntry
			ACCESS not-accessible
			STATUS mandatory
			DESCRIPTION
				"A list of sensor table entries. The number of entries corresponds with number of detected sensors."
			::= { sensdesk 3 }

		
		-- 1.3.6.1.4.1.21796.5.1.3.1
		sensEntry OBJECT-TYPE
			SYNTAX SensEntry
			ACCESS not-accessible
			STATUS mandatory
			DESCRIPTION
				"An entry containing information applicable to a particular sensor."
			INDEX { sensIndex }
			::= { sensTable 1 }

		
		SensEntry ::=
			SEQUENCE { 
				sensIndex
					GaugeIdx,
				sensId
					PositiveInteger,
				sensHWId
					HWID,
				sensName
					Name,
				sensAlias
					Alias,
				sensValue
					INTEGER,
				sensValueTxt
					ValueTxt,
				sensUnit
					SensorUnit,
				sensExp
					INTEGER,
				sensMin
					INTEGER,
				sensMax
					INTEGER,
				sensHyst
					INTEGER,
				sensDelay
					INTEGER,
				sensType
					SensorType,
				sensShift
					INTEGER,
				sensDescription
					OCTET STRING,
				sensState
					SensorState,
				sensDevId
					PositiveInteger,
				sensLastRead
					ExtUTCTime
			 }

		-- 1.3.6.1.4.1.21796.5.1.3.1.1
		sensIndex OBJECT-TYPE
			SYNTAX GaugeIdx
			ACCESS read-only
			STATUS mandatory
			DESCRIPTION
				"The sensor index."
			::= { sensEntry 1 }

		
		-- 1.3.6.1.4.1.21796.5.1.3.1.2
		sensId OBJECT-TYPE
			SYNTAX PositiveInteger
			ACCESS read-only
			STATUS mandatory
			DESCRIPTION
				"The sensor ID (in portal)."
			::= { sensEntry 2 }

		
		-- 1.3.6.1.4.1.21796.5.1.3.1.3
		sensHWId OBJECT-TYPE
			SYNTAX HWID
			ACCESS read-only
			STATUS mandatory
			DESCRIPTION
				"The sensor Unique HWID."
			::= { sensEntry 3 }

		
		-- 1.3.6.1.4.1.21796.5.1.3.1.4
		sensName OBJECT-TYPE
			SYNTAX Name
			ACCESS read-only
			STATUS mandatory
			DESCRIPTION
				"The sensor name (in device)."
			::= { sensEntry 4 }

		
		-- 1.3.6.1.4.1.21796.5.1.3.1.5
		sensAlias OBJECT-TYPE
			SYNTAX Alias
			ACCESS read-write
			STATUS mandatory
			DESCRIPTION
				"The sensor name (in portal)."
			::= { sensEntry 5 }

		
		-- 1.3.6.1.4.1.21796.5.1.3.1.6
		sensValue OBJECT-TYPE
			SYNTAX INTEGER
			ACCESS read-only
			STATUS mandatory
			DESCRIPTION
				"The integer representation of sensor value."
			::= { sensEntry 6 }

		
		-- 1.3.6.1.4.1.21796.5.1.3.1.7
		sensValueTxt OBJECT-TYPE
			SYNTAX ValueTxt
			ACCESS read-only
			STATUS mandatory
			DESCRIPTION
				"The integer representation of sensor value."
			::= { sensEntry 7 }

		
		-- 1.3.6.1.4.1.21796.5.1.3.1.8
		sensUnit OBJECT-TYPE
			SYNTAX SensorUnit
			ACCESS read-only
			STATUS mandatory
			DESCRIPTION
				"The sensor unit."
			::= { sensEntry 8 }

		
		-- 1.3.6.1.4.1.21796.5.1.3.1.9
		sensExp OBJECT-TYPE
			SYNTAX INTEGER
			ACCESS read-only
			STATUS mandatory
			DESCRIPTION
				"The integer representation of exponent for sensor value."
			::= { sensEntry 9 }

		
		-- 1.3.6.1.4.1.21796.5.1.3.1.10
		sensMin OBJECT-TYPE
			SYNTAX INTEGER
			ACCESS read-write
			STATUS mandatory
			DESCRIPTION
				"The integer representation of exponent for sensor value."
			::= { sensEntry 10 }

		
		-- 1.3.6.1.4.1.21796.5.1.3.1.11
		sensMax OBJECT-TYPE
			SYNTAX INTEGER
			ACCESS read-write
			STATUS mandatory
			DESCRIPTION
				"The integer representation of exponent for sensor value."
			::= { sensEntry 11 }

		
		-- 1.3.6.1.4.1.21796.5.1.3.1.12
		sensHyst OBJECT-TYPE
			SYNTAX INTEGER
			ACCESS read-write
			STATUS mandatory
			DESCRIPTION
				"The integer representation of exponent for sensor value."
			::= { sensEntry 12 }

		
		-- 1.3.6.1.4.1.21796.5.1.3.1.13
		sensDelay OBJECT-TYPE
			SYNTAX INTEGER
			ACCESS read-write
			STATUS mandatory
			DESCRIPTION
				"The integer representation of exponent for sensor value."
			::= { sensEntry 13 }

		
		-- 1.3.6.1.4.1.21796.5.1.3.1.14
		sensType OBJECT-TYPE
			SYNTAX SensorType
			ACCESS read-only
			STATUS mandatory
			DESCRIPTION
				"The Type of sensor."
			::= { sensEntry 14 }

		
		-- 1.3.6.1.4.1.21796.5.1.3.1.15
		sensShift OBJECT-TYPE
			SYNTAX INTEGER
			ACCESS read-write
			STATUS mandatory
			DESCRIPTION
				"The integer representation of shift value from raw value (from device)."
			::= { sensEntry 15 }

		
		-- 1.3.6.1.4.1.21796.5.1.3.1.16
		sensDescription OBJECT-TYPE
			SYNTAX OCTET STRING (SIZE (0..255))
			ACCESS read-write
			STATUS mandatory
			DESCRIPTION
				"The sensor description."
			::= { sensEntry 16 }

		
		-- 1.3.6.1.4.1.21796.5.1.3.1.17
		sensState OBJECT-TYPE
			SYNTAX SensorState
			ACCESS read-only
			STATUS mandatory
			DESCRIPTION
				"The sensor state."
			::= { sensEntry 17 }

		
		-- 1.3.6.1.4.1.21796.5.1.3.1.18
		sensDevId OBJECT-TYPE
			SYNTAX PositiveInteger
			ACCESS read-only
			STATUS mandatory
			DESCRIPTION
				"The device ID."
			::= { sensEntry 18 }

		
		-- 1.3.6.1.4.1.21796.5.1.3.1.19
		sensLastRead OBJECT-TYPE
			SYNTAX ExtUTCTime
			ACCESS read-write
			STATUS mandatory
			DESCRIPTION
				"Time of last read success"
			::= { sensEntry 19 }

		
		-- 1.3.6.1.4.1.21796.5.1.4
		inpTable OBJECT-TYPE
			SYNTAX SEQUENCE OF InpEntry
			ACCESS not-accessible
			STATUS mandatory
			DESCRIPTION
				"A list of binary input entries."
			::= { sensdesk 4 }

		
		-- 1.3.6.1.4.1.21796.5.1.4.1
		inpEntry OBJECT-TYPE
			SYNTAX InpEntry
			ACCESS not-accessible
			STATUS mandatory
			DESCRIPTION
				"An entry containing information applicable to a particular binary input."
			INDEX { inpIndex }
			::= { inpTable 1 }

		
		InpEntry ::=
			SEQUENCE { 
				inpIndex
					GaugeIdx,
				inpId
					PositiveInteger,
				inpName
					Name,
				inpAlias
					Alias,
				inpValue
					OnOff,
				inpState
					SensorState,
				inpAlarmSetup
					InputAlarmSetup,
				inpDescription
					OCTET STRING,
				inpDevId
					PositiveInteger,
				inpDelay
					INTEGER,
				inpLastRead
					ExtUTCTime
			 }

		-- 1.3.6.1.4.1.21796.5.1.4.1.1
		inpIndex OBJECT-TYPE
			SYNTAX GaugeIdx
			ACCESS read-only
			STATUS mandatory
			DESCRIPTION
				"The binary input index."
			::= { inpEntry 1 }

		
		-- 1.3.6.1.4.1.21796.5.1.4.1.2
		inpId OBJECT-TYPE
			SYNTAX PositiveInteger
			ACCESS read-only
			STATUS mandatory
			DESCRIPTION
				"The binary input ID (in portal)."
			::= { inpEntry 2 }

		
		-- 1.3.6.1.4.1.21796.5.1.4.1.3
		inpName OBJECT-TYPE
			SYNTAX Name
			ACCESS read-only
			STATUS mandatory
			DESCRIPTION
				"The binary input name (in device)."
			::= { inpEntry 3 }

		
		-- 1.3.6.1.4.1.21796.5.1.4.1.4
		inpAlias OBJECT-TYPE
			SYNTAX Alias
			ACCESS read-write
			STATUS mandatory
			DESCRIPTION
				"The binary input name (in portal)."
			::= { inpEntry 4 }

		
		-- 1.3.6.1.4.1.21796.5.1.4.1.5
		inpValue OBJECT-TYPE
			SYNTAX OnOff
			ACCESS read-only
			STATUS mandatory
			DESCRIPTION
				"The binary input value."
			::= { inpEntry 5 }

		
		-- 1.3.6.1.4.1.21796.5.1.4.1.6
		inpState OBJECT-TYPE
			SYNTAX SensorState
			ACCESS read-write
			STATUS mandatory
			DESCRIPTION
				"The binary input alarm state."
			::= { inpEntry 6 }

		
		-- 1.3.6.1.4.1.21796.5.1.4.1.7
		inpAlarmSetup OBJECT-TYPE
			SYNTAX InputAlarmSetup
			ACCESS read-write
			STATUS mandatory
			DESCRIPTION
				"You can enable alarm for this binary input. Alarm can be inactive or active for On/Off state."
			::= { inpEntry 7 }

		
		-- 1.3.6.1.4.1.21796.5.1.4.1.8
		inpDescription OBJECT-TYPE
			SYNTAX OCTET STRING (SIZE (0..255))
			ACCESS read-write
			STATUS mandatory
			DESCRIPTION
				"The input description."
			::= { inpEntry 8 }

		
		-- 1.3.6.1.4.1.21796.5.1.4.1.9
		inpDevId OBJECT-TYPE
			SYNTAX PositiveInteger
			ACCESS read-only
			STATUS mandatory
			DESCRIPTION
				"The device ID."
			::= { inpEntry 9 }

		
		-- 1.3.6.1.4.1.21796.5.1.4.1.10
		inpDelay OBJECT-TYPE
			SYNTAX INTEGER
			ACCESS read-write
			STATUS mandatory
			DESCRIPTION
				"The integer representation of exponent for sensor value."
			::= { inpEntry 10 }

		
		-- 1.3.6.1.4.1.21796.5.1.4.1.11
		inpLastRead OBJECT-TYPE
			SYNTAX ExtUTCTime
			ACCESS read-only
			STATUS mandatory
			DESCRIPTION
				"Time of last read success"
			::= { inpEntry 11 }

		
		-- 1.3.6.1.4.1.21796.5.1.5
		outTable OBJECT-TYPE
			SYNTAX SEQUENCE OF OutEntry
			ACCESS not-accessible
			STATUS mandatory
			DESCRIPTION
				"A list of binary output entries."
			::= { sensdesk 5 }

		
		-- 1.3.6.1.4.1.21796.5.1.5.1
		outEntry OBJECT-TYPE
			SYNTAX OutEntry
			ACCESS not-accessible
			STATUS mandatory
			DESCRIPTION
				"An entry containing information applicable to a particular binary output."
			INDEX { outIndex }
			::= { outTable 1 }

		
		OutEntry ::=
			SEQUENCE { 
				outIndex
					GaugeIdx,
				outId
					PositiveInteger,
				outName
					Name,
				outAlias
					Alias,
				outValue
					OnOff,
				outState
					SensorState,
				outDescription
					OCTET STRING,
				outDevId
					PositiveInteger,
				outAlarmSetup
					InputAlarmSetup,
				outLastRead
					ExtUTCTime
			 }

		-- 1.3.6.1.4.1.21796.5.1.5.1.1
		outIndex OBJECT-TYPE
			SYNTAX GaugeIdx
			ACCESS read-only
			STATUS mandatory
			DESCRIPTION
				"The binary output index"
			::= { outEntry 1 }

		
		-- 1.3.6.1.4.1.21796.5.1.5.1.2
		outId OBJECT-TYPE
			SYNTAX PositiveInteger
			ACCESS read-only
			STATUS mandatory
			DESCRIPTION
				"The binary output ID (in portal)"
			::= { outEntry 2 }

		
		-- 1.3.6.1.4.1.21796.5.1.5.1.3
		outName OBJECT-TYPE
			SYNTAX Name
			ACCESS read-only
			STATUS mandatory
			DESCRIPTION
				"The binary output name (in device)."
			::= { outEntry 3 }

		
		-- 1.3.6.1.4.1.21796.5.1.5.1.4
		outAlias OBJECT-TYPE
			SYNTAX Alias
			ACCESS read-write
			STATUS mandatory
			DESCRIPTION
				"The binary output name (in portal)."
			::= { outEntry 4 }

		
		-- 1.3.6.1.4.1.21796.5.1.5.1.5
		outValue OBJECT-TYPE
			SYNTAX OnOff
			ACCESS read-only
			STATUS mandatory
			DESCRIPTION
				"The binary output value. 0 off(open), 1 on(close)"
			::= { outEntry 5 }

		
		-- 1.3.6.1.4.1.21796.5.1.5.1.6
		outState OBJECT-TYPE
			SYNTAX SensorState
			ACCESS read-write
			STATUS mandatory
			DESCRIPTION
				"The binary output alarm state."
			::= { outEntry 6 }

		
		-- 1.3.6.1.4.1.21796.5.1.5.1.7
		outDescription OBJECT-TYPE
			SYNTAX OCTET STRING (SIZE (0..255))
			ACCESS read-write
			STATUS mandatory
			DESCRIPTION
				"The output description."
			::= { outEntry 7 }

		
		-- 1.3.6.1.4.1.21796.5.1.5.1.8
		outDevId OBJECT-TYPE
			SYNTAX PositiveInteger
			ACCESS read-only
			STATUS mandatory
			DESCRIPTION
				"The device ID."
			::= { outEntry 8 }

		
		-- 1.3.6.1.4.1.21796.5.1.5.1.9
		outAlarmSetup OBJECT-TYPE
			SYNTAX InputAlarmSetup
			ACCESS read-write
			STATUS mandatory
			DESCRIPTION
				"You can enable alarm for this binary input. Alarm can be inactive or active for On/Off state."
			::= { outEntry 9 }

		
		-- 1.3.6.1.4.1.21796.5.1.5.1.10
		outLastRead OBJECT-TYPE
			SYNTAX ExtUTCTime
			ACCESS read-only
			STATUS mandatory
			DESCRIPTION
				"Time of last read success"
			::= { outEntry 10 }

		
		-- 1.3.6.1.4.1.21796.5.1.6
		noticeTable OBJECT-TYPE
			SYNTAX SEQUENCE OF NoticeEntry
			ACCESS not-accessible
			STATUS mandatory
			DESCRIPTION
				"Description."
			::= { sensdesk 6 }

		
		-- 1.3.6.1.4.1.21796.5.1.6.1
		noticeEntry OBJECT-TYPE
			SYNTAX NoticeEntry
			ACCESS not-accessible
			STATUS mandatory
			DESCRIPTION
				"Description."
			INDEX { noticeIndex }
			::= { noticeTable 1 }

		
		NoticeEntry ::=
			SEQUENCE { 
				noticeIndex
					GaugeIdx,
				noticeId
					PositiveInteger,
				noticeName
					Alias,
				noticeUnit
					SensorUnit,
				noticeMin
					ValueTxt,
				noticeMax
					ValueTxt,
				noticeHyst
					ValueTxt,
				noticeDelay
					INTEGER
			 }

		-- 1.3.6.1.4.1.21796.5.1.6.1.1
		noticeIndex OBJECT-TYPE
			SYNTAX GaugeIdx
			ACCESS read-write
			STATUS mandatory
			DESCRIPTION
				"Description."
			::= { noticeEntry 1 }

		
		-- 1.3.6.1.4.1.21796.5.1.6.1.2
		noticeId OBJECT-TYPE
			SYNTAX PositiveInteger
			ACCESS read-write
			STATUS mandatory
			DESCRIPTION
				"Description."
			::= { noticeEntry 2 }

		
		-- 1.3.6.1.4.1.21796.5.1.6.1.3
		noticeName OBJECT-TYPE
			SYNTAX Alias
			ACCESS read-write
			STATUS mandatory
			DESCRIPTION
				"Description."
			::= { noticeEntry 3 }

		
		-- 1.3.6.1.4.1.21796.5.1.6.1.4
		noticeUnit OBJECT-TYPE
			SYNTAX SensorUnit
			ACCESS read-write
			STATUS mandatory
			DESCRIPTION
				"Description."
			::= { noticeEntry 4 }

		
		-- 1.3.6.1.4.1.21796.5.1.6.1.5
		noticeMin OBJECT-TYPE
			SYNTAX ValueTxt
			ACCESS read-write
			STATUS mandatory
			DESCRIPTION
				"Description."
			::= { noticeEntry 5 }

		
		-- 1.3.6.1.4.1.21796.5.1.6.1.6
		noticeMax OBJECT-TYPE
			SYNTAX ValueTxt
			ACCESS read-write
			STATUS mandatory
			DESCRIPTION
				"Description."
			::= { noticeEntry 6 }

		
		-- 1.3.6.1.4.1.21796.5.1.6.1.7
		noticeHyst OBJECT-TYPE
			SYNTAX ValueTxt
			ACCESS read-write
			STATUS mandatory
			DESCRIPTION
				"Description."
			::= { noticeEntry 7 }

		
		-- 1.3.6.1.4.1.21796.5.1.6.1.8
		noticeDelay OBJECT-TYPE
			SYNTAX INTEGER
			ACCESS read-write
			STATUS mandatory
			DESCRIPTION
				"Description."
			::= { noticeEntry 8 }

		
		-- 1.3.6.1.4.1.21796.5.1.7
		info OBJECT IDENTIFIER ::= { sensdesk 7 }

		
		-- 1.3.6.1.4.1.21796.5.1.7.1
		infoName OBJECT-TYPE
			SYNTAX OCTET STRING (SIZE (1..255))
			ACCESS read-write
			STATUS mandatory
			DESCRIPTION
				"Portal name."
			::= { info 1 }

		
		-- 1.3.6.1.4.1.21796.5.1.7.2
		infoAddr OBJECT-TYPE
			SYNTAX OCTET STRING (SIZE (4..255))
			ACCESS read-write
			STATUS mandatory
			DESCRIPTION
				"URL address in text form. It is here to distinguish devices in trap messages."
			::= { info 2 }

		
		-- 1.3.6.1.4.1.21796.5.1.7.3
		infoVer OBJECT-TYPE
			SYNTAX OCTET STRING (SIZE (5..12))
			ACCESS read-only
			STATUS mandatory
			DESCRIPTION
				"Portal version (release) in text form."
			::= { info 3 }

		
		-- 1.3.6.1.4.1.21796.5.1.7.4
		infoTeam OBJECT-TYPE
			SYNTAX OCTET STRING (SIZE (1..255))
			ACCESS read-only
			STATUS mandatory
			DESCRIPTION
				"MAC address in text form. It is here to distinguish devices in trap messages."
			::= { info 4 }

		
--  The Alarm group.
		-- 1.3.6.1.4.1.21796.5.1.8
		tsAlarm OBJECT IDENTIFIER ::= { sensdesk 8 }

		
		-- 1.3.6.1.4.1.21796.5.1.8.1
		tsAlarmsPresent OBJECT-TYPE
			SYNTAX Gauge
			ACCESS read-only
			STATUS mandatory
			DESCRIPTION
				"The present number of active alarm conditions."
			::= { tsAlarm 1 }
-- The present number of active alarm conditions.
		
		-- 1.3.6.1.4.1.21796.5.1.8.2
		tsAlarmTable OBJECT-TYPE
			SYNTAX SEQUENCE OF TsAlarmEntry
			ACCESS not-accessible
			STATUS mandatory
			DESCRIPTION
				"A list of alarm table entries.  The table contains
				zero, one, or many rows at any moment, depending upon
				the number of alarm conditions in effect.  The table
				is initially empty at agent startup.  The agent
				creates a row in the table each time a condition is
				detected and deletes that row when that condition no
				longer pertains.  The agent creates the first row with
				tsAlarmId equal to 1, and increments the value of
				tsAlarmId each time a new row is created, wrapping to
				the first free value greater than or equal to 1 when
				the maximum value of tsAlarmId would otherwise be
				exceeded.  Consequently, after multiple operations,
				the table may become sparse, e.g., containing entries
				for rows 95, 100, 101, and 203 and the entries should
				not be assumed to be in chronological order because
				tsAlarmId might have wrapped.
				
				The number of rows in the table at any given time is
				reflected by the value of tsAlarmsPresent."
			::= { tsAlarm 2 }

		
		-- 1.3.6.1.4.1.21796.5.1.8.2.1
		tsAlarmEntry OBJECT-TYPE
			SYNTAX TsAlarmEntry
			ACCESS not-accessible
			STATUS mandatory
			DESCRIPTION
				"An entry containing information applicable
				to a particular alarm."
			INDEX { tsAlarmIdx }
			::= { tsAlarmTable 1 }

		
		TsAlarmEntry ::=
			SEQUENCE { 
				tsAlarmIdx
					GaugeIdx,
				tsAlarmId
					PositiveInteger,
				tsAlarmDescr
					INTEGER,
				tsAlarmTime
					ExtUTCTime
			 }

		-- 1.3.6.1.4.1.21796.5.1.8.2.1.1
		tsAlarmIdx OBJECT-TYPE
			SYNTAX GaugeIdx
			ACCESS read-only
			STATUS mandatory
			DESCRIPTION
				"An index to alarm table."
			::= { tsAlarmEntry 1 }

		
--  (used in trap variables)
		-- 1.3.6.1.4.1.21796.5.1.8.2.1.2
		tsAlarmId OBJECT-TYPE
			SYNTAX PositiveInteger
			ACCESS read-only
			STATUS mandatory
			DESCRIPTION
				"A unique identifier for an alarm condition. This value must remain constant."
			::= { tsAlarmEntry 2 }

		
		-- 1.3.6.1.4.1.21796.5.1.8.2.1.3
		tsAlarmDescr OBJECT-TYPE
			SYNTAX INTEGER
				{
				inp(1),
				out(2),
				sens(3),
				dev(4)
				}
			ACCESS read-write
			STATUS mandatory
			DESCRIPTION
				"Description."
			::= { tsAlarmEntry 3 }

		
		-- 1.3.6.1.4.1.21796.5.1.8.2.1.4
		tsAlarmTime OBJECT-TYPE
			SYNTAX ExtUTCTime
			ACCESS read-only
			STATUS mandatory
			DESCRIPTION
				"The value of sysUpTime when the alarm condition was
				detected.  If the alarm condition was detected
				at the time of agent startup and presumably existed
				before agent startup, the value of tsAlarmTime shall equal 0."
			::= { tsAlarmEntry 4 }

		
	
--
-- Trap definitions
--
	
		inpAlarmStart TRAP-TYPE 
			ENTERPRISE sdTraps
			VARIABLES { infoName, infoAddr, infoTeam, tsAlarmId, noticeId, 
				tsAlarmTime, inpId, inpAlias, inpValue, inpState
				 }
			DESCRIPTION 
				"Input state entered/left alarm condition."
			::=  1
-- Input state entered/left alarm condition.
		inpAlarmEnd TRAP-TYPE 
			ENTERPRISE sdTraps
			VARIABLES { infoName, infoAddr, infoTeam, tsAlarmId, noticeId, 
				tsAlarmTime, inpId, inpAlias, inpValue, inpState
				 }
			DESCRIPTION 
				"Input state entered/left alarm condition."
			::=  2
-- Input state entered/left alarm condition.
		sensAlarmStart TRAP-TYPE 
			ENTERPRISE sdTraps
			VARIABLES { infoName, infoAddr, infoTeam, tsAlarmId, sensAlias, 
				sensValueTxt, sensValue, sensExp, sensUnit, sensMin, 
				sensMax, sensHyst, sensState, sensDescription, tsAlarmTime
				 }
			DESCRIPTION 
				"The sensor state entered/left alarm condition."
			::=  3
-- The sensor state entered/left alarm condition.
		sensAlarmEnd TRAP-TYPE 
			ENTERPRISE sdTraps
			VARIABLES { infoName, infoAddr, infoTeam, tsAlarmId, sensAlias, 
				sensValueTxt, sensValue, sensExp, sensUnit, sensMin, 
				sensMax, sensHyst, sensState, sensDescription, tsAlarmTime
				 }
			DESCRIPTION 
				"The sensor state entered/left alarm condition."
			::=  4
-- The sensor state entered/left alarm condition.
		sensNoticeStart TRAP-TYPE 
			ENTERPRISE sdTraps
			VARIABLES { infoName, infoAddr, infoTeam, tsAlarmId, sensAlias, 
				sensValueTxt, sensValue, sensExp, sensUnit, sensState, 
				noticeId, noticeName, noticeMin, noticeMax, noticeHyst, 
				tsAlarmTime }
			DESCRIPTION 
				"The sensor state entered/left alarm condition."
			::=  5
-- The sensor state entered/left alarm condition.
		sensNoticeEnd TRAP-TYPE 
			ENTERPRISE sdTraps
			VARIABLES { infoName, infoAddr, infoTeam, tsAlarmId, sensAlias, 
				sensValueTxt, sensValue, sensExp, sensUnit, sensState, 
				noticeId, noticeName, noticeMin, noticeMax, noticeHyst, 
				tsAlarmTime }
			DESCRIPTION 
				"The sensor state entered/left alarm condition."
			::=  6
-- The sensor state entered/left alarm condition.
		outAlarmStart TRAP-TYPE 
			ENTERPRISE sdTraps
			VARIABLES { infoName, infoAddr, infoTeam, tsAlarmId, noticeId, 
				tsAlarmTime, outId, outAlias, outValue, outState
				 }
			DESCRIPTION 
				"The output state entered/left alarm condition."
			::=  7
-- Output state entered/left alarm condition.
		outAlarmEnd TRAP-TYPE 
			ENTERPRISE sdTraps
			VARIABLES { infoName, infoAddr, infoTeam, tsAlarmId, noticeId, 
				tsAlarmTime, outId, outAlias, outValue, outState
				 }
			DESCRIPTION 
				"The output state entered/left alarm condition."
			::=  8
-- Output state entered/left alarm condition.
		devAlarmStart TRAP-TYPE 
			ENTERPRISE sdTraps
			VARIABLES { infoName, infoAddr, infoTeam, tsAlarmId, devAlias, 
				devName, devId, tsAlarmTime }
			DESCRIPTION 
				"The dev state entered/left alarm condition."
			::=  9
-- Output state entered/left alarm condition.
		devAlarmEnd TRAP-TYPE 
			ENTERPRISE sdTraps
			VARIABLES { infoName, infoAddr, infoTeam, tsAlarmId, devAlias, 
				devName, devId, tsAlarmTime }
			DESCRIPTION 
				"The dev state entered/left alarm condition."
			::=  10
-- Output state entered/left alarm condition.
	
	END

--
-- SD-PORTAL-MIB.mib
--
