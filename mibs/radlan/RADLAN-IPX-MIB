RADLAN-IPX-MIB DEFINITIONS ::= BEGIN

-- Title:      RADLAN IPX Private MIB
-- Version:    7.35
-- Date:       07 Nov 2003

IMPORTS
    Counter                             FROM RFC1155-SMI
    OBJECT-TYPE                         FROM RFC-1212
    PhysAddress                         FROM RFC1213-MIB
    rndIPX                              FROM RADLAN-MIB;

    NetNumber ::=  OCTET STRING (SIZE(4))

rndIPXdriver      OBJECT IDENTIFIER ::=  { rndIPX 1 }
rndIPXRip         OBJECT IDENTIFIER ::=  { rndIPX 2 }

-- Global RIP filter is defined per IPX router.

rndIPXRipFilterGlbTable OBJECT-TYPE
SYNTAX SEQUENCE OF RndIPXRipFilterGlbEntry
ACCESS  not-accessible
STATUS  mandatory
DESCRIPTION
      "The table of RIP global filters per IPX router."
::= { rndIPXRip 10 }

rndIPXRipFilterGlbEntry  OBJECT-TYPE
SYNTAX   RndIPXRipFilterGlbEntry
ACCESS    not-accessible
STATUS    mandatory
DESCRIPTION
      " An entry in the RIP global filter table "
INDEX  { rndIPXRipFilterGlbFLtype,
         rndIPXRipFilterGlbFLnumber }
::= { rndIPXRipFilterGlbTable 1 }

RndIPXRipFilterGlbEntry  ::= SEQUENCE {
      rndIPXRipFilterGlbFLtype          INTEGER,
      rndIPXRipFilterGlbFLnumber        INTEGER,
      rndIPXRipFilterGlbFLStatus        INTEGER,
      rndIPXRipFilterGlbFLnetworkPatern OCTET STRING (SIZE(4)),
      rndIPXRipFilterGlbFLnetworkMask   OCTET STRING (SIZE(4)),
      rndIPXRipFilterGlbFLaction        INTEGER
}

rndIPXRipFilterGlbFLtype  OBJECT-TYPE
SYNTAX INTEGER  {
    input(1),
    output(2)
}
ACCESS  read-only
STATUS  mandatory
DESCRIPTION
    " Type of filter - input/output "
::= {rndIPXRipFilterGlbEntry 1}

rndIPXRipFilterGlbFLnumber OBJECT-TYPE
SYNTAX  INTEGER
ACCESS  read-only
STATUS  mandatory
DESCRIPTION
   " Number of RIP filter. "
::= {rndIPXRipFilterGlbEntry  2}

rndIPXRipFilterGlbFLStatus OBJECT-TYPE
SYNTAX INTEGER  {
    valid (1),
    invalid (2),
    underCreation (3)
}
ACCESS read-write
STATUS mandatory
DESCRIPTION
   " The validity of this entry. An entry with this value set
   to invalid  may be deleted from the table with IPX
   implementation's discretion."
  DEFVAL  { valid }
::= {rndIPXRipFilterGlbEntry 3}

rndIPXRipFilterGlbFLnetworkPatern OBJECT-TYPE
SYNTAX  OCTET STRING (SIZE(4))
ACCESS  read-write
STATUS  mandatory
DESCRIPTION
   "Number of filtered network. Value 0xFFFFFFFF  applies for
   any network. "
  DEFVAL {'FFFFFFFF'H}
::= {rndIPXRipFilterGlbEntry  4}

rndIPXRipFilterGlbFLnetworkMask  OBJECT-TYPE
SYNTAX  OCTET STRING (SIZE(4))
ACCESS  read-write
STATUS  mandatory
DESCRIPTION
   "Network mask"
DEFVAL {'FFFFFFFF'H}
::= {rndIPXRipFilterGlbEntry 5}

rndIPXRipFilterGlbFLaction OBJECT-TYPE
SYNTAX INTEGER {
   deny(1),
   permit(2)
}
ACCESS  read-write
STATUS  mandatory
DESCRIPTION
   " Filter action - permit/deny for this network"
DEFVAL { permit }
::= {rndIPXRipFilterGlbEntry  6}


-- Circuit RIP filter is defined per IPX circuit number
--            (Ifindex plus type of L2 encapsulation).

rndIPXRipFilterCircuitTable OBJECT-TYPE
SYNTAX SEQUENCE OF RndIPXRipFilterCircuitEntry
ACCESS  not-accessible
STATUS  mandatory
DESCRIPTION
   "Table of input/output  RIP filters used per IPX circuit number."
::= { rndIPXRip 11 }

rndIPXRipFilterCircuitEntry  OBJECT-TYPE
SYNTAX RndIPXRipFilterCircuitEntry
ACCESS not-accessible
STATUS mandatory
DESCRIPTION
   " An entry in the Circuit RIP filter table"
INDEX  {rndIPXRipFilterCircFLIfIndex ,
        rndIPXRipFilterCircFLType,
        rndIPXRipFilterCircFLnumber}
::= { rndIPXRipFilterCircuitTable 1 }

RndIPXRipFilterCircuitEntry  ::= SEQUENCE {
      rndIPXRipFilterCircFLIfIndex       INTEGER,
      rndIPXRipFilterCircFLType          INTEGER,
      rndIPXRipFilterCircFLnumber        INTEGER,
      rndIPXRipFilterCircFLStatus        INTEGER,
      rndIPXRipFilterCircFLnetworkPatern OCTET STRING (SIZE(4)),
      rndIPXRipFilterCircFLnetworkMask   OCTET STRING (SIZE(4)),
      rndIPXRipFilterCircFLaction        INTEGER
}

rndIPXRipFilterCircFLIfIndex  OBJECT-TYPE
SYNTAX  INTEGER
ACCESS  read-only
STATUS  mandatory
DESCRIPTION
   " The Interface identifier for this filter. This value
   correspond to rndIPXIfIndex or ipxCircIndex for ET16"
::= {rndIPXRipFilterCircuitEntry 1}


rndIPXRipFilterCircFLType  OBJECT-TYPE
SYNTAX INTEGER  {
   input(1),
   output(2)
}
ACCESS read-only
STATUS mandatory
DESCRIPTION
   " Type of filter - input/output "
::= {rndIPXRipFilterCircuitEntry 2}

rndIPXRipFilterCircFLnumber OBJECT-TYPE
SYNTAX INTEGER
ACCESS read-only
STATUS mandatory
DESCRIPTION
   " Number of RIP filter for this circuit"
::= {rndIPXRipFilterCircuitEntry  3}

rndIPXRipFilterCircFLStatus   OBJECT-TYPE
SYNTAX INTEGER  {
   valid (1),
   invalid (2),
   underCreation (3)
}
ACCESS read-write
STATUS mandatory
DESCRIPTION
   " The validity of this entry. An entry with this value set
   to invalid  may be deleted from the table with IPX
   implementation's discretion."
DEFVAL  { valid }
::= {rndIPXRipFilterCircuitEntry  4}

rndIPXRipFilterCircFLnetworkPatern  OBJECT-TYPE
SYNTAX OCTET STRING (SIZE(4))
ACCESS read-write
STATUS mandatory
DESCRIPTION
   "Number of filtered network. Value 0xFFFFFFFF applies for
   any network. "
DEFVAL {'FFFFFFFF'H}
::= {rndIPXRipFilterCircuitEntry  5}

rndIPXRipFilterCircFLnetworkMask  OBJECT-TYPE
SYNTAX OCTET STRING (SIZE(4))
ACCESS read-write
STATUS mandatory
DESCRIPTION
   "Network mask"
DEFVAL {  'FFFFFFFF'H }
::= {rndIPXRipFilterCircuitEntry 6}

rndIPXRipFilterCircFLaction OBJECT-TYPE
SYNTAX INTEGER  {
   deny(1),
   permit(2)
}
ACCESS read-write
STATUS mandatory
DESCRIPTION
   " Filter action - permit/deny "
DEFVAL { permit }
::= {rndIPXRipFilterCircuitEntry  7}


-- Service Advertising Protocol

rndIPXSap         OBJECT IDENTIFIER ::=  { rndIPX 3 }

rndIPXSapFilterGlbTable OBJECT-TYPE
   SYNTAX SEQUENCE OF RndIPXSapFilterGlbEntry
   ACCESS not-accessible
   STATUS mandatory
   DESCRIPTION
       "The table of SAP global filter susedper IPX router."
::= {rndIPXSap 10}

rndIPXSapFilterGlbEntry  OBJECT-TYPE
   SYNTAX RndIPXSapFilterGlbEntry
   ACCESS not-accessible
   STATUS mandatory
   DESCRIPTION
      "An entry in the SAP global filter table"
   INDEX{rndIPXSapFilterGlbFLtype,
         rndIPXSapFilterGlbFLnumber}
   ::= {rndIPXSapFilterGlbTable 1}

RndIPXSapFilterGlbEntry ::= SEQUENCE{
   rndIPXSapFilterGlbFLtype           INTEGER,
   rndIPXSapFilterGlbFLnumber         INTEGER,
   rndIPXSapFilterGlbFLStatus         INTEGER,
   rndIPXSapFilterGlbFLnetworkPatern  OCTET STRING (SIZE(4)),
   rndIPXSapFilterGlbFLnetworkMask    OCTET STRING (SIZE(4)),
   rndIPXSapFilterGlbFLserviceType    INTEGER,
   rndIPXSapFilterGlbFLserviceName    OCTET STRING (SIZE(1..48)),
   rndIPXSapFilterGlbFLaction         INTEGER
   }

rndIPXSapFilterGlbFLtype OBJECT-TYPE
   SYNTAX INTEGER{
      input(1),
      output(2)
   }
   ACCESS read-only
   STATUS mandatory
   DESCRIPTION
      "Type of filter-input/output"
   ::= {rndIPXSapFilterGlbEntry 1}

rndIPXSapFilterGlbFLnumber OBJECT-TYPE
   SYNTAX INTEGER
   ACCESS read-only
   STATUS mandatory
   DESCRIPTION
      "Number of SAP filter."
   ::= {rndIPXSapFilterGlbEntry 2}


rndIPXSapFilterGlbFLStatus OBJECT-TYPE
   SYNTAX INTEGER{
      valid(1),
      invalid(2),
      underCreation(3)
   }
   ACCESS read-write
   STATUS mandatory
   DESCRIPTION
      "The validity of this entry. An entry with this value set
       to invalid may be deleted from the table with IPX
       implementation's discretion."
DEFVAL { 1 }
::= {rndIPXSapFilterGlbEntry 3}

rndIPXSapFilterGlbFLnetworkPatern OBJECT-TYPE
   SYNTAX OCTET STRING (SIZE(4))
   ACCESS read-write
   STATUS mandatory
   DESCRIPTION
      "Number network of the filter edservice. Value
       0xFFFFFFFF applies for any network."
DEFVAL {'FFFFFFFF'H}
::= {rndIPXSapFilterGlbEntry 4}

rndIPXSapFilterGlbFLnetworkMask OBJECT-TYPE
   SYNTAX OCTET STRING (SIZE(4))
   ACCESS read-write
   STATUS mandatory
   DESCRIPTION
       "Network mask"
DEFVAL {'FFFFFFFF'H}
::= {rndIPXSapFilterGlbEntry 5}

rndIPXSapFilterGlbFLserviceType OBJECT-TYPE
   SYNTAX INTEGER
   ACCESS read-write
   STATUS mandatory
   DESCRIPTION
      "The type of the service which may be filtered ;value0xFFFF
       applies for all types of service and it's default"
DEFVAL {'FFFF'H}
::= {rndIPXSapFilterGlbEntry 6}



rndIPXSapFilterGlbFLserviceName OBJECT-TYPE
   SYNTAX OCTET STRING (SIZE(1..48))
   ACCESS read-write
   STATUS mandatory
   DESCRIPTION
      "The name of the service which may be filtered; wild
      cardas * may be used in end of the name."
DEFVAL {"*"}
::= {rndIPXSapFilterGlbEntry 7}

rndIPXSapFilterGlbFLaction OBJECT-TYPE
   SYNTAX INTEGER{
      deny(1),
      permit(2)
   }
   ACCESS read-write
   STATUS mandatory
   DESCRIPTION
      "Filter mode - permit/deny for this service"
DEFVAL {permit}
::= {rndIPXSapFilterGlbEntry 8}


-- Circuit SAP filter is defined per IPX circuit (interface identifier (Ifindex) plus
-- type of L2 encapsulation).

rndIPXSapFilterCircuitTable OBJECT-TYPE
   SYNTAX SEQUENCE OF RndIPXSapFilterCircuitEntry
   ACCESS not-accessible
   STATUS mandatory
   DESCRIPTION
      "Table of input/output SAP filter susedper IPX circuit number."
   ::= {rndIPXSap 11 }

rndIPXSapFilterCircuitEntry  OBJECT-TYPE
   SYNTAX RndIPXSapFilterCircuitEntry
   ACCESS not-accessible
   STATUS mandatory
   DESCRIPTION
       "An entry in the Circuit SAP filter table"
   INDEX { rndIPXSapFilterCircFLIfIndex,
           rndIPXSapFilterCircFLtype,
           rndIPXSapFilterCircFLnumber}
   ::= {rndIPXSapFilterCircuitTable 1 }

RndIPXSapFilterCircuitEntry ::= SEQUENCE{
   rndIPXSapFilterCircFLIfIndex       INTEGER,
   rndIPXSapFilterCircFLtype          INTEGER,
   rndIPXSapFilterCircFLnumber        INTEGER,
   rndIPXSapFilterCircFLStatus        INTEGER,
   rndIPXSapFilterCircFLnetworkPatern OCTET STRING (SIZE(4)),
   rndIPXSapFilterCircFLnetworkMask   OCTET STRING (SIZE(4)),
   rndIPXSapFilterCircFLserviceType   INTEGER,
   rndIPXSapFilterCircFLserviceName   OCTET STRING (SIZE(1..48)),
   rndIPXSapFilterCircFLaction        INTEGER
}

rndIPXSapFilterCircFLIfIndex OBJECT-TYPE
   SYNTAX INTEGER
   ACCESS read-only
   STATUS mandatory
   DESCRIPTION
      "The Interface identifier for this filter.  This value
      correspondtornd IPXIfIndex or ipxCircIndex for ET16"
   ::= {rndIPXSapFilterCircuitEntry 1}


rndIPXSapFilterCircFLtype OBJECT-TYPE
   SYNTAX INTEGER{
      input(1),
      output(2)
   }
   ACCESS read-only
   STATUS mandatory
   DESCRIPTION
      "Type of filter-input/output"
   ::= {rndIPXSapFilterCircuitEntry  2}

rndIPXSapFilterCircFLnumber OBJECT-TYPE
   SYNTAX INTEGER
   ACCESS read-only
   STATUS mandatory
   DESCRIPTION
      "Number of SAP filter. Th is value correspondto rndIPXSapFilterNumber"
   ::= {rndIPXSapFilterCircuitEntry  3}

rndIPXSapFilterCircFLStatus OBJECT-TYPE
   SYNTAX INTEGER{
      valid(1),
      invalid(2),
      underCreation(3)
   }
   ACCESS read-write
   STATUS mandatory
   DESCRIPTION
      "The validity of this entry. An entry with this value set
      to invalid may be deleted from the table with IPX implementation's discretion."
  DEFVAL { 1 }
::= {rndIPXSapFilterCircuitEntry  4}

rndIPXSapFilterCircFLnetworkPatern OBJECT-TYPE
   SYNTAX OCTET STRING (SIZE(4))
   ACCESS read-write
   STATUS mandatory
   DESCRIPTION
      "Number network of the filtered service. Value
      0xFFFFFFFF  applies for any network."
   DEFVAL {'FFFFFFFF'H}
::= {rndIPXSapFilterCircuitEntry  5}

rndIPXSapFilterCircFLnetworkMask OBJECT-TYPE
   SYNTAX OCTET STRING (SIZE(4))
   ACCESS read-write
   STATUS mandatory
   DESCRIPTION
      "Network mask"
   DEFVAL {'FFFFFFFF'H}
::= {rndIPXSapFilterCircuitEntry  6}

rndIPXSapFilterCircFLserviceType OBJECT-TYPE
   SYNTAX INTEGER
   ACCESS read-write
   STATUS mandatory
   DESCRIPTION
      "The type of the service which may be filtered; value 0xFFFF
       applies for all types of service and it's default"
   DEFVAL {'FFFF'H}
::= {rndIPXSapFilterCircuitEntry 7}

rndIPXSapFilterCircFLserviceName OBJECT-TYPE
   SYNTAX OCTET STRING (SIZE(1..48))
   ACCESS read-write
   STATUS mandatory
   DESCRIPTION
      "The name of the service which may be filtered; wild
       cardas * may be used i n end of the name."
   DEFVAL {"*"}
::= {rndIPXSapFilterCircuitEntry 8}

rndIPXSapFilterCircFLaction OBJECT-TYPE
   SYNTAX INTEGER{
       deny(1),
       permit(2)
}
   ACCESS read-write
   STATUS mandatory
   DESCRIPTION
      "Filter mode-permit/deny"
   DEFVAL {permit}
::= {rndIPXSapFilterCircuitEntry 9}

--
-- This MIB defines the management information for a system using the IPX
-- protocol.  The MIB consists of four groups:
--
--    1.  System Group - contains general information about all instances
--                       of IPX on the system
--
--    2.  Circuit Group - contains information about all circuits used by
--                        IPX on the system
--
--    3.  Forwarding Group - contains generic routing information that
--                           must be provided by any IPX routing protocol.
--
--    4.  Services Group - contains information about all known services.
--
-- The MIB is designed to support multiple instances of the IPX
-- protocol on one system via a system instance identifier which is the
-- primary index for every table in this MIB.
--
-- This MIB is designed to provide a basic framework for the management
-- of systems implementing the IPX protocol.  Additional MIBs may be
-- created (especially in the area of IPX routing protocols) to contain
-- more specific information.  Whenever possible, these additional MIBs
-- should follow the format of this IPX MIB.  Information in these MIBs
-- should be linked to this MIB via the use of the system instance
-- identifier mentioned above.
--
-- System Group
--   This group contains global information about each instance of IPX
--   running on one system.
ipxSystem     OBJECT IDENTIFIER ::= {rndIPX 4}
-- Basic System Table
--   This table contains one entry for each instance of IPX running on
--   the system.  It contains the management information that should
--   be made available by all implementations of the IPX protocol.

ipxBasicSysTable OBJECT-TYPE
   SYNTAX  SEQUENCE OF IpxBasicSysEntry
   ACCESS  not-accessible
   STATUS  mandatory
   DESCRIPTION "The IPX System table - basic information."
   ::= {ipxSystem 1}

ipxBasicSysEntry OBJECT-TYPE
   SYNTAX  IpxBasicSysEntry
   ACCESS  not-accessible
   STATUS  mandatory
   DESCRIPTION "Each entry corresponds to one instance of IPX running
                on the system."
   INDEX   {ipxBasicSysInstance}
   ::= {ipxBasicSysTable 1}

IpxBasicSysEntry ::= SEQUENCE {
   ipxBasicSysInstance             INTEGER,
   ipxBasicSysExistState           INTEGER,
   ipxBasicSysInReceives           Counter,
   ipxBasicSysInHdrErrors          Counter,
   ipxBasicSysInUnknownSockets     Counter,
   ipxBasicSysInDiscards           Counter,
   ipxBasicSysInDelivers           Counter,
   ipxBasicSysNoRoutes             Counter,
   ipxBasicSysOutRequests          Counter,
   ipxBasicSysOutMalformedRequests Counter,
   ipxBasicSysOutDiscards          Counter,
   ipxBasicSysOutPackets           Counter
   }

ipxBasicSysInstance OBJECT-TYPE
   SYNTAX  INTEGER
   ACCESS  read-write
   STATUS  mandatory
   DESCRIPTION "The unique identifier of the instance of IPX to which this
                row corresponds.  This value may be written only when
                creating a new entry in the table."
   ::= {ipxBasicSysEntry 1}

ipxBasicSysExistState OBJECT-TYPE
   SYNTAX  INTEGER {
      off(1),
      on(2)
      }
   ACCESS  read-write
   STATUS  mandatory
   DESCRIPTION "The validity of this entry in the IPX system table.
                Setting this field to off indicates that this entry may be
                deleted from the system table at the IPX implementation's
                discretion."
   ::= {ipxBasicSysEntry 2}

ipxBasicSysInReceives OBJECT-TYPE
   SYNTAX  Counter
   ACCESS  read-only
   STATUS  mandatory
   DESCRIPTION "The total number of IPX packets received, including
                those received in error."
   ::= {ipxBasicSysEntry 3}

ipxBasicSysInHdrErrors OBJECT-TYPE
   SYNTAX  Counter
   ACCESS  read-only
   STATUS  mandatory
   DESCRIPTION "The number of IPX packets discarded due to errors in
                their headers, including any IPX packet with a size less
                than the minimum of 30 bytes."
   ::= {ipxBasicSysEntry 4}

ipxBasicSysInUnknownSockets OBJECT-TYPE
   SYNTAX  Counter
   ACCESS  read-only
   STATUS  mandatory
   DESCRIPTION "The number of IPX packets discarded because the
                destination socket was not open."
   ::= {ipxBasicSysEntry 5}

ipxBasicSysInDiscards OBJECT-TYPE
   SYNTAX  Counter
   ACCESS  read-only
   STATUS  mandatory
   DESCRIPTION "The number of IPX packets received but discarded due to
                reasons other than those accounted for by
                ipxBasicSysInHdrErrors, ipxBasicSysInUnknownSockets,
                ipxAdvSysInDiscards, and ipxAdvSysInCompressDiscards."
   ::= {ipxBasicSysEntry 6}

ipxBasicSysInDelivers OBJECT-TYPE
   SYNTAX  Counter
   ACCESS  read-only
   STATUS  mandatory
   DESCRIPTION "The total number of IPX packets delivered locally,
                including packets from local applications."
   ::= {ipxBasicSysEntry 7}

ipxBasicSysNoRoutes OBJECT-TYPE
   SYNTAX  Counter
   ACCESS  read-only
   STATUS  mandatory
   DESCRIPTION "The number of times no route to a destination was
                found."
   ::= {ipxBasicSysEntry 8}

ipxBasicSysOutRequests OBJECT-TYPE
   SYNTAX  Counter
   ACCESS  read-only
   STATUS  mandatory
   DESCRIPTION "The number of IPX packets supplied locally for
                transmission, not including any packets counted in
                ipxAdvForwPackets."
   ::= {ipxBasicSysEntry 9}

ipxBasicSysOutMalformedRequests OBJECT-TYPE
   SYNTAX  Counter
   ACCESS  read-only
   STATUS  mandatory
   DESCRIPTION "The number of IPX packets supplied locally that contained
                errors in their structure."
   ::= {ipxBasicSysEntry 10}

ipxBasicSysOutDiscards OBJECT-TYPE
   SYNTAX  Counter
   ACCESS  read-only
   STATUS  mandatory
   DESCRIPTION "The number of outgoing IPX packets discarded due to
                reasons other than those accounted for in
                ipxBasicSysOutMalformedRequests, ipxAdvSysOutFiltered,
                and ipxAdvSysOutCompressDiscards."
   ::= {ipxBasicSysEntry 11}

ipxBasicSysOutPackets OBJECT-TYPE
   SYNTAX  Counter
   ACCESS  read-only
   STATUS  mandatory
   DESCRIPTION "The total number of IPX packets transmitted."
   ::= {ipxBasicSysEntry 12}


-- Circuit Group
--   This group contains management information for each circuit known
--   to this system.

ipxCircuit    OBJECT IDENTIFIER ::= {rndIPX 5}

-- Circuit Table
--   The Circuit table contains an entry for each circuit known to the
--   system.

ipxCircTable OBJECT-TYPE
   SYNTAX  SEQUENCE OF IpxCircEntry
   ACCESS  not-accessible
   STATUS  mandatory
   DESCRIPTION "The Circuit table."
   ::= {ipxCircuit 1}

ipxCircEntry OBJECT-TYPE
   SYNTAX  IpxCircEntry
   ACCESS  not-accessible
   STATUS  mandatory
   DESCRIPTION "Each entry corresponds to one circuit known to the
                system."
   INDEX   {ipxCircSysInstance,
            ipxCircIndex }
   ::= {ipxCircTable 1}

IpxCircEntry ::= SEQUENCE {
   ipxCircSysInstance    INTEGER,
   ipxCircIndex          INTEGER,
   ipxCircExistState     INTEGER,
   ipxCircOperState      INTEGER,
   ipxCircIfIndex        INTEGER,
   ipxCircNetNumber      NetNumber,
   ipxCircTimeToNet      INTEGER,
   ipxCircEncaps         INTEGER,
   ipxCircNetbiosDeliver INTEGER
   }

ipxCircSysInstance OBJECT-TYPE
   SYNTAX  INTEGER
   ACCESS  read-write
   STATUS  mandatory
   DESCRIPTION "The unique identifier of the instance of IPX
                to which this entry corresponds.  This value may be
                written only when creating a new entry in the table."
   ::= {ipxCircEntry 1}

ipxCircIndex OBJECT-TYPE
   SYNTAX  INTEGER
   ACCESS  read-write
   STATUS  mandatory
   DESCRIPTION "The identifier of this circuit, unique within the
                instance of IPX.  This value may be written
                only when creating a new entry in the table."
   ::= {ipxCircEntry 2}

ipxCircExistState OBJECT-TYPE
   SYNTAX  INTEGER {
      off(1),
      on(2),
      sleeping(3)
      }
   ACCESS  read-write
   STATUS  mandatory
   DESCRIPTION "The validity of this circuit entry.  A circuit with this
                value set to off may be deleted from the table at the
                IPX implementation's discretion."
   ::= {ipxCircEntry 3}

ipxCircOperState OBJECT-TYPE
   SYNTAX  INTEGER {
      down(1),
      up(2),
      dormant(3)
      }
   ACCESS  read-only
   STATUS  mandatory
   DESCRIPTION "The operational state of the circuit."
   ::= {ipxCircEntry 4}

ipxCircIfIndex OBJECT-TYPE
   SYNTAX  INTEGER
   ACCESS  read-write
   STATUS  mandatory
   DESCRIPTION "The value of ifIndex for the interface used by this
                circuit.  This value may be written only when creating
                a new entry in the table."
   ::= {ipxCircEntry 5}

ipxCircNetNumber OBJECT-TYPE
   SYNTAX  NetNumber
   ACCESS  read-write
   STATUS  mandatory
   DESCRIPTION "The IPX network number of this circuit.  This value may
                be written only when creating a new entry in the table."
   ::= {ipxCircEntry 6}

ipxCircTimeToNet OBJECT-TYPE
    SYNTAX  INTEGER  (1..65535)
    ACCESS  read-write
    STATUS  mandatory
    DESCRIPTION
           "The time to net value associated with this interface, in
    term of 1/18ths of a second."
    ::= {ipxCircEntry 7}

ipxCircEncaps OBJECT-TYPE
    SYNTAX  INTEGER  {
       novell(1),
       ethernet(2),
       llc(3),
       snap(4),
       none(10)
       }
    ACCESS  read-write
    STATUS  mandatory
    DESCRIPTION
            " The encapsulation method associated with this interface."
    ::= {ipxCircEntry 8}

ipxCircNetbiosDeliver OBJECT-TYPE
    SYNTAX  INTEGER {
        enabled(1),
        disabled(2)
    }
    ACCESS  read-write
    STATUS  mandatory
    DESCRIPTION
        " Deliver NetBios All Networks Broadcast Packets "
    DEFVAL  { enabled }
    ::= {ipxCircEntry 9}

-- Forwarding Group
--   This group provides a representation of the forwarding database used
--   by all instances of IPX on the system.

ipxForwarding OBJECT IDENTIFIER ::= {rndIPX 6}

-- Destination Table
--   The Destination table contains information about all known
--   destinations.  The routing information shown in this table represents
--   the path currently being used to reach the destination.

ipxDestTable OBJECT-TYPE
   SYNTAX  SEQUENCE OF IpxDestEntry
   ACCESS  not-accessible
   STATUS  mandatory
   DESCRIPTION "The Destination table contains information about all
                known destinations."
   ::= {ipxForwarding 1}

ipxDestEntry OBJECT-TYPE
   SYNTAX  IpxDestEntry
   ACCESS  not-accessible
   STATUS  mandatory
   DESCRIPTION "Each entry corresponds to one destination."
   INDEX { ipxDestSysInstance,
           ipxDestNetNum,
           ipxDestNextHopCircIndex}
   ::= {ipxDestTable 1}

IpxDestEntry ::= SEQUENCE {
   ipxDestSysInstance        INTEGER,
   ipxDestNetNum             NetNumber,
   ipxDestNextHopCircIndex   INTEGER,
   ipxDestProtocol           INTEGER,
   ipxDestTicks              INTEGER,
   ipxDestHopCount           INTEGER,
   ipxDestNextHopNICAddress  PhysAddress,
   ipxDestNextHopNetNum      NetNumber,
   ipxDestExistState         INTEGER
   }

ipxDestSysInstance OBJECT-TYPE
   SYNTAX  INTEGER
   ACCESS  read-only
   STATUS  mandatory
   DESCRIPTION "The unique identifier of the instance of IPX
                to which this row corresponds."
   ::= {ipxDestEntry 1}

ipxDestNetNum OBJECT-TYPE
   SYNTAX  NetNumber
   ACCESS  read-only
   STATUS  mandatory
   DESCRIPTION "The IPX network number of the destination."
   ::= {ipxDestEntry 2}

ipxDestNextHopCircIndex OBJECT-TYPE
   SYNTAX  INTEGER
   ACCESS  read-write
   STATUS  mandatory
   DESCRIPTION "The unique identifier of the circuit used to reach the
                next hop."
   ::= {ipxDestEntry 3}

ipxDestProtocol OBJECT-TYPE
   SYNTAX  INTEGER {
      other(1),
      local(2),
      rip(3),
      nlsp(4),
      static(5)
      }
   ACCESS  read-only
   STATUS  mandatory
   DESCRIPTION "The routing protocol from which knowledge of this
                destination was obtained."
   ::= {ipxDestEntry 4}

ipxDestTicks OBJECT-TYPE
   SYNTAX  INTEGER
   ACCESS  read-write
   STATUS  mandatory
   DESCRIPTION "The delay in ticks to reach this destination."
   ::= {ipxDestEntry 5}

ipxDestHopCount OBJECT-TYPE
   SYNTAX  INTEGER
   ACCESS  read-write
   STATUS  mandatory
   DESCRIPTION "The number of hops necessary to reach the destination."
   ::= {ipxDestEntry 6}

ipxDestNextHopNICAddress OBJECT-TYPE
   SYNTAX  PhysAddress
   ACCESS  read-write
   STATUS  mandatory
   DESCRIPTION "The NIC address of the next hop."
   ::= {ipxDestEntry 7}

ipxDestNextHopNetNum OBJECT-TYPE
   SYNTAX  NetNumber
   ACCESS  read-write
   STATUS  mandatory
   DESCRIPTION "The IPX network number of the next hop."
   ::= {ipxDestEntry 8}

ipxDestExistState OBJECT-TYPE
   SYNTAX  INTEGER {
      off(1),
      on(2)
      }
   ACCESS  read-write
   STATUS  mandatory
   DESCRIPTION "The validity of this entry.  An entry with this
                value set to off may be deleted from the table at the
                IPX implementation's discretion."
   ::= {ipxDestEntry 9}

-- Services Group
--   The Services group contains management information for all known
--   services.

ipxServices   OBJECT IDENTIFIER ::= {rndIPX 7}

-- Services Table
--    This table contains the services information indexed by service
--    name and type.

ipxServTable OBJECT-TYPE
   SYNTAX  SEQUENCE OF IpxServEntry
   ACCESS  not-accessible
   STATUS  mandatory
   DESCRIPTION "The table of services, indexed by name and type."
   ::= {ipxServices 1}

ipxServEntry OBJECT-TYPE
   SYNTAX  IpxServEntry
   ACCESS  not-accessible
   STATUS  mandatory
   DESCRIPTION "Each entry corresponds to one service."
   INDEX  {
      ipxServSysInstance,
      ipxServType,
      IMPLIED ipxServName
      }
   ::= {ipxServTable 1}

IpxServEntry ::= SEQUENCE {
   ipxServSysInstance   INTEGER,
   ipxServType          OCTET STRING,
   ipxServName          OCTET STRING,
   ipxServProtocol      INTEGER,
   ipxServNetNum        NetNumber,
   ipxServNode          OCTET STRING,
   ipxServSocket        OCTET STRING,
   ipxServHopCount      INTEGER,
   ipxServExistState    INTEGER
   }

ipxServSysInstance OBJECT-TYPE
   SYNTAX  INTEGER
   ACCESS  read-only
   STATUS  mandatory
   DESCRIPTION "The unique identifier of the instance of IPX
                to which this entry corresponds."
   ::= {ipxServEntry 1}

ipxServType OBJECT-TYPE
   SYNTAX  OCTET STRING (SIZE(2))
   ACCESS  read-write
   STATUS  mandatory
   DESCRIPTION "The service type."
   ::= {ipxServEntry 2}

ipxServName OBJECT-TYPE
   SYNTAX  OCTET STRING (SIZE(1..48))
   ACCESS  read-write
   STATUS  mandatory
   DESCRIPTION "The service name."
   ::= {ipxServEntry 3}

ipxServProtocol OBJECT-TYPE
   SYNTAX  INTEGER {
      other(1),
      local(2),
      nlsp(4),
      static(5),
      sap(6)
      }
   ACCESS  read-only
   STATUS  mandatory
   DESCRIPTION "The protocol from which knowledge of this service was
                obtained."
   ::= {ipxServEntry 4}

ipxServNetNum OBJECT-TYPE
   SYNTAX  NetNumber
   ACCESS  read-write
   STATUS  mandatory
   DESCRIPTION "The IPX network number portion of the IPX address of the
                service."
   ::= {ipxServEntry 5}

ipxServNode OBJECT-TYPE
   SYNTAX  OCTET STRING (SIZE(6))
   ACCESS  read-write
   STATUS  mandatory
   DESCRIPTION "The node portion of the IPX address of the service."
   ::= {ipxServEntry 6}

ipxServSocket OBJECT-TYPE
   SYNTAX  OCTET STRING (SIZE(2))
   ACCESS  read-write
   STATUS  mandatory
   DESCRIPTION "The socket portion of the IPX address of the service."
   ::= {ipxServEntry 7}

ipxServHopCount OBJECT-TYPE
   SYNTAX  INTEGER
   ACCESS  read-write
   STATUS  mandatory
   DESCRIPTION "The number of hops to the service."
   ::= {ipxServEntry 8}

ipxServExistState OBJECT-TYPE
   SYNTAX  INTEGER {
      off(1),
      on(2)
      }
   ACCESS  read-write
   STATUS  mandatory
   DESCRIPTION "The validity of this entry.  An entry with this
                value set to off may be deleted from the table at the
                IPX implementation's discretion."
   ::= {ipxServEntry 9}


-- This sub-tree defines the management information for the RIP and SAP
-- protocols running in an IPX enviroment.  It provides information in
-- addition to that contained in the IPX MIB itself.  All tables in this
-- MIB are linked to an instance of IPX via the system instance
-- identifier as defined in the IPX MIB.

ripsap        OBJECT IDENTIFIER ::= {rndIPX 8}

-- System Group
--   This group contains global information about each instance of
--   RIP/SAP running on one system.

ripsapSystem  OBJECT IDENTIFIER ::= {ripsap 1}

-- RIP System Table
--   This table contains an entry for each instance of RIP
--   running on the system.

ripSysTable OBJECT-TYPE
   SYNTAX  SEQUENCE OF RipSysEntry
   ACCESS  not-accessible
   STATUS  mandatory
   DESCRIPTION "The RIP system table."
   ::= {ripsapSystem 1}

ripSysEntry OBJECT-TYPE
   SYNTAX  RipSysEntry
   ACCESS  not-accessible
   STATUS  mandatory
   DESCRIPTION "Each entry corresponds to one instance of RIP
                running on the system."
   INDEX   {ripSysInstance}
   ::= {ripSysTable 1}

RipSysEntry ::= SEQUENCE {
   ripSysInstance         INTEGER,
   ripSysState            INTEGER,
   ripSysIncorrectPackets Counter
   }

ripSysInstance OBJECT-TYPE
   SYNTAX  INTEGER
   ACCESS  read-write
   STATUS  mandatory
   DESCRIPTION "The unique identifier of the instance of RIP to
                which this row corresponds.  This value links the
                instance of RIP to an instance of IPX running on the
                system  (i.e. the value of ripSysInstance should be the
                same as a value of ipxSysInstance).  This value may be
                written only when creating a new entry in the table."
   ::= {ripSysEntry 1}

ripSysState OBJECT-TYPE
   SYNTAX  INTEGER {
      off(1),
      on(2)
      }
   ACCESS  read-write
   STATUS  mandatory
   DESCRIPTION "Indicates the operational state of this instance of RIP."
   ::= {ripSysEntry 2}

ripSysIncorrectPackets OBJECT-TYPE
   SYNTAX  Counter
   ACCESS  read-only
   STATUS  mandatory
   DESCRIPTION "The number of times that an incorrectly formatted RIP
                packet was received."
   ::= {ripSysEntry 3}


-- SAP System Table
--   This table contains an entry for each instance of SAP
--   running on the system.

sapSysTable OBJECT-TYPE
   SYNTAX  SEQUENCE OF SapSysEntry
   ACCESS  not-accessible
   STATUS  mandatory
   DESCRIPTION "The SAP system table."
   ::= {ripsapSystem 2}

sapSysEntry OBJECT-TYPE
   SYNTAX  SapSysEntry
   ACCESS  not-accessible
   STATUS  mandatory
   DESCRIPTION "Each entry corresponds to one instance of SAP
                running on the system."
   INDEX   {sapSysInstance}
   ::= {sapSysTable 1}

SapSysEntry ::= SEQUENCE {
   sapSysInstance          INTEGER,
   sapSysState             INTEGER,
   sapSysIncorrectPackets  Counter
   }

sapSysInstance OBJECT-TYPE
   SYNTAX  INTEGER
   ACCESS  read-write
   STATUS  mandatory
   DESCRIPTION "The unique identifier of the instance of SAP to
                which this row corresponds.  This value links the
                instance of SAP to an instance of IPX running on the
                system  (i.e. the value of SApSysInstance should be the
                same as a value of ipxSysInstance).  This value may be
                written only when creating a new entry in the table."
   ::= {sapSysEntry 1}

sapSysState OBJECT-TYPE
   SYNTAX  INTEGER {
      off(1),
      on(2)
      }
   ACCESS  read-only
   STATUS  mandatory
   DESCRIPTION "Indicates the operational state of this instance of SAP."
   ::= {sapSysEntry 2}

sapSysIncorrectPackets OBJECT-TYPE
   SYNTAX  Counter
   ACCESS  read-only
   STATUS  mandatory
   DESCRIPTION "The number of times that an incorrectly formatted SAP
                packet was received."
   ::= {sapSysEntry 3}


-- Circuit Group
--   This group contains RIP and SAP management information for each
--   circuit known to this system.

ripsapCircuit OBJECT IDENTIFIER ::= {ripsap 2}

-- RIP Circuit Table
--   The RIP Circuit table contains an entry for the RIP information for
--   each circuit known to the system.

ripCircTable OBJECT-TYPE
   SYNTAX  SEQUENCE OF RipCircEntry
   ACCESS  not-accessible
   STATUS  mandatory
   DESCRIPTION "The RIP Circuit table."
   ::= {ripsapCircuit 1}

ripCircEntry OBJECT-TYPE
   SYNTAX  RipCircEntry
   ACCESS  not-accessible
   STATUS  mandatory
   DESCRIPTION "Each entry corresponds to one circuit known to the
                system."
   INDEX   {ripCircSysInstance,
            ripCircIndex
            }
   ::= {ripCircTable 1}

RipCircEntry ::= SEQUENCE {
   ripCircSysInstance    INTEGER,
   ripCircIndex          INTEGER,
   ripCircState          INTEGER,
   ripCircUpdate         INTEGER,
   ripCircAgeMultiplier  INTEGER,
   ripCircOutPackets     Counter,
   ripCircInPackets      Counter
   }

ripCircSysInstance OBJECT-TYPE
   SYNTAX  INTEGER
   ACCESS  read-write
   STATUS  mandatory
   DESCRIPTION "The unique identifier of the instance of RIP and IPX
                (via ipxSysInstance) to which this entry corresponds.
                This value may be written only when creating a new entry in
                the table."
   ::= {ripCircEntry 1}

ripCircIndex OBJECT-TYPE
   SYNTAX  INTEGER
   ACCESS  read-write
   STATUS  mandatory
   DESCRIPTION "The identifier of this circuit, unique within the
                instance of RIP.  This value corresponds to the circuit
                identifier found in ipxCircIndex.   This value may be
                written only when creating a new entry in the table."
   ::= {ripCircEntry 2}

ripCircState OBJECT-TYPE
   SYNTAX  INTEGER {
      off(1),
      on(2)
      }
   ACCESS  read-write
   STATUS  mandatory
   DESCRIPTION "Indicates whether RIP information may be sent/received
                over this circuit."
   DEFVAL  { on }
   ::= {ripCircEntry 3}

ripCircUpdate OBJECT-TYPE
   SYNTAX  INTEGER
   ACCESS  read-write
   STATUS  mandatory
   DESCRIPTION "The RIP periodic update interval, in seconds."
   DEFVAL  { 60 }
   ::= {ripCircEntry 4}

ripCircAgeMultiplier OBJECT-TYPE
   SYNTAX  INTEGER
   ACCESS  read-write
   STATUS  mandatory
   DESCRIPTION "The holding multiplier for information received in RIP
                periodic updates."
   DEFVAL  { 4 }
   ::= {ripCircEntry 5}

ripCircOutPackets OBJECT-TYPE
   SYNTAX  Counter
   ACCESS  read-only
   STATUS  mandatory
   DESCRIPTION "The number of RIP packets sent on this circuit."
   ::= {ripCircEntry 6}

ripCircInPackets OBJECT-TYPE
   SYNTAX  Counter
   ACCESS  read-only
   STATUS  mandatory
   DESCRIPTION "The number of RIP packets received on this circuit."
   ::= {ripCircEntry 7}


-- SAP Circuit Table
--   The SAP Circuit table contains an entry for the SAP information for
--   each circuit known to the system.

sapCircTable OBJECT-TYPE
   SYNTAX  SEQUENCE OF SapCircEntry
   ACCESS  not-accessible
   STATUS  mandatory
   DESCRIPTION "The SAP Circuit table."
   ::= {ripsapCircuit 2}

sapCircEntry OBJECT-TYPE
   SYNTAX  SapCircEntry
   ACCESS  not-accessible
   STATUS  mandatory
   DESCRIPTION "Each entry corresponds to one circuit known to the
                system."
   INDEX   {sapCircSysInstance,
            sapCircIndex }
   ::= {sapCircTable 1}

SapCircEntry ::= SEQUENCE {
   sapCircSysInstance           INTEGER,
   sapCircIndex                 INTEGER,
   sapCircState                 INTEGER,
   sapCircUpdate                INTEGER,
   sapCircAgeMultiplier         INTEGER,
   sapCircGetNearestServerReply INTEGER,
   sapCircOutPackets            Counter,
   sapCircInPackets             Counter
   }

sapCircSysInstance OBJECT-TYPE
   SYNTAX  INTEGER
   ACCESS  read-write
   STATUS  mandatory
   DESCRIPTION "The unique identifier of the instance of SAP and IPX
                (via ipxSysInstance) to which this entry corresponds.
                This value may be written only when creating a new entry in
                the table."
   ::= {sapCircEntry 1}

sapCircIndex OBJECT-TYPE
   SYNTAX  INTEGER
   ACCESS  read-write
   STATUS  mandatory
   DESCRIPTION "The identifier of this circuit, unique within the
                instance of SAP.  This value corresponds to the circuit
                identifier found in ipxCircIndex.   This value may be
                written only when creating a new entry in the table."
   ::= {sapCircEntry 2}

sapCircState OBJECT-TYPE
   SYNTAX  INTEGER {
      off(1),
      on(2)
      }
   ACCESS  read-write
   STATUS  mandatory
   DESCRIPTION "Indicates whether SAP information may be sent/received
                over this circuit."
   DEFVAL      { off }
   ::= {sapCircEntry 3}

sapCircUpdate OBJECT-TYPE
   SYNTAX  INTEGER
   ACCESS  read-write
   STATUS  mandatory
   DESCRIPTION "The SAP periodic update interval, in seconds."
   DEFVAL  { 60 }
   ::= {sapCircEntry 4}

sapCircAgeMultiplier OBJECT-TYPE
   SYNTAX  INTEGER
   ACCESS  read-write
   STATUS  mandatory
   DESCRIPTION "The holding multiplier for information received in SAP
                periodic updates."
   DEFVAL  { 4 }
   ::= {sapCircEntry 5}

sapCircGetNearestServerReply OBJECT-TYPE
   SYNTAX  INTEGER {
      no(1),
      yes(2)
      }
   ACCESS  read-write
   STATUS  mandatory
   DESCRIPTION "Indicates whether to respond to SAP get nearest server
                requests received on this circuit."
   DEFVAL  { yes }
   ::= {sapCircEntry 6}

sapCircOutPackets OBJECT-TYPE
   SYNTAX  Counter
   ACCESS  read-only
   STATUS  mandatory
   DESCRIPTION "The number of SAP packets sent on this circuit."
   ::= {sapCircEntry 7}

sapCircInPackets OBJECT-TYPE
   SYNTAX  Counter
   ACCESS  read-only
   STATUS  mandatory
   DESCRIPTION "The number of SAP packets received on this circuit."
   ::= {sapCircEntry 8}

END
