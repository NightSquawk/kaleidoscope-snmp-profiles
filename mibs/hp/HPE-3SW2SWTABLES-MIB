HPE-3SW2SWTABLES-MIB DEFINITIONS ::= BEGIN

-- Title:                HPE ROS
--                       Private 3SW 2SW TABLES MIB
-- Version:              7.46
-- Date:                 15-Jan-2007

IMPORTS
    nm                                                     FROM HPE-MIB
    OBJECT-TYPE, MODULE-IDENTITY                            FROM SNMPv2-SMI;

rl3sw2swTables MODULE-IDENTITY
                LAST-UPDATED "200701020000Z"
                ORGANIZATION "HPE"
                CONTACT-INFO
				"HPE"
                DESCRIPTION
                      "This private MIB module defines 3sw 2sw Tables private MIBs."
                REVISION "200701020000Z"
                DESCRIPTION
                      "Initial revision."
        ::= { nm 63 }

rl3sw2swTablesPollingInterval OBJECT-TYPE
    SYNTAX  INTEGER
    MAX-ACCESS  read-write
    STATUS  current
    DESCRIPTION
        "The polling interval for dynamic 3SW/2SW tables in seconds."
    DEFVAL { 3 }
    ::= { rl3sw2swTables 1 }

END
