-- *****************************************************************
-- MY-AUTH-GATEWAY-MIB.mib:  My Auth-Gateway MIB file
--
-- $Copyright$
-- 
-- *****************************************************************
--

DES7200-AUTH-GATEWAY-MIB DEFINITIONS ::= BEGIN

IMPORTS
        MODULE-IDENTITY,
        OBJECT-TYPE,
        NOTIFICATION-TYPE,
        Gauge32,
        Counter32
                FROM SNMPv2-SMI
        TruthValue,
        DisplayString,
        RowStatus,
        PhysAddress
                FROM SNMPv2-TC
        MODULE-COMPLIANCE,
        OBJECT-GROUP,
        NOTIFICATION-GROUP
                FROM SNMPv2-CONF
        IfIndex
                FROM DES7200-TC        
        ip
                FROM RFC1213-MIB
        myMgmt
                FROM DES7200-SMI;

myAuthGatewayMIB MODULE-IDENTITY
        LAST-UPDATED "200203200000Z"
        ORGANIZATION "$Company$"
        CONTACT-INFO
                " 
                Tel: $Telephone$ 

                E-mail: $E-mail$"
        DESCRIPTION
                "This module defines my authGateway mibs."
        REVISION      "200203200000Z"
        DESCRIPTION
                "Initial version of this MIB module."
        ::= { myMgmt 40}

myAuthGatewayMIBObjects OBJECT IDENTIFIER ::= { myAuthGatewayMIB 1 }


 -- IP Address Translation table

 -- The IP address translation table contain the IpAddress to
 -- `physical' address equivalences for ARP(Address Resolution Protocol). 
   
 myAuthGatewayUserTable OBJECT-TYPE
     SYNTAX  SEQUENCE OF MyAuthGatewayUserEntry
     ACCESS  not-accessible
     STATUS  current
     DESCRIPTION
             "认证用户表,存放已通过认证的用户.用户下线时用户记录暂时不删除,
             但如果记录满了无法加入新记录时,会强制更新已下线的用户记录."
     ::= { myAuthGatewayMIBObjects 1 }

 myAuthGatewayUserEntry OBJECT-TYPE
     SYNTAX  MyAuthGatewayUserEntry
     ACCESS  not-accessible
     STATUS  current
     DESCRIPTION
             "认证用户表入口."
     INDEX   { userIpaddr }
     ::= { myAuthGatewayUserTable 1 }

 MyAuthGatewayUserEntry ::=
     SEQUENCE {
         userIpaddr
             IpAddress,
         onlineFlag
             Gauge32,    
         timeLimit
             Gauge32,    
         timeUsed
             Gauge32,    
         bandwidthLimitUplink
             Gauge32,    
         bandwidthLimitDownlink
             Gauge32,    
         intramuralFluxLimitUplink
             Gauge32,    
         intramuralFluxLimitDownlink
             Gauge32,    
         inlandFluxLimitUplink
             Gauge32,    
         inlandFluxLimitDownlink
             Gauge32,    
         overseasFluxLimitUplink
             Gauge32,    
         overseasFluxLimitDownlink
             Gauge32,    
         intramuralFluxCountUplink
             Counter32,    
         intramuralFluxCountDownlink
             Counter32,    
         inlandFluxCountUplink
             Counter32,    
         inlandFluxCountDownlink
             Counter32,    
         overseasFluxCountUplink
             Counter32,    
         overseasFluxCountDownlink
             Counter32,    
         userStatus   
             RowStatus 
     }

 userIpaddr OBJECT-TYPE
     SYNTAX  IpAddress
     ACCESS  read-only
     STATUS  current
     DESCRIPTION
             "认证用户IP地址."
     ::= { myAuthGatewayUserEntry 1 }

 onlineFlag OBJECT-TYPE
     SYNTAX  Gauge32
     ACCESS  read-only
     STATUS  current
     DESCRIPTION
             "上线标志,用户创建时就为已上线(1),用户超流量或超时长时被置位,表示已下线(0)."
     ::= { myAuthGatewayUserEntry 2 }


 timeLimit OBJECT-TYPE
     SYNTAX  Gauge32
     ACCESS  read-write
     STATUS  current
     DESCRIPTION
             "时长限制,单位秒,0表示无限制."
     ::= { myAuthGatewayUserEntry 3 }

 timeUsed OBJECT-TYPE
     SYNTAX  Gauge32
     ACCESS  read-only
     STATUS  current
     DESCRIPTION
             "已用时长,单位秒,用户已用时长,用户状态设置Active时开始计算,用户下线时停止计算."
     ::= { myAuthGatewayUserEntry 4 }

 bandwidthLimitUplink OBJECT-TYPE
     SYNTAX  Gauge32
     ACCESS  read-write
     STATUS  current
     DESCRIPTION
             "上行带宽限制,单位kbps,范围64k~1G,0表示无限制."
     ::= { myAuthGatewayUserEntry 5 }

 bandwidthLimitDownlink OBJECT-TYPE
     SYNTAX  Gauge32
     ACCESS  read-write
     STATUS  current
     DESCRIPTION
             "下行带宽限制,单位kbps,范围64k~1G,0表示无限制."
     ::= { myAuthGatewayUserEntry 6 }

 intramuralFluxLimitUplink OBJECT-TYPE
     SYNTAX  Gauge32
     ACCESS  read-write
     STATUS  current
     DESCRIPTION
             "校内可用上行流量限制,单位k,达到上限时强制下线,0表示无限制."
     ::= { myAuthGatewayUserEntry 7 }

 intramuralFluxLimitDownlink OBJECT-TYPE
     SYNTAX  Gauge32
     ACCESS  read-write
     STATUS  current
     DESCRIPTION
             "校内可用下行流量限制,单位k,达到上限时强制下线,0表示无限制."
     ::= { myAuthGatewayUserEntry 8 }

 inlandFluxLimitUplink OBJECT-TYPE
     SYNTAX  Gauge32
     ACCESS  read-write
     STATUS  current
     DESCRIPTION
             "国内可用上行流量限制,单位k,达到上限时强制下线,0表示无限制."
     ::= { myAuthGatewayUserEntry 9 }

 inlandFluxLimitDownlink OBJECT-TYPE
     SYNTAX  Gauge32
     ACCESS  read-write
     STATUS  current
     DESCRIPTION
             "国内可用下行流量限制,单位k,达到上限时强制下线,0表示无限制."
     ::= { myAuthGatewayUserEntry 10 }

 overseasFluxLimitUplink OBJECT-TYPE
     SYNTAX  Gauge32
     ACCESS  read-write
     STATUS  current
     DESCRIPTION
             "国外可用上行流量限制,单位k,达到上限时强制下线,0表示无限制."
     ::= { myAuthGatewayUserEntry 11 }

 overseasFluxLimitDownlink OBJECT-TYPE
     SYNTAX  Gauge32
     ACCESS  read-write
     STATUS  current
     DESCRIPTION
             "国外可用下行流量限制,单位k,达到上限时强制下线,0表示无限制."
     ::= { myAuthGatewayUserEntry 12 }
    
 intramuralFluxCountUplink OBJECT-TYPE
     SYNTAX  Counter32
     ACCESS  read-only
     STATUS  current
     DESCRIPTION
             "校内可用上行流量统计,单位k."
     ::= { myAuthGatewayUserEntry 13 }

 intramuralFluxCountDownlink OBJECT-TYPE
     SYNTAX  Counter32
     ACCESS  read-only
     STATUS  current
     DESCRIPTION
             "校内可用下行流量统计,单位k."
     ::= { myAuthGatewayUserEntry 14 }

 inlandFluxCountUplink OBJECT-TYPE
     SYNTAX  Counter32
     ACCESS  read-only
     STATUS  current
     DESCRIPTION
             "国内可用上行流量统计,单位k."
     ::= { myAuthGatewayUserEntry 15 }

 inlandFluxCountDownlink OBJECT-TYPE
     SYNTAX  Counter32
     ACCESS  read-only
     STATUS  current
     DESCRIPTION
             "国内可用下行流量统计,单位k."
     ::= { myAuthGatewayUserEntry 16 }

 overseasFluxCountUplink OBJECT-TYPE
     SYNTAX  Counter32
     ACCESS  read-only
     STATUS  current
     DESCRIPTION
             "国外可用上行流量统计,单位k."
     ::= { myAuthGatewayUserEntry 17 }

 overseasFluxCountDownlink OBJECT-TYPE
     SYNTAX  Counter32
     ACCESS  read-only
     STATUS  current
     DESCRIPTION
             "国外可用下行流量统计,单位k."
     ::= { myAuthGatewayUserEntry 18 }
        
 userStatus OBJECT-TYPE
        SYNTAX RowStatus
        MAX-ACCESS read-create
        STATUS current
        DESCRIPTION
            "用户状态,1-Active,5-Create and wait,6-Distory."
    ::= { myAuthGatewayUserEntry 19 }        

-- auth-gateway trap
                
myAuthGatewayMIBTraps OBJECT IDENTIFIER ::= { myAuthGatewayMIB 2 }      
        
myAuthGatewayUserLeave NOTIFICATION-TYPE
        OBJECTS   { userIpaddr }
        STATUS     current
        DESCRIPTION
                "用户下线发送的Trap."
        ::= { myAuthGatewayMIBTraps 1 }                    


-- compliance statements
         
myAuthGatewayMIBConformance OBJECT IDENTIFIER ::= { myAuthGatewayMIB 3 }
myAuthGatewayMIBCompliances OBJECT IDENTIFIER ::= { myAuthGatewayMIBConformance 1 }
myAuthGatewayMIBGroups      OBJECT IDENTIFIER ::= { myAuthGatewayMIBConformance 2 }

myAuthGatewayMIBCompliance MODULE-COMPLIANCE
        STATUS  current
        DESCRIPTION
                "The compliance statement for entities which implement
                the My AuthGateway MIB"
        MODULE  -- this module
                MANDATORY-GROUPS { myAuthGatewayMIBGroup
                 }
                       
        ::= { myAuthGatewayMIBCompliances 1 }
                
-- units of conformance

myAuthGatewayMIBGroup OBJECT-GROUP
        OBJECTS {
         userIpaddr,
         onlineFlag,
         timeLimit,
         timeUsed,
         bandwidthLimitUplink,
         bandwidthLimitDownlink,
         intramuralFluxLimitUplink,
         intramuralFluxLimitDownlink,
         inlandFluxLimitUplink,
         inlandFluxLimitDownlink,
         overseasFluxLimitUplink,
         overseasFluxLimitDownlink,
         intramuralFluxCountUplink,
         intramuralFluxCountDownlink,
         inlandFluxCountUplink,
         inlandFluxCountDownlink,
         overseasFluxCountUplink,
         overseasFluxCountDownlink,
         userStatus   
        }
        STATUS  current
        DESCRIPTION
                "A collection of objects providing authGateway management and
                opertion to a My agent."
        ::= { myAuthGatewayMIBGroups 1 } 
  
END
