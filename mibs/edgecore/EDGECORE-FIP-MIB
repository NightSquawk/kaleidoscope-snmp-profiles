EDGECORE-FIP-MIB DEFINITIONS ::= BEGIN

-- Title:      MARVELLFIP Configuration
-- Version:    7.50.00.00
-- Date:       29-March-2009
--

IMPORTS
    TruthValue,TEXTUAL-CONVENTION                        FROM SNMPv2-TC
    MODULE-IDENTITY, OBJECT-TYPE                         FROM SNMPv2-SMI
    PortList                                             FROM Q-BRIDGE-MIB
    MacAddress                                           FROM BRIDGE-MIB
    RowStatus                                            FROM SNMPv2-TC
    rnd                                                  FROM EDGECORE-MIB;



rlFip  MODULE-IDENTITY
       LAST-UPDATED "200711070000Z"
       ORGANIZATION "Marvell Semiconductor, Inc."
       CONTACT-INFO
                "www.marvell.com"
       DESCRIPTION
                "The private MIB module definition for FIP MIB."
       REVISION "200711070000Z"
       DESCRIPTION
                "Initial version of this MIB."
           ::= { rnd 150 }



-------------------------------------------------------------------------------



RlFipIfType ::= TEXTUAL-CONVENTION
    STATUS  current
    DESCRIPTION
        "Each port may be in one of the following states:
         Non-Snooping - The port forwards the FCoE and FIP traffic. Snooping is disabled.
         Non-FCoE - Discards all FCoE and FIP traffic received on the port.
         FCoE  - A port that is connected to FC Forwarders and/or Enodes.
         ENODE - A port that is connected to FC Enode."
    SYNTAX  INTEGER {
        non-snooping(1),
        non-fcoe(2),
        fcoe(3),
        enode(4)
}

--- rlFipIfTable table

rlFipIfTable OBJECT-TYPE
    SYNTAX     SEQUENCE OF RlFipIfEntry
    MAX-ACCESS not-accessible
    STATUS     current
    DESCRIPTION
           "This table used to configure Global FCF MAC addresses."
    ::= { rlFip 1 }

rlFipIfEntry OBJECT-TYPE
    SYNTAX     RlFipIfEntry
    MAX-ACCESS not-accessible
    STATUS     current
    DESCRIPTION
           "FIP Interface Table."
    INDEX { rlFipIfIndex }
    ::= { rlFipIfTable 1 }

RlFipIfEntry ::= SEQUENCE {
        rlFipIfIndex                            INTEGER,
        rlFipIfType                             RlFipIfType,
        rlFipIfRowStatus                        RowStatus
    }

rlFipIfIndex     OBJECT-TYPE
    SYNTAX INTEGER
    MAX-ACCESS not-accessible
    STATUS current
    DESCRIPTION
        "Interface index."
    ::= { rlFipIfEntry 1 }


rlFipIfType OBJECT-TYPE
    SYNTAX     RlFipIfType
    MAX-ACCESS read-write
    STATUS     current
    DESCRIPTION
           "Interface type."
    DEFVAL { enode }
    ::= { rlFipIfEntry 2 }

rlFipIfRowStatus OBJECT-TYPE
    SYNTAX      RowStatus
    MAX-ACCESS  read-create
    STATUS      current
    DESCRIPTION
        "The status of the entry. It's used to add/delete the entries"
    ::= { rlFipIfEntry 3 }





--- rlFipGlobalFcfList table

rlFipGlobalFcfListTable OBJECT-TYPE
    SYNTAX     SEQUENCE OF RlFipGlobalFcfListEntry
    MAX-ACCESS not-accessible
    STATUS     current
    DESCRIPTION
           "This table used to configure Global FCF MAC addresses."
    ::= { rlFip 2 }

rlFipGlobalFcfListEntry OBJECT-TYPE
    SYNTAX     RlFipGlobalFcfListEntry
    MAX-ACCESS not-accessible
    STATUS     current
    DESCRIPTION
           "Global FCF MAC address."
    INDEX { rlFipGlobalFcfListMac }
    ::= { rlFipGlobalFcfListTable 1 }

RlFipGlobalFcfListEntry ::= SEQUENCE {
        rlFipGlobalFcfListMac                   MacAddress,
        rlFipGlobalFcfListStatus                RowStatus
    }

rlFipGlobalFcfListMac OBJECT-TYPE
    SYNTAX     MacAddress
    MAX-ACCESS not-accessible
    STATUS     current
    DESCRIPTION
           "Global FCF MAC address."
    ::= { rlFipGlobalFcfListEntry 1 }

rlFipGlobalFcfListStatus OBJECT-TYPE
    SYNTAX      RowStatus
    MAX-ACCESS  read-create
    STATUS      current
    DESCRIPTION
        "The status of the entry. It's used to add/delete the entries"
    ::= { rlFipGlobalFcfListEntry 2 }


--- rlFipStaticFcoeTunnel table

rlFipStaticFcoeTunnelTable OBJECT-TYPE
    SYNTAX     SEQUENCE OF RlFipStaticFcoeTunnelEntry
    MAX-ACCESS not-accessible
    STATUS     current
    DESCRIPTION
           "This table used to configure Fip Static FCOE Tunnels."
    ::= { rlFip 3 }

rlFipStaticFcoeTunnelEntry OBJECT-TYPE
    SYNTAX     RlFipStaticFcoeTunnelEntry
    MAX-ACCESS not-accessible
    STATUS     current
    DESCRIPTION
           "FIP Static FCOE Tunnel."
    INDEX { rlFipStaticFcoeTunnelPort,rlFipStaticFcoeTunnelSrcMac,rlFipStaticFcoeTunnelDstMac}
    ::= { rlFipStaticFcoeTunnelTable 1 }

RlFipStaticFcoeTunnelEntry ::= SEQUENCE {
        rlFipStaticFcoeTunnelPort               INTEGER,
        rlFipStaticFcoeTunnelSrcMac             MacAddress,
        rlFipStaticFcoeTunnelDstMac             MacAddress,
        rlFipStaticFcoeTunnelStatus             RowStatus
    }

rlFipStaticFcoeTunnelPort OBJECT-TYPE
    SYNTAX     INTEGER
    MAX-ACCESS not-accessible
    STATUS     current
    DESCRIPTION
           "FCOE tunnel port."
    ::= { rlFipStaticFcoeTunnelEntry 1 }

rlFipStaticFcoeTunnelSrcMac OBJECT-TYPE
    SYNTAX     MacAddress
    MAX-ACCESS not-accessible
    STATUS     current
    DESCRIPTION
           "FCOE tunnel Source MAC address."
    ::= { rlFipStaticFcoeTunnelEntry 2 }

rlFipStaticFcoeTunnelDstMac OBJECT-TYPE
    SYNTAX     MacAddress
    MAX-ACCESS not-accessible
    STATUS     current
    DESCRIPTION
           "FCOE tunnel Destination MAC address."
    ::= { rlFipStaticFcoeTunnelEntry 3 }

rlFipStaticFcoeTunnelStatus OBJECT-TYPE
    SYNTAX      RowStatus
    MAX-ACCESS  read-create
    STATUS      current
    DESCRIPTION
        "The status of the entry. It's used to add/delete the entries"
    ::= { rlFipStaticFcoeTunnelEntry 4 }




--- rlFipActiveFcoeTunnel table

rlFipActiveFcoeTunnelTable OBJECT-TYPE
    SYNTAX     SEQUENCE OF RlFipActiveFcoeTunnelEntry
    MAX-ACCESS not-accessible
    STATUS     current
    DESCRIPTION
           "This table used to show Fip Active FCOE Tunnels."
    ::= { rlFip 4 }

rlFipActiveFcoeTunnelEntry OBJECT-TYPE
    SYNTAX     RlFipActiveFcoeTunnelEntry
    MAX-ACCESS not-accessible
    STATUS     current
    DESCRIPTION
           "FIP Active FCOE Tunnel."
    INDEX { rlFipActiveFcoeTunnelPort, rlFipActiveFcoeTunnelSrcMac, rlFipActiveFcoeTunnelDstMac, rlFipActiveFcoeTunnelSid }
    ::= { rlFipActiveFcoeTunnelTable 1 }

RlFipActiveFcoeTunnelEntry ::= SEQUENCE {
        rlFipActiveFcoeTunnelPort               INTEGER,
        rlFipActiveFcoeTunnelSrcMac             MacAddress,
        rlFipActiveFcoeTunnelDstMac             MacAddress,
        rlFipActiveFcoeTunnelSid                OCTET STRING(SIZE(0..3)),
        rlFipActiveFcoeTunnelStatus             RowStatus
    }

rlFipActiveFcoeTunnelPort OBJECT-TYPE
    SYNTAX     INTEGER
    MAX-ACCESS not-accessible
    STATUS     current
    DESCRIPTION
           "FCOE tunnel port."
    ::= { rlFipActiveFcoeTunnelEntry 1 }

rlFipActiveFcoeTunnelSrcMac OBJECT-TYPE
    SYNTAX     MacAddress
    MAX-ACCESS not-accessible
    STATUS     current
    DESCRIPTION
           "FCOE tunnel Source MAC address."
    ::= { rlFipActiveFcoeTunnelEntry 2 }

rlFipActiveFcoeTunnelDstMac OBJECT-TYPE
    SYNTAX     MacAddress
    MAX-ACCESS not-accessible
    STATUS     current
    DESCRIPTION
           "FCOE tunnel Destination MAC address."
    ::= { rlFipActiveFcoeTunnelEntry 3 }


rlFipActiveFcoeTunnelSid OBJECT-TYPE
    SYNTAX     OCTET STRING(SIZE(0..3))
    MAX-ACCESS not-accessible
    STATUS     current
    DESCRIPTION
           "FCOE Source ID."
    ::= { rlFipActiveFcoeTunnelEntry 4 }


rlFipActiveFcoeTunnelStatus OBJECT-TYPE
    SYNTAX      RowStatus
    MAX-ACCESS  read-create
    STATUS      current
    DESCRIPTION
        "The status of the entry. It's used to add/delete the entries"
    ::= { rlFipActiveFcoeTunnelEntry 5 }



-- Scalars -----------------------------

rlFipEnableScalar OBJECT-TYPE
    SYNTAX  TruthValue
    MAX-ACCESS  read-write
    STATUS      current
    DESCRIPTION
        "FIP Enable/Disable."
    ::= { rlFip 5 }


rlFipClearDynamicEntiesScalar OBJECT-TYPE
    SYNTAX  INTEGER
    MAX-ACCESS  read-write
    STATUS      current
    DESCRIPTION
        "Clear dynamic tunnels."
    ::= { rlFip 6 }


rlFipGlobalFcfFilteringEnableScalar OBJECT-TYPE
    SYNTAX  TruthValue
    MAX-ACCESS  read-write
    STATUS      current
    DESCRIPTION
        "Enable/Disable filtering of packets based on
         configured list of MAC addresses of FCFs."
    ::= { rlFip 7 }



END
