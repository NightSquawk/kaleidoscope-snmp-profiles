TERACOM-TCW111-MIB DEFINITIONS ::= BEGIN

IMPORTS
   enterprises, IpAddress, Gauge, TimeTicks     FROM RFC1155-SMI
   DisplayString                                FROM RFC1213-MIB
   OBJECT-TYPE                                  FROM RFC-1212
   TRAP-TYPE                                    FROM RFC-1215;

teracom                           OBJECT IDENTIFIER ::=  { enterprises 38783 }

product                            OBJECT IDENTIFIER ::=  { teracom 1 }
setup                               OBJECT IDENTIFIER ::=  { teracom 2 }
monitorNcontrol                     OBJECT IDENTIFIER ::=  { teracom 3 }

   RECIPIENT          ::=   INTEGER { RECIPIENT2(1), RECIPIENT1(0) }
   VOLT-RANGE          ::=   INTEGER { 0V_TO_5V(0), 0V_TO_100V(1) }
   ON-OFF          ::=   INTEGER { ON(1), OFF(0) }
   RISING-FALLING          ::=   INTEGER { RISING(1), FALLING(0) }
   CONTROLLED          ::=   INTEGER { DIGITAL_INPUT(4), ANALOG_INPUT(3), HUMIDITY(2), TEMPERATURE(1), MANUAL(0) }
   ACTION          ::=   INTEGER { SEND_MAIL(1), NO_ACTION(0) }
   DIGITAL-ACTION          ::=   INTEGER { RISING(2), FALLING(1), NO_ACTION(0) }


name    OBJECT-TYPE
   SYNTAX DisplayString
   ACCESS read-only
   STATUS mandatory
   DESCRIPTION
      "Name of product. e.g. teracom.net etc."
   ::= { product 1 }
   

version    OBJECT-TYPE
   SYNTAX DisplayString
   ACCESS read-only
   STATUS mandatory
   DESCRIPTION
      "Version string. e.g. 1.0"
   ::= { product 2 }
   
date    OBJECT-TYPE
   SYNTAX DisplayString
   ACCESS read-only
   STATUS mandatory
   DESCRIPTION
      "Date of version"
   ::= { product 3 }

--MACfilter1                             OBJECT IDENTIFIER ::=  { MACfilters 1 }
--MACfilter2                             OBJECT IDENTIFIER ::=  { MACfilters 2 }
--MACfilter3                             OBJECT IDENTIFIER ::=  { MACfilters 3 }
--SMTPsetup                             OBJECT IDENTIFIER ::=  { network 7 }
--VlanSetup                             OBJECT IDENTIFIER ::=  { network 8 }

network                             	OBJECT IDENTIFIER ::=  { setup 1 }
oneWireSensor                      		OBJECT IDENTIFIER ::=  { setup 2 }
--temperature                        		OBJECT IDENTIFIER ::=  { setup 7 }
--analogInput                        		OBJECT IDENTIFIER ::=  { setup 8 }
--digitalInput                        	OBJECT IDENTIFIER ::=  { setup 9 }
--relay	                        		OBJECT IDENTIFIER ::=  { setup 10 }


deviceIPAddress OBJECT-TYPE
    SYNTAX  IpAddress
    ACCESS  read-write
    STATUS mandatory
    DESCRIPTION
        "Device IP address"
    ::= { network 1 }


subnetMask OBJECT-TYPE
    SYNTAX  IpAddress
    ACCESS  read-write
    STATUS mandatory
    DESCRIPTION
        "Subnet Mask"
    ::= { network 2 }

gateway OBJECT-TYPE
    SYNTAX  IpAddress
    ACCESS  read-write
    STATUS mandatory
    DESCRIPTION
        "Gateway IP address"
    ::= { network 3 }

deviceMACAddress OBJECT-TYPE
    SYNTAX  OCTET STRING (SIZE(6))
    ACCESS  read-write
    STATUS mandatory
    DESCRIPTION
        "Device MAC address"
    ::= { network 4 }

dhcpConfig OBJECT-TYPE
    SYNTAX INTEGER { ON(1), OFF(0) }
    ACCESS read-write
    STATUS mandatory
    DESCRIPTION 
        "DHCP configuration ON/OFF"
    ::= { network 5 }

DNS OBJECT-TYPE
    SYNTAX  IpAddress
    ACCESS  read-write
    STATUS mandatory
    DESCRIPTION
        "Domain Name Server Address"
    ::= { network 6 }

hostName  OBJECT-TYPE
    SYNTAX  DisplayString (SIZE (0..38))
    ACCESS read-write
    STATUS mandatory
    DESCRIPTION
        "Host Name"
    ::= { network 7 }
	
timeServer  OBJECT-TYPE
    SYNTAX  DisplayString (SIZE (0..38))
    ACCESS read-write
    STATUS mandatory
    DESCRIPTION
        "Time Server"
    ::= { network 8 }
	

timeZone  OBJECT-TYPE
    SYNTAX  DisplayString (SIZE (0..38))
    ACCESS read-write
    STATUS mandatory
    DESCRIPTION
        "Time Zone"
    ::= { network 9 }

VLAN                             		OBJECT IDENTIFIER ::=  { network 10 }

vlanStatus OBJECT-TYPE
    SYNTAX INTEGER { ENABLED(1), DISABLED(0) }
    ACCESS read-write
    STATUS mandatory
    DESCRIPTION 
        "VLAN Status ENABLED/DISABLED"
    ::= { VLAN 1 }

vlanId OBJECT-TYPE
    SYNTAX INTEGER (0..4095)
    ACCESS read-write
    STATUS mandatory
    DESCRIPTION 
        "VLAN ID (0-4095)"
    ::= { VLAN 2 }

macFilter                             	OBJECT IDENTIFIER ::=  { network 11 }
filterMACAddress1 OBJECT-TYPE
    SYNTAX  OCTET STRING (SIZE(6))
    ACCESS  read-only
    STATUS mandatory
    DESCRIPTION
        "filter1 MAC address"
    ::= { macFilter 1 }

filterMACEnable1 OBJECT-TYPE
    SYNTAX INTEGER { ENABLED(1), DISABLED(0) }
    ACCESS read-write
    STATUS mandatory
    DESCRIPTION 
        "MAC filter 1 Enable ENABLED/DISABLED"
    ::= { macFilter 2  }
	
filterMACAddress2 OBJECT-TYPE
    SYNTAX  OCTET STRING (SIZE(6))
    ACCESS  read-write
    STATUS mandatory
    DESCRIPTION
        "filter2 MAC address"
    ::= { macFilter 3 }
	
filterMACEnable2 OBJECT-TYPE
    SYNTAX INTEGER { ENABLED(1), DISABLED(0) }
    ACCESS read-write
    STATUS mandatory
    DESCRIPTION 
        "MAC filter 2 Enable ENABLED/DISABLED"
    ::= { macFilter 4 }

filterMACAddress3 OBJECT-TYPE
    SYNTAX  OCTET STRING (SIZE(6))
    ACCESS  read-write
    STATUS mandatory
    DESCRIPTION
        "filter3 MAC address"
    ::= { macFilter 5 }

filterMACEnable3 OBJECT-TYPE
    SYNTAX INTEGER { ENABLED(1), DISABLED(0) }
    ACCESS read-write
    STATUS mandatory
    DESCRIPTION 
        "MAC filter 3 Enable ENABLED/DISABLED"
    ::= { macFilter 6 }

--trapSetup                               OBJECT IDENTIFIER ::=  { SNMPSetup 1}
--voltage1range                               OBJECT IDENTIFIER ::=  { trapSetup 8}
--meratureRange                               OBJECT IDENTIFIER ::=  { trapSetup 10}

SMTP                             		OBJECT IDENTIFIER ::=  { network 12 }

smtpServerAddress OBJECT-TYPE
    SYNTAX  DisplayString (SIZE (0..38))
    ACCESS read-write
    STATUS mandatory
    DESCRIPTION
        "Sender Server Address"
    ::= { SMTP 1 }

smtpPort OBJECT-TYPE
    SYNTAX INTEGER (1..65535)
    ACCESS read-write
    STATUS mandatory
    DESCRIPTION 
        "SMTP Port (1-65535)"
    ::= { SMTP 2 }

senderEmailAddress  OBJECT-TYPE
    SYNTAX  DisplayString (SIZE (0..37))
    ACCESS read-write
    STATUS mandatory
    DESCRIPTION
        "Sender e-mail address"
    ::= { SMTP 3 }

SNMP                             		OBJECT IDENTIFIER ::=  { network 13 }

SNMPConfiguration OBJECT-TYPE
    SYNTAX INTEGER { ENABLED(1), DISABLED(0) }
    ACCESS read-write
    STATUS mandatory
    DESCRIPTION 
        "SNMP Configuration ENABLED/DISABLED"
    ::= { SNMP 1 }
	
trapEnabled OBJECT-TYPE
    SYNTAX INTEGER { Yes(1), No(0) }
    ACCESS read-write
    STATUS mandatory
    DESCRIPTION
        "Indicates if this trap entry is enabled or not."
    ::= { SNMP 2 }

trapReceiverIPAddress OBJECT-TYPE
    SYNTAX  IpAddress
    ACCESS  read-write
    STATUS mandatory
    DESCRIPTION
        "Trap receiver IP address"
    ::= { SNMP 3 }

trapCommunity OBJECT-TYPE
    SYNTAX  DisplayString (SIZE (0..13))
    ACCESS  read-write
    STATUS mandatory
    DESCRIPTION
        "Trap community to be used by agent to send trap"
    ::= { SNMP 4 }

trapInterval OBJECT-TYPE
    SYNTAX INTEGER (0..255)
    ACCESS read-write
    STATUS mandatory
    DESCRIPTION 
        "Trap Interval"
    ::= { SNMP 5 }

maxNumberOfTraps OBJECT-TYPE
    SYNTAX UNSIGNED-INTEGER (0..255)
    ACCESS read-write
    STATUS mandatory
    DESCRIPTION 
        "Max Number of Traps"
    ::= { SNMP 6 }
	

temperature                      		OBJECT IDENTIFIER ::=  { oneWireSensor 1 }

temperatureMin OBJECT-TYPE
    SYNTAX INTEGER (-400..2000)
    ACCESS  read-write
    STATUS mandatory
    DESCRIPTION
        "Temperature minimum"
    ::= { temperature 1 }
	
temperatureMax OBJECT-TYPE
    SYNTAX INTEGER (-400..2000)
    ACCESS  read-write
    STATUS mandatory
    DESCRIPTION
        "Temperature maximum"
    ::= { temperature 2 }

temperatureHyst OBJECT-TYPE
    SYNTAX INTEGER (0..2400)
    ACCESS  read-write
    STATUS mandatory
    DESCRIPTION
        "Temperature hysteresis"
    ::= { temperature 3 }

temperatureAction OBJECT-TYPE
    SYNTAX  ACTION
    ACCESS  read-write
    STATUS mandatory
    DESCRIPTION
        "Temperature Action"
    ::= { temperature 4 }
	
humidity                      		OBJECT IDENTIFIER ::=  { oneWireSensor 2 }

humidityMin OBJECT-TYPE
    SYNTAX INTEGER (0..2000)
    ACCESS  read-write
    STATUS mandatory
    DESCRIPTION
        "Humidity minimum"
    ::= { humidity 1 }

humidityMax OBJECT-TYPE
    SYNTAX INTEGER (0..2000)
    ACCESS  read-write
    STATUS mandatory
    DESCRIPTION
        "Humidity maximum"
    ::= { humidity 2 }
	
humidityHyst OBJECT-TYPE
    SYNTAX INTEGER (0..2000)
    ACCESS  read-write
    STATUS mandatory
    DESCRIPTION
        "Humidity hysteresis"
    ::= { humidity 3 }

humidityAction OBJECT-TYPE
    SYNTAX  ACTION
    ACCESS  read-write
    STATUS mandatory
    DESCRIPTION
        "Humidity Action"
    ::= { humidity 4 }
	

analogInput                      		OBJECT IDENTIFIER ::=  { setup 3 }

voltageMin OBJECT-TYPE
    SYNTAX INTEGER (0..4000)
    ACCESS  read-write
    STATUS mandatory
    DESCRIPTION
        "Voltage minimum"
    ::= { analogInput 1 }
	
voltageMax OBJECT-TYPE
    SYNTAX INTEGER (0..4000)
    ACCESS  read-write
    STATUS mandatory
    DESCRIPTION
        "Voltage maximum"
    ::= { analogInput 2 }

voltageHyst OBJECT-TYPE
    SYNTAX INTEGER (0..4000)
    ACCESS  read-write
    STATUS mandatory
    DESCRIPTION
        "Voltage hysteresis"
    ::= { analogInput 3 }

voltageAction OBJECT-TYPE
    SYNTAX  ACTION
    ACCESS  read-write
    STATUS mandatory
    DESCRIPTION
        "Voltage Action"
    ::= { analogInput 4 }
	
voltageRange OBJECT-TYPE
    SYNTAX  VOLT-RANGE
    ACCESS  read-write
    STATUS mandatory
    DESCRIPTION
        "Voltage Range"
    ::= { analogInput 5 }

	
--digitalInput
digitalInput                      		OBJECT IDENTIFIER ::=  { setup 4 }

digitalInputAction OBJECT-TYPE
    SYNTAX  DIGITAL-ACTION
    ACCESS  read-write
    STATUS mandatory
    DESCRIPTION
        "Digital Input Action"
    ::= { digitalInput 1 }


relay                      		OBJECT IDENTIFIER ::=  { setup 5 }
	
relayControl OBJECT-TYPE
    SYNTAX  CONTROLLED
    ACCESS  read-write
    STATUS mandatory
    DESCRIPTION
        "Relay Control Item"
    ::= { relay 1 }
	
relayPulseWidth OBJECT-TYPE
    SYNTAX INTEGER (0..255)
    ACCESS read-write
    STATUS mandatory
    DESCRIPTION 
        "Relay Pulse Width"
    ::= { relay 2 }


recipients                      		OBJECT IDENTIFIER ::=  { setup 6 }

recipient1  OBJECT-TYPE
    SYNTAX  DisplayString (SIZE (0..37))
    ACCESS read-write
    STATUS mandatory
    DESCRIPTION
        "recipient1's e-mail address"
    ::= { recipients 1 }
	

digitalInputState OBJECT-TYPE
    SYNTAX INTEGER { ON(1), OFF(0) }
    ACCESS read-write
    STATUS mandatory
    DESCRIPTION 
        "Digital Input State"
    ::= { monitorNcontrol 1 }

relayState OBJECT-TYPE
    SYNTAX INTEGER { ON(1), OFF(0) }
    ACCESS read-write
    STATUS mandatory
    DESCRIPTION 
        "Relay State"
    ::= { monitorNcontrol 2 }

relayPulse OBJECT-TYPE
    SYNTAX INTEGER { ON(1), OFF(0) }
    ACCESS read-write
    STATUS mandatory
    DESCRIPTION 
        "Relay Pulse"
    ::= { monitorNcontrol 3 }
	
voltx10Int OBJECT-TYPE
    SYNTAX INTEGER (0..65535)
    ACCESS read-only
    STATUS mandatory
    DESCRIPTION 
        "Voltage x10 in Integer format"
    ::= { monitorNcontrol 4 }
	

tempx10Int OBJECT-TYPE
	SYNTAX INTEGER (-400..1750)
	ACCESS read-only
	STATUS mandatory
	DESCRIPTION
		"Temperature x10 in Integer format"
	::= { monitorNcontrol 5 }
	
   
humix10Int OBJECT-TYPE
    SYNTAX INTEGER (0..65535)
    ACCESS read-only
    STATUS mandatory
    DESCRIPTION 
        "Humidity x10 in Integer format"
    ::= { monitorNcontrol 6 }


-- inputs	

--- configurationSaved
configurationSaved OBJECT-TYPE
	SYNTAX INTEGER { SAVED(1), UNSAVED(0) }
	ACCESS read-write
	STATUS mandatory
	DESCRIPTION
		"Configuration save status SAVED/UNSAVED"
	::= { monitorNcontrol 7 }

restartDevice OBJECT-TYPE
	SYNTAX INTEGER { RESTART(1), CANCEL(0) }
	ACCESS read-write
	STATUS mandatory
	DESCRIPTION
		"Restart Device"
	::= { monitorNcontrol 8 }

trcDigitalInputState TRAP-TYPE
        ENTERPRISE teracom
        VARIABLES  {digitalInput}
        DESCRIPTION
            "This trap is sent each time when Digital Input changes its state"
       ::=  101
	   
trcVoltagex10Int TRAP-TYPE
        ENTERPRISE teracom
        VARIABLES  {voltx10Int}
        DESCRIPTION
            "The voltage measured on Analog Input entered alarm condition"
       ::=  102

trcTempx10Int TRAP-TYPE
        ENTERPRISE teracom
        VARIABLES  {tempx10Int}
        DESCRIPTION
            "Temperature entered alarm condition"
       ::=  103

trcHumix10Int TRAP-TYPE
        ENTERPRISE teracom
        VARIABLES  {humix10Int}
        DESCRIPTION
            "Humidity entered alarm condition"
       ::=  104
	   
trcRestartDevice TRAP-TYPE
        ENTERPRISE teracom
        VARIABLES  {restartDevice}
        DESCRIPTION
            "Device restart"
       ::=  105
END
