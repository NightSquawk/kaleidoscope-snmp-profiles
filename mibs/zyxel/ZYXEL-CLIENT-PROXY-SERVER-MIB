-- ZyXEL Communications Corporation
-- Private Enterprise MIB definition

-- This file describes the ZyXEL Communications Corporation Enterprise MIB.
-- It contains ZyXEL products OIDs, and common managed objects.

-- $ Log: ZYXEL-CLIENT-PROXY-SERVER-MIB.mib $
-- Revision 1.0  2019/09/30 09:00:00 Tiger Fu
-- Initial revision

ZYXEL-CLIENT-PROXY-SERVER-MIB DEFINITIONS ::= BEGIN

	--  =============================================================================
	--                            Include related libraries
    --  =============================================================================
    IMPORTS
   		esMgmt				FROM ZYXEL-ES-SMI
		OBJECT-TYPE			FROM SNMPv2-SMI
		DisplayString       FROM SNMPv2-TC
		EnabledStatus       FROM P-BRIDGE-MIB;

    --  =============================================================================
	--                            ROOT(Client Proxy Server)
    --  =============================================================================
	zyxelClientProxyServer MODULE-IDENTITY
		LAST-UPDATED	"201909300900Z"
		ORGANIZATION	"Enterprise Solution ZyXEL"
		CONTACT-INFO
			""
		DESCRIPTION
			"The subtree for client proxy server."
		::= { esMgmt 121 }

    --  =============================================================================
	--                            Client Proxy Server Setup
    --  =============================================================================
	zyxelClientProxyServerSetup OBJECT IDENTIFIER ::= { zyxelClientProxyServer 1 }

	--  =============================================================================
	--                          Client HTTP Proxy Server State
    --  =============================================================================
 	zyClientProxyServerHttpState OBJECT-TYPE
	    SYNTAX     EnabledStatus
	    MAX-ACCESS read-write
	    STATUS     current
	    DESCRIPTION
	        "Enable(1)/Disable(2) client connection over proxy."
	    ::= { zyxelClientProxyServerSetup 1 }

	--  =============================================================================
	--                         Client HTTP Proxy Server Server
    --  =============================================================================
 	zyClientProxyServerHttpServer OBJECT-TYPE
	    SYNTAX     DisplayString
	    MAX-ACCESS read-write
	    STATUS     current
	    DESCRIPTION
	        "Proxy server hostname or IP address.
			(Ex: www.zyxel.com.tw or 192.168.1.1)"
	    ::= { zyxelClientProxyServerSetup 2 }

	--  =============================================================================
	--                          Client HTTP Proxy Server Port
    --  =============================================================================
 	zyClientProxyServerHttpPort OBJECT-TYPE
	    SYNTAX     INTEGER
	    MAX-ACCESS read-write
	    STATUS     current
	    DESCRIPTION
	        "Proxy listen TCP port number.
			The valid value should be in range 1-65535."
	    ::= { zyxelClientProxyServerSetup 3 }

	--  =============================================================================
	--                  Client HTTP Proxy Server Authentication State
    --  =============================================================================
 	zyClientProxyServerHttpAuthenticationState OBJECT-TYPE
	    SYNTAX     EnabledStatus
	    MAX-ACCESS read-write
	    STATUS     current
	    DESCRIPTION
	        "Enable(1)/Disable(2) to use proxy authentication.
			(Send out proxy login information)"
	    ::= { zyxelClientProxyServerSetup 4 }

	--  =============================================================================
	--                        Client HTTP Proxy Server Username
    --  =============================================================================
 	zyClientProxyServerHttpUsername OBJECT-TYPE
	    SYNTAX     DisplayString
	    MAX-ACCESS read-write
	    STATUS     current
	    DESCRIPTION
	        "Get/set proxy login username."
	    ::= { zyxelClientProxyServerSetup 5 }

	--  =============================================================================
	--                        Client HTTP Proxy Server Password
    --  =============================================================================
 	zyClientProxyServerHttpPassword OBJECT-TYPE
	    SYNTAX     DisplayString
	    MAX-ACCESS read-write
	    STATUS     current
	    DESCRIPTION
	        "Set the plain text password.
			Get the password is disallowed for safe security."
	    ::= { zyxelClientProxyServerSetup 6 }
END
