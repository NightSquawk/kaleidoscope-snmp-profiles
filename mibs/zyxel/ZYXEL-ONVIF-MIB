-- ZyXEL Communications Corporation
-- Private Enterprise MIB definition 
  
-- This file describes the ZyXEL Communications Corporation Enterprise MIB.
-- It contains ZyXEL products OIDs, and common managed objects.



ZYXEL-ONVIF-MIB DEFINITIONS ::= BEGIN
	IMPORTS
	OBJECT-TYPE
		FROM SNMPv2-SMI			-- RFC2578	
		
	MODULE-IDENTITY
		FROM SNMPv2-SMI
	
	RowStatus
		FROM SNMPv2-TC			-- RFC2579
	
	PortList
		FROM  Q-BRIDGE-MIB

	EnabledStatus
		FROM  P-BRIDGE-MIB 
		
	DisplayString                                          
	  	FROM SNMPv2-TC

	esMgmt			
		FROM ZYXEL-ES-SMI;	

	zyxelOnvif MODULE-IDENTITY
		LAST-UPDATED	"201912160000Z"    
		ORGANIZATION "Enterprise Solution ZyXEL"     
		CONTACT-INFO
			""	   
		DESCRIPTION
			"The subtree for ONVIF"
		::= { esMgmt 123 }

	zyxelOnvifSetup 				OBJECT IDENTIFIER ::= { zyxelOnvif 1 }

-- 	******************************************************************
-- *
-- 1.zyxelOnvifSetup
-- *
-- ******************************************************************         
		zyOnvifState OBJECT-TYPE
		SYNTAX  EnabledStatus
		MAX-ACCESS  read-write
		STATUS  current
		DESCRIPTION
			"Enable/Disable ONVIF on the switch."
		::= { zyxelOnvifSetup 1 }
		
--	zyxelOnvifVlanTable 
        zyOnvifMaxNumberOfVlans OBJECT-TYPE
        SYNTAX  INTEGER
        MAX-ACCESS  read-only
        STATUS  current
        DESCRIPTION
		"The maximum number of ONVIF VLAN entries that can be created"
        ::= { zyxelOnvifSetup 2 }        

		zyxelOnvifVlanTable OBJECT-TYPE
		SYNTAX	SEQUENCE OF ZyxelOnvifVlanEntry
        MAX-ACCESS  not-accessible
        STATUS  current
        DESCRIPTION   
        "The table contains ONVIF VLAN configuration."		
		::=	{ zyxelOnvifSetup 3 }
		
		zyxelOnvifVlanEntry OBJECT-TYPE
		SYNTAX  ZyxelOnvifVlanEntry
        MAX-ACCESS	not-accessible              
        STATUS	current
        DESCRIPTION	
        "An entry contains ONVIF VLAN configuration."
		INDEX	{ zyOnvifVlanVid }
		::={ zyxelOnvifVlanTable 1 }
		
		ZyxelOnvifVlanEntry ::=
			SEQUENCE {
				zyOnvifVlanVid			INTEGER,
				zyOnvifVlanPorts		PortList,
				zyOnvifVlanRowStatus	RowStatus
			}
		
		
		zyOnvifVlanVid OBJECT-TYPE
		SYNTAX 	INTEGER  (1.. 4094)
        MAX-ACCESS	not-accessible
        STATUS	current
        DESCRIPTION	
        "This parameter specifies the VLAN identification nember."
		::={ zyxelOnvifVlanEntry 1 }
		
		zyOnvifVlanPorts OBJECT-TYPE
		SYNTAX 	PortList
        MAX-ACCESS	read-write
        STATUS	current
        DESCRIPTION	
        "The set of ports which should send probe packets for this VLAN entry."
		::={ zyxelOnvifVlanEntry 2 }

		zyOnvifVlanRowStatus OBJECT-TYPE
		SYNTAX 	RowStatus
        MAX-ACCESS	read-create
        STATUS	current
        DESCRIPTION	
        "This object allow ONVIF VLAN entries to be create and deleted from ONVIF VLAN table."
		::={ zyxelOnvifVlanEntry 3 }        
                
END
