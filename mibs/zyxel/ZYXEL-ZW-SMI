-- **********************************************
-- ZYXEL-ZW-SMI.MIB
-- Zyxel Communications Corporation
-- 
-- ZyWALL Security Gateway MIB definitions
-- Structure of Management Information (SMI)
--
-- Joshua Jang
--
-- Copyright by Zyxel Communications Corp.
-- All rights reserved.
-- **********************************************

ZYXEL-ZW-SMI DEFINITIONS ::= BEGIN

IMPORTS

	MODULE-IDENTITY,
	OBJECT-IDENTITY,
	enterprises		FROM SNMPv2-SMI;
    	
zyxel			OBJECT IDENTIFIER ::= { enterprises 890 }
products		OBJECT IDENTIFIER ::= { zyxel 1 }
	
zywall MODULE-IDENTITY
	LAST-UPDATED "201904010000Z"
	ORGANIZATION "Zyxel GSBU"     
	CONTACT-INFO
		""	     
	DESCRIPTION
		"The MIB Module for ZyWALL Secrity Gateway"
	::= { products 6 }

zywallZLDCommon           OBJECT-IDENTITY
	STATUS		current
	DESCRIPTION
		"Subtree for MIBs common for ZyWALL ZLD products"
	::= { zywall 22 }
	
END
