-- ZyXEL Communications Corporation
-- Private Enterprise MIB definition 
  
-- This file describes the ZyXEL Communications Corporation Enterprise MIB.
-- It contains ZyXEL products OIDs, and common managed objects.

-- $Log: ZYXEL-OSPFv3-MIB.mib $ 


ZYXEL-OSPFv3-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
		
	DisplayString                                          
	  	FROM SNMPv2-TC
	  	
	EnabledStatus
		FROM  P-BRIDGE-MIB
 	
    IpAddress
        FROM SNMPv2-SMI

	esMgmt			
		FROM ZYXEL-ES-SMI;

	zyxelOspfv3 MODULE-IDENTITY
		LAST-UPDATED	"201801080000Z"    
		ORGANIZATION "Enterprise Solution ZyXEL"     
		CONTACT-INFO
			""	   
		DESCRIPTION
			"The subtree for Open Shortest Path First for IPv6 (OSPFv3)"
		::= { esMgmt 117 }
	
	zyxelOspfv3Setup     			OBJECT IDENTIFIER ::= { zyxelOspfv3 1 }
	zyxelOspfv3Notifications		OBJECT IDENTIFIER ::= { zyxelOspfv3 4 }
  
-- *******************************************************************
-- *
-- * zyxelOspfv3Setup
-- *
-- *******************************************************************
       
-- zyxelOspfv3RedistributeRouteTable
        zyxelOspfv3RedistributeRouteTable	OBJECT-TYPE
        SYNTAX		SEQUENCE OF ZyxelOspfv3RedistributeRouteEntry
        MAX-ACCESS  not-accessible
        STATUS  	current
        DESCRIPTION
                 	"The table contains OSPFv3 redistribute route configuration."
        ::= { zyxelOspfv3Setup 1 }
        
		zyxelOspfv3RedistributeRouteEntry OBJECT-TYPE
        SYNTAX		ZyxelOspfv3RedistributeRouteEntry
        MAX-ACCESS	not-accessible
        STATUS		current
        DESCRIPTION    	
					"An entry contains OSPFv3 redistribute route configuration."
		INDEX          	{ zyOspfv3RedistributeRouteProtocol }
        ::= { zyxelOspfv3RedistributeRouteTable 1 }

        ZyxelOspfv3RedistributeRouteEntry ::=
		SEQUENCE {
        	zyOspfv3RedistributeRouteProtocol	INTEGER,
        	zyOspfv3RedistributeRouteState		EnabledStatus,
        	zyOspfv3RedistributeRouteType		INTEGER,
        	zyOspfv3RedistributeRouteMetric		INTEGER
        } 
		
        zyOspfv3RedistributeRouteProtocol OBJECT-TYPE
        SYNTAX  INTEGER{		
		ripng(1),
		static(2)
        }
        MAX-ACCESS  read-only
        STATUS  current
        DESCRIPTION
                      	"Route redistribution allows your switch to import and translate external routes learned through RIP routing protocol or configured manually (Static) into the OSPFv3 network transparently."
        ::= { zyxelOspfv3RedistributeRouteEntry 1 }

        zyOspfv3RedistributeRouteState OBJECT-TYPE
        SYNTAX  	EnabledStatus
        MAX-ACCESS  read-write
        STATUS  	current
        DESCRIPTION
                      	"Enable/Disable the routing protocol to activate route redistribution for routes learned."
        ::= { zyxelOspfv3RedistributeRouteEntry 2 }

        zyOspfv3RedistributeRouteType OBJECT-TYPE
        SYNTAX  	INTEGER
        MAX-ACCESS  read-write
        STATUS		current
        DESCRIPTION
                      	"Select 1 for routing protocols (such as RIPng) whose external metrics are directly comparable to the internal OSPFv3 cost. 
						When selecting a path, the internal OSPFv3 cost is added to the AB boundary router to the external metrics. 
						Select 2 for routing protocols whose external metrics are not comparable to the OSPFv3 cost. 
						In this case, the external cost of the AB boundary router is used in path decision to a destination."
        ::= { zyxelOspfv3RedistributeRouteEntry 3 }

        zyOspfv3RedistributeRouteMetric OBJECT-TYPE
        SYNTAX  	INTEGER
        MAX-ACCESS  read-write
        STATUS  	current
        DESCRIPTION
			"Specify a route cost (between 0 and 16777215)."
        ::= { zyxelOspfv3RedistributeRouteEntry 4 }
		
-- zyxelOspfv3GeneralGroup        
		zyxelOspfv3GeneralGroup OBJECT IDENTIFIER ::= { zyxelOspfv3Setup 2 }

		zyOspfv3Distance OBJECT-TYPE
			SYNTAX   	INTEGER
			MAX-ACCESS   read-write
			STATUS   	current
			DESCRIPTION
			   "The administrative distance of OSPFv3 routes."		   
		::= { zyxelOspfv3GeneralGroup 1 }


-- *******************************************************************
-- *
-- * zyxelOspfv3Notifications
-- *
-- *******************************************************************
    
	   zyOspfv3ExceedMaxDynamicRoutePath NOTIFICATION-TYPE
	   STATUS  current
       DESCRIPTION
               "Receive LSA route path is over maximum LSA. "
       ::= { zyxelOspfv3Notifications 1 }
		
END
