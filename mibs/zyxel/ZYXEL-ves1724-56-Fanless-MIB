-- ZyXEL Communications Corporation
-- Private Enterprise MIB definition

-- This file describes the ZyXEL Communications Corporation Enterprise MIB.
-- It contains ZyXEL products OIDs, and common managed objects.


ZYXEL-ves1724-56-Fanless-MIB DEFINITIONS ::= BEGIN

    IMPORTS
	enterprises		FROM RFC1155-SMI

	OBJECT-TYPE
		FROM SNMPv2-SMI			-- RFC2578
	RowStatus, DateAndTime, TruthValue, StorageType, MacAddress
		FROM SNMPv2-TC			-- RFC2579
	DisplayString
	  	FROM RFC1213-MIB
	EnabledStatus
		FROM  P-BRIDGE-MIB
	PortList
		FROM  Q-BRIDGE-MIB
	dot1dBasePort
        	FROM BRIDGE-MIB
	InterfaceIndexOrZero			-- RFC2863
		FROM IF-MIB
	SnmpAdminString
		FROM SNMP-FRAMEWORK-MIB		-- RFC2571
	InetAddressType, InetAddress
		FROM INET-ADDRESS-MIB		-- RFC2851
	OperationResponseStatus
		FROM DISMAN-PING-MIB	
	vdslLineConfProfileName 
		FROM VDSL-LINE-MIB	
	vdslLineAlarmConfProfileName 
		FROM VDSL-LINE-MIB
	vdslPerf1DayIntervalNumber
		FROM VDSL-LINE-MIB
	vdslPhysSide
		FROM VDSL-LINE-MIB
	ifIndex
		FROM IF-MIB
	vdslPerfIntervalNumber
		FROM VDSL-LINE-MIB
	dot1qVlanIndex
		FROM  Q-BRIDGE-MIB
	Dot1agCfmMepId
		FROM IEEE8021-CFM-MIB	
	Xdsl2RaMode
		FROM VDSL2-LINE-TC-MIB	
	Xdsl2LineLdsf
	    FROM VDSL2-LINE-TC-MIB	
	xdsl2PMChHist1DInterval
	    FROM VDSL2-LINE-MIB
	xdsl2LineBand
	    FROM VDSL2-LINE-MIB
	xdsl2SCStatusSegment,xdsl2LineSegmentDirection
	    FROM VDSL2-LINE-MIB
	xdsl2LineSegment
	    FROM VDSL2-LINE-MIB
	xdsl2ChStatusUnit
	    FROM VDSL2-LINE-MIB
	xdsl2SCStatusDirection
	    FROM VDSL2-LINE-MIB
	xdsl2SCStatusBand
	    FROM VDSL2-LINE-MIB
	xdsl2PMLHist15MUnit
	    FROM VDSL2-LINE-MIB
	xdsl2PMLHist15MInterval
	    FROM VDSL2-LINE-MIB
	xdsl2PMLHist1DUnit
	    FROM VDSL2-LINE-MIB
	xdsl2PMLHist1DInterval
	    FROM VDSL2-LINE-MIB
	xdsl2PMChCurrUnit
	    FROM VDSL2-LINE-MIB
	xdsl2PMChHist15MUnit
	    FROM VDSL2-LINE-MIB
	xdsl2PMChHist15MInterval
	    FROM VDSL2-LINE-MIB
	xdsl2PMLCurrUnit
	    FROM VDSL2-LINE-MIB
	xdsl2PMChHist1DUnit
	    FROM VDSL2-LINE-MIB
	xdsl2LConfTempTemplateName
	    FROM VDSL2-LINE-MIB
	xdsl2LConfProfProfileName
	    FROM VDSL2-LINE-MIB
	xdsl2ChConfProfProfileName
	    FROM VDSL2-LINE-MIB
	xdsl2LAlarmConfTempTemplateName
	    FROM VDSL2-LINE-MIB
	xdsl2LineAlarmConfProfileName
	    FROM VDSL2-LINE-MIB
	xdsl2ChAlarmConfProfileName
	    FROM VDSL2-LINE-MIB
			
    IpAddress
        FROM SNMPv2-SMI
    Ipv6Address    
    	FROM IPV6-TC
    Ipv6AddressPrefix            
    	FROM IPV6-TC

    NOTIFICATION-TYPE
        FROM SNMPv2-SMI
    sysObjectID
        FROM RFC1213-MIB
    BridgeId, Timeout
        FROM BRIDGE-MIB


   HCPerfIntervalThreshold,
   HCPerfTimeElapsed
      FROM  HC-PerfHist-TC-MIB;   -- [RFC3705]
		
		zyxel		OBJECT IDENTIFIER ::= { enterprises 890 }
		products	OBJECT IDENTIFIER ::= { zyxel 1 }
		accessSwitch  	OBJECT IDENTIFIER ::= { products 5 }
		vesSeries	OBJECT IDENTIFIER ::= { accessSwitch 12 }

		ves1724-56fanless MODULE-IDENTITY
			LAST-UPDATED "1111080000Z" -- 11/08, 2011
			ORGANIZATION "ZyXEL"
			CONTACT-INFO "EMS"
			DESCRIPTION "ZyXEL Private MIB"
			::= { vesSeries 47 }

 --
   -- textual conventions used in this MIB
   --
   
   Vdsl2Band ::= TEXTUAL-CONVENTION
     STATUS current
     DESCRIPTION
        "Identifies a band in a
        VDSL2/ADSL/ADSL2/ADSL2+
        link. For a band in the upstream direction,
        transmission is from the remote end (xTU-R)
        towards the central office end (xTU-C).
        A band in the upstream direction is
        indicated by upstream(1) for
        ADSL/ADSL2/ADSL2+ single band, or any of
        us0(3), us1(5), us2(7), us3(9), or us4(11) for
        VDSL2 multiple bands.
        For a band in the downstream direction,
        transmission is from the xTU-C towards the xTU-R.
        A band in the downstream direction is
        indicated by downstream(2) for
        ADSL/ADSL2/ADSL2+ single band, or any of
        ds1(4), ds2(6), ds3(8), or ds4(10) for
        VDSL2 multiple bands.
        Specified as an INTEGER,
        the values are defined as follows:"
     SYNTAX INTEGER {
        upstream(1),   -- Transmission from the ATU-R to the ATU-C
                       -- (ADSL/ADSL2/ADSL2+).
        downstream(2), -- Transmission from the ATU-C to the ATU-R
                       --(ADSL/ADSL2/ADSL2+).
        us0(3),        -- Upstream band number 0 (US0) (VDSL2).
        ds1(4),        -- Downstream band number 1 (DS1) (VDSL2).
        us1(5),        -- Upstream band number 1 (US1) (VDSL2).
        ds2(6),        -- Downstream band number 2 (DS2) (VDSL2).
        us2(7),        -- Upstream band number 2 (US2) (VDSL2).
        ds3(8),        -- Downstream band number 3 (DS3) (VDSL2).
        us3(9),        -- Upstream band number 3 (US3) (VDSL2).
        ds4(10),       -- Downstream band number 4 (DS4) (VDSL2).
        us4(11)        -- Upstream band number 4 (US4) (VDSL2).
            }

--  sysInfo
	sysInfo     	OBJECT IDENTIFIER ::= { ves1724-56fanless 1 }

        sysSwPlatformMajorVers OBJECT-TYPE
        SYNTAX  INTEGER
        MAX-ACCESS  read-only
        STATUS  current
        DESCRIPTION
                      "SW platform major version, e.g. 3."
        ::= { sysInfo 1 }

        sysSwPlatformMinorVers OBJECT-TYPE
        SYNTAX  INTEGER
        MAX-ACCESS  read-only
        STATUS  current
        DESCRIPTION
                      "SW platform minor version, e.g. 50."
        ::= { sysInfo 2 }

        sysSwModelString OBJECT-TYPE
        SYNTAX  DisplayString
        MAX-ACCESS  read-only
        STATUS  current
        DESCRIPTION
                      "Model letters, e.g. TJ"
        ::= { sysInfo 3 }

        sysSwVersionControlNbr OBJECT-TYPE
        SYNTAX  INTEGER
        MAX-ACCESS  read-only
        STATUS  current
        DESCRIPTION
                      "Version control number, e.g. 0."
        ::= { sysInfo 4 }

        sysSwDay OBJECT-TYPE
        SYNTAX  INTEGER
        MAX-ACCESS  read-only
        STATUS  current
        DESCRIPTION
                      "SW compilation day, e.g. 19."
        ::= { sysInfo 5 }

        sysSwMonth OBJECT-TYPE
        SYNTAX  INTEGER
        MAX-ACCESS  read-only
        STATUS  current
        DESCRIPTION
                      "SW compilation month, e.g. 8."
        ::= { sysInfo 6 }

        sysSwYear OBJECT-TYPE
        SYNTAX  INTEGER
        MAX-ACCESS  read-only
        STATUS  current
        DESCRIPTION
                      "SW compilation year, e.g. 2004."
        ::= { sysInfo 7 }

        sysHwMajorVers OBJECT-TYPE
        SYNTAX  INTEGER
        MAX-ACCESS  read-only
        STATUS  current
        DESCRIPTION
                      "HW major version number, e.g. 1."
        ::= { sysInfo 8 }

        sysHwMinorVers OBJECT-TYPE
        SYNTAX  INTEGER
        MAX-ACCESS  read-only
        STATUS  current
        DESCRIPTION
                      "HW minor version number, e.g. 0."
        ::= { sysInfo 9 }

        sysSerialNumber OBJECT-TYPE
        SYNTAX  DisplayString
        MAX-ACCESS  read-only
        STATUS  current
        DESCRIPTION
                      "Serial number"
        ::= { sysInfo 10 }

        sysFirmwareVersion OBJECT-TYPE
        SYNTAX  DisplayString
        MAX-ACCESS  read-only
        STATUS  current
        DESCRIPTION
                      "VDSL Switch Firmware Version"
        ::= { sysInfo 11 }        

        sysModemCodeVersion OBJECT-TYPE
        SYNTAX  DisplayString
        MAX-ACCESS  read-only
        STATUS  current
        DESCRIPTION
                      "VDSL Modem Code Version"
        ::= { sysInfo 12 }   
        
        sysPowerInfo OBJECT-TYPE
        SYNTAX  DisplayString
        MAX-ACCESS  read-only
        STATUS  current
        DESCRIPTION
                      "CO Power info"
        ::= { sysInfo 13 }          

        sysSwBootUpImage OBJECT-TYPE
        SYNTAX  INTEGER{
         		image_1(1),
         		image_2(2)
        }
        MAX-ACCESS  read-only
        STATUS  current
        DESCRIPTION
                      "Current system boot up image,
                      You can change the boot up image of next rebooting by setting sysMgmtBootupImage."
        ::= { sysInfo 14 }  

        sysImage1FwVersion OBJECT-TYPE
        SYNTAX  DisplayString
        MAX-ACCESS  read-only
        STATUS  current
        DESCRIPTION
                      "VDSL Switch Image 1 Firmware Version"
        ::= { sysInfo 15 }   
        
        sysImage2FwVersion OBJECT-TYPE
        SYNTAX  DisplayString
        MAX-ACCESS  read-only
        STATUS  current
        DESCRIPTION
                      "VDSL Switch Image 2 Firmware Version"
        ::= { sysInfo 16 }  
        
             
-- brLimitSetup
	brLimitSetup OBJECT IDENTIFIER ::= { ves1724-56fanless 3 }

        brLimitState OBJECT-TYPE
        SYNTAX  EnabledStatus
        MAX-ACCESS  read-write
        STATUS  current
        DESCRIPTION
                      	"Broadcast/multicast/DLF rate limiting enabled/disabled for the switch."
        ::= { brLimitSetup 1 }

-- brLimitPortTable
        brLimitPortTable OBJECT-TYPE
        SYNTAX	SEQUENCE OF BrLimitPortEntry
        MAX-ACCESS  not-accessible
        STATUS  current
        DESCRIPTION
                 	""
        ::= { brLimitSetup 2 }

	brLimitPortEntry OBJECT-TYPE
        SYNTAX	BrLimitPortEntry
        MAX-ACCESS	not-accessible
        STATUS	current
        DESCRIPTION    	"An entry in brLimitPortTable."
        INDEX          	{ dot1dBasePort }
        ::= { brLimitPortTable 1 }

        BrLimitPortEntry ::=
           SEQUENCE {
        	brLimitPortBrState	EnabledStatus,
		brLimitPortBrRate	INTEGER,
		brLimitPortMcState	EnabledStatus,
		brLimitPortMcRate	INTEGER,
		brLimitPortDlfState	EnabledStatus,
		brLimitPortDlfRate	INTEGER
           }

        brLimitPortBrState OBJECT-TYPE
        SYNTAX  EnabledStatus
        MAX-ACCESS  read-write
        STATUS  current
        DESCRIPTION
                      	"Broadcast rate limiting enabled/disabled on the port."
        ::= { brLimitPortEntry 1 }

        brLimitPortBrRate OBJECT-TYPE
        SYNTAX  INTEGER
        MAX-ACCESS  read-write
        STATUS  current
        DESCRIPTION
                      	"Allowed broadcast rate in pkts/s. For FE port,
                      	the maximum value is 148800. For GE port, the maximum value is 262143."
        ::= { brLimitPortEntry 2 }

        brLimitPortMcState OBJECT-TYPE
        SYNTAX  EnabledStatus
        MAX-ACCESS  read-write
        STATUS  current
        DESCRIPTION
                      	"Multicast rate limiting enabled/disabled on the port."
        ::= { brLimitPortEntry 3 }

        brLimitPortMcRate OBJECT-TYPE
        SYNTAX  INTEGER
        MAX-ACCESS  read-write
        STATUS  current
        DESCRIPTION
                      	"AAllowed mullticast rate in pkts/s. For FE port,
                      	the maximum value is 148800. For GE port, the maximum value is 262143."
        ::= { brLimitPortEntry 4 }

        brLimitPortDlfState OBJECT-TYPE
        SYNTAX  EnabledStatus
        MAX-ACCESS  read-write
        STATUS  current
        DESCRIPTION
                      	"Destination lookup failure frames rate limiting enabled/disabled on the port."
        ::= { brLimitPortEntry 5 }

        brLimitPortDlfRate OBJECT-TYPE
        SYNTAX  INTEGER
        MAX-ACCESS  read-write
        STATUS  current
        DESCRIPTION
                      	"Allowed destination lookup failure frames rate in pkts/s.
                      	For FE port, the maximum value is 148800. For GE port, the maximum value is 262143."
        ::= { brLimitPortEntry 6 }

-- portSecuritySetup
	portSecuritySetup OBJECT IDENTIFIER ::= { ves1724-56fanless 4 }

	portSecurityState OBJECT-TYPE
        SYNTAX  INTEGER
        MAX-ACCESS  read-write
        STATUS  current
        DESCRIPTION
        "0: Port/VLAN security disable
				 1: Port security Enable, VLAN security Disable
				 2: Port security Disable, VLAN security Enable
				 3: Port/VLAN security Enable"				
        ::= { portSecuritySetup 1 }

        portSecurityPortTable OBJECT-TYPE
        SYNTAX	SEQUENCE OF PortSecurityPortEntry
        MAX-ACCESS  not-accessible
        STATUS  current
        DESCRIPTION
                 	""
        ::= { portSecuritySetup 2 }

	portSecurityPortEntry OBJECT-TYPE
        SYNTAX	PortSecurityPortEntry
        MAX-ACCESS	not-accessible
        STATUS	current
        DESCRIPTION    	"An entry in portSecurityPortTable."
        INDEX          	{ dot1dBasePort }
        ::= { portSecurityPortTable 1 }

        PortSecurityPortEntry ::=
           SEQUENCE {
        	portSecurityPortState		EnabledStatus,
		portSecurityPortLearnState	EnabledStatus,
					portSecurityPortCount		INTEGER,
					portSecurityPortMacSpoofing	EnabledStatus					
           }

        portSecurityPortState OBJECT-TYPE
        SYNTAX  EnabledStatus
        MAX-ACCESS  read-write
        STATUS  current
        DESCRIPTION
                      	"Port Security enabled/disabled on the port.
                      	Active(1) means this port only accept frames from static MAC addresses that are configured for the port,
                      	and dynamic MAC address frames up to the number specified by portSecurityPortCount object."
        ::= { portSecurityPortEntry 1 }

        portSecurityPortLearnState OBJECT-TYPE
        SYNTAX  EnabledStatus
        MAX-ACCESS  read-write
        STATUS  current
        DESCRIPTION
                      	"MAC address learning  enabled/disable on the port."
        ::= { portSecurityPortEntry 2 }

        portSecurityPortCount OBJECT-TYPE
        SYNTAX  INTEGER
        MAX-ACCESS  read-write
        STATUS  current
        DESCRIPTION
                      	"Number of (dynamic) MAC addresses that may be learned on the port."
        ::= { portSecurityPortEntry 3 }

        portSecurityPortMacSpoofing OBJECT-TYPE
        SYNTAX  EnabledStatus
        MAX-ACCESS  read-write
        STATUS  current
        DESCRIPTION
											"Enable/Disable MAC spoofing.
											When enable, the port would not relearn MAC which has existed on L2 table."
        ::= { portSecurityPortEntry 4 }


	portSecurityMacFreeze OBJECT-TYPE
        SYNTAX  PortList
        MAX-ACCESS  read-write
        STATUS  current
        DESCRIPTION
                      	"This entry is used to execute MacFreeze action to port.
                      	It's meaningless while reading this entry."
        ::= { portSecuritySetup 3 }

-- vlanTrunkPortTable
	vlanTrunkSetup OBJECT IDENTIFIER ::= { ves1724-56fanless 5 }

        vlanTrunkPortTable OBJECT-TYPE
        SYNTAX	SEQUENCE OF VlanTrunkPortEntry
        MAX-ACCESS  not-accessible
        STATUS  current
        DESCRIPTION
                 	""
        ::= { vlanTrunkSetup 1 }

	vlanTrunkPortEntry OBJECT-TYPE
        SYNTAX	VlanTrunkPortEntry
        MAX-ACCESS	not-accessible
        STATUS	current
        DESCRIPTION    	"An entry in vlanTrunkPortTable."
        INDEX          	{ dot1dBasePort }
        ::= { vlanTrunkPortTable 1 }

        VlanTrunkPortEntry ::=
           SEQUENCE {
        	vlanTrunkPortState		EnabledStatus
           }

        vlanTrunkPortState OBJECT-TYPE
        SYNTAX  EnabledStatus
        MAX-ACCESS  read-write
        STATUS  current
        DESCRIPTION
                      	"VlanTrunking enabled/disabled on the port.
                      	Active(1) to allow frames belonging to unknown
                      	VLAN groups to pass through the switch."
        ::= { vlanTrunkPortEntry 1 }

--  ctlProtTransSetup
	ctlProtTransSetup OBJECT IDENTIFIER ::= { ves1724-56fanless 6 }

        ctlProtTransState OBJECT-TYPE
        SYNTAX  EnabledStatus
        MAX-ACCESS  read-write
        STATUS  current
        DESCRIPTION
                      	"Bridge control protocol transparency enabled/disabled for the switch"
        ::= { ctlProtTransSetup 1 }

-- ctlProtTransTunnelPortTable

        ctlProtTransTunnelPortTable OBJECT-TYPE
        SYNTAX	SEQUENCE OF CtlProtTransTunnelPortEntry
        MAX-ACCESS  not-accessible
        STATUS  current
        DESCRIPTION
                 	""
        ::= { ctlProtTransSetup 2 }

	ctlProtTransTunnelPortEntry OBJECT-TYPE
        SYNTAX	CtlProtTransTunnelPortEntry
        MAX-ACCESS	not-accessible
        STATUS	current
        DESCRIPTION    	"An entry in ctlProtTransTunnelPortTable."
        INDEX          	{ dot1dBasePort }
        ::= { ctlProtTransTunnelPortTable 1 }

        CtlProtTransTunnelPortEntry ::=
           SEQUENCE {
        	ctlProtTransTunnelMode	INTEGER
           }

        ctlProtTransTunnelMode OBJECT-TYPE
        SYNTAX  INTEGER{
		peer(0),
		tunnel(1),
		discard(2),
		network(3)
        }
        MAX-ACCESS  read-write
        STATUS  current
        DESCRIPTION
                      	"Bridge control protocol transparency mode for the port.
                      	Modes:  Peer(0), Tunnel(1), Discard(2),  Network(3)"
        ::= { ctlProtTransTunnelPortEntry 1 }

--  vlanStackSetup
	vlanStackSetup OBJECT IDENTIFIER ::= { ves1724-56fanless 7 }

        vlanStackState OBJECT-TYPE
        SYNTAX  EnabledStatus
        MAX-ACCESS  read-write
        STATUS  current
        DESCRIPTION
                      "VLAN Stacking enabled/disabled for the switch."
        ::= { vlanStackSetup 1 }

        vlanStackTpid OBJECT-TYPE
        SYNTAX  INTEGER
        MAX-ACCESS  read-write
        STATUS  current
        DESCRIPTION
                      "SP TPID in hex format, e.g. 8100."
        ::= { vlanStackSetup 2 }

-- vlanStackPortTable

        vlanStackPortTable OBJECT-TYPE
        SYNTAX	SEQUENCE OF VlanStackPortEntry
        MAX-ACCESS  not-accessible
        STATUS  current
        DESCRIPTION
                 	""
        ::= { vlanStackSetup 3 }

	vlanStackPortEntry OBJECT-TYPE
        SYNTAX	VlanStackPortEntry
        MAX-ACCESS	not-accessible
        STATUS	current
        DESCRIPTION    	"An entry in vlanStackPortTable."
        INDEX          	{ dot1dBasePort }
        ::= { vlanStackPortTable 1 }

        VlanStackPortEntry ::=
           SEQUENCE {
        	vlanStackPortMode	INTEGER,
        	vlanStackPortVid	INTEGER,
        	vlanStackPortPrio	INTEGER,
        	vlanStackTunnelPortTpid	INTEGER,
        	vlanStackPCopyCtagPrio	EnabledStatus
           }

        vlanStackPortMode OBJECT-TYPE
        SYNTAX  INTEGER {
        normal(1),
		access(2),
		tunnel(3)
	}
        MAX-ACCESS  read-write
        STATUS  current
        DESCRIPTION
                      	"Mode of the port. Set Normal to have the switch ignore frames received 
                      	(or transmitted) on this port with VLAN stacking tags. 
                      	Anything you configure in SPVID and Priority are ignored. 
			Set Access mode to have the switch add the SP TPID tag to all incoming
			frames received on this port. Set Access  mode for ingress ports at the
			edge of the service provider's network. Set Tunnel mode (available for
			Gigabit ports only) for egress ports at the edge of the service provider's
			network. In order to support VLAN stacking on a port, the port must be able
			to allow frames of 1526 Bytes (1522 Bytes + 4 Bytes for the second tag)
			to pass through it. normal (1), Access (2),  tunnel (3)"
        ::= { vlanStackPortEntry 1 }

        vlanStackPortVid OBJECT-TYPE
        SYNTAX  INTEGER
        MAX-ACCESS  read-write
        STATUS  current
        DESCRIPTION
                      	"VLAN ID used in service provider tag."
        ::= { vlanStackPortEntry 2 }

        vlanStackPortPrio OBJECT-TYPE
        SYNTAX  INTEGER {
        		priority_0(0),
        		priority_1(1),
        		priority_2(2),
        		priority_3(3),
        		priority_4(4),
        		priority_5(5),
        		priority_6(6),
        		priority_7(7)
        }

        MAX-ACCESS  read-write
        STATUS  current
        DESCRIPTION
                      	"Priority value for service provider tag.
                      	0 is the lowest priority level and 7 is the highest."
        ::= { vlanStackPortEntry 3 }

        vlanStackTunnelPortTpid OBJECT-TYPE
        SYNTAX  INTEGER
        MAX-ACCESS  read-write
        STATUS  current
        DESCRIPTION
                      	"Tunnel Port TPID in hex format, e.g. 8100."
        ::= { vlanStackPortEntry 4 }

        vlanStackPCopyCtagPrio OBJECT-TYPE
        SYNTAX  EnabledStatus
        MAX-ACCESS  read-create
        STATUS  current
        DESCRIPTION
                      	""
        ::= { vlanStackPortEntry 5 }        

        
-- selectiveQinQTable
        selectiveQinQTable OBJECT-TYPE
        SYNTAX	SEQUENCE OF SelectiveQinQEntry
        MAX-ACCESS  not-accessible
        STATUS  current
        DESCRIPTION
                 	""
        ::= { vlanStackSetup 4 }
        
	selectiveQinQEntry OBJECT-TYPE
        SYNTAX	SelectiveQinQEntry
        MAX-ACCESS	not-accessible
        STATUS	current
        DESCRIPTION    	"An entry in selective qinq table"
        INDEX          	{ selectiveQinQPort, selectiveQinQCvid }
        ::= { selectiveQinQTable 1 }

        SelectiveQinQEntry ::=
           SEQUENCE {
           	selectiveQinQName		DisplayString,
        	selectiveQinQPort		INTEGER,
        	selectiveQinQCvid		INTEGER,
        	selectiveQinQSpvid		INTEGER,
        	selectiveQinQPriority	INTEGER,
        	selectiveQinQRowStatus	RowStatus,
		selectiveQinQACtivePrio		EnabledStatus
           }

        selectiveQinQName OBJECT-TYPE
        SYNTAX  DisplayString
        MAX-ACCESS  read-write
        STATUS  current
        DESCRIPTION
                      	"The name of selective qinq entry"
        ::= { selectiveQinQEntry 1 }

        selectiveQinQPort OBJECT-TYPE
        SYNTAX  INTEGER
        MAX-ACCESS  read-only
        STATUS  current
        DESCRIPTION
                     	"interface port id"
        ::= { selectiveQinQEntry 2 }

        selectiveQinQCvid OBJECT-TYPE
        SYNTAX  INTEGER
        MAX-ACCESS  read-only
        STATUS  current
        DESCRIPTION
                     	"inner vid"
        ::= { selectiveQinQEntry 3 }
        
        selectiveQinQSpvid OBJECT-TYPE
        SYNTAX  INTEGER
        MAX-ACCESS  read-write
        STATUS  current
        DESCRIPTION
                     	"outer vid"
        ::= { selectiveQinQEntry 4 }
        
        selectiveQinQPriority OBJECT-TYPE
        SYNTAX  INTEGER {
        		priority_0(0),
        		priority_1(1),
        		priority_2(2),
        		priority_3(3),
        		priority_4(4),
        		priority_5(5),
        		priority_6(6),
        		priority_7(7)
        }

        MAX-ACCESS  read-write
        STATUS  current
        DESCRIPTION
                     	"priority"
        ::= { selectiveQinQEntry 5 }

        selectiveQinQACtivePrio OBJECT-TYPE
        SYNTAX  EnabledStatus
        MAX-ACCESS  read-write
        STATUS  current
        DESCRIPTION
                     	"Use the value for priority for Stag"
        ::= { selectiveQinQEntry 7 }
        
        selectiveQinQRowStatus OBJECT-TYPE
        SYNTAX  RowStatus
        MAX-ACCESS  read-create
        STATUS  current
        DESCRIPTION
                     	""
        ::= { selectiveQinQEntry 6 }

-- PortBasedInnerQTable
        
        portBasedInnerQTable OBJECT-TYPE
        SYNTAX	SEQUENCE OF PortBasedInnerQEntry
        MAX-ACCESS  not-accessible
        STATUS  current
        DESCRIPTION
                 	""
        ::= { vlanStackSetup 5 }
        
	portBasedInnerQEntry OBJECT-TYPE
        SYNTAX	PortBasedInnerQEntry
        MAX-ACCESS	not-accessible
        STATUS	current
        DESCRIPTION    	"An entry in PortBasedInnerQTable."
        INDEX          	{ dot1dBasePort }
        ::= { portBasedInnerQTable 1 }

        PortBasedInnerQEntry ::=
           SEQUENCE {
        	portBasedInnerQVid			INTEGER,
        	portBasedInnerQPrio			INTEGER,
        	portBasedInnerQActive		EnabledStatus,
        	portBasedInnerQTxUntag		EnabledStatus
           }


        portBasedInnerQVid OBJECT-TYPE
        SYNTAX  INTEGER
        MAX-ACCESS  read-write
        STATUS  current
        DESCRIPTION
                      	"VLAN ID used in inner tag."
        ::= { portBasedInnerQEntry 1 }

        portBasedInnerQPrio OBJECT-TYPE
        SYNTAX  INTEGER {
        		priority_0(0),
        		priority_1(1),
        		priority_2(2),
        		priority_3(3),
        		priority_4(4),
        		priority_5(5),
        		priority_6(6),
        		priority_7(7)
        }
        
        MAX-ACCESS  read-write
        STATUS  current
        DESCRIPTION
                      	"Priority value for inner tag.  
                      	0 is the lowest priority level and 7 is the highest."
        ::= { portBasedInnerQEntry 2 }
        

        portBasedInnerQActive OBJECT-TYPE
        SYNTAX  EnabledStatus
        MAX-ACCESS  read-write
        STATUS  current
        DESCRIPTION
                      	""
        ::= { portBasedInnerQEntry 3 }
        
        portBasedInnerQTxUntag OBJECT-TYPE
        SYNTAX  EnabledStatus
        MAX-ACCESS  read-write
        STATUS  current
        DESCRIPTION
                      	"Tx without Ctag (Only active when innerQ is enable)"
        ::= { portBasedInnerQEntry 4 }

--  dot1xSetup
	dot1xSetup OBJECT IDENTIFIER ::= { ves1724-56fanless 8 }

--  portAuthState
        portAuthState OBJECT-TYPE
        SYNTAX  EnabledStatus
        MAX-ACCESS  read-write
        STATUS  current
        DESCRIPTION
                      	"802.1x port authentication enabled/disabled for the switch."
        ::= { dot1xSetup 3 }


-- 8021xPortAuthTable

        portAuthTable OBJECT-TYPE
        SYNTAX	SEQUENCE OF PortAuthEntry
        MAX-ACCESS  not-accessible
        STATUS  current
        DESCRIPTION
                 	""
        ::= { dot1xSetup 4 }

		portAuthEntry OBJECT-TYPE
        SYNTAX	PortAuthEntry
        MAX-ACCESS	not-accessible
        STATUS	current
        DESCRIPTION    	"An entry in portAuthTable."
        INDEX          	{ dot1dBasePort }
        ::= { portAuthTable 1 }

        PortAuthEntry ::=
           SEQUENCE {
        	portAuthEntryState	EnabledStatus,
        	portReAuthEntryState	EnabledStatus,
        	portReAuthEntryTimer	INTEGER
           }

        portAuthEntryState OBJECT-TYPE
        SYNTAX  EnabledStatus
        MAX-ACCESS  read-write
        STATUS  current
        DESCRIPTION
                      	"802.1x port authentication enabled or disabled on the port."
        ::= { portAuthEntry 1 }

        portReAuthEntryState OBJECT-TYPE
        SYNTAX  EnabledStatus
        MAX-ACCESS  read-write
        STATUS  current
        DESCRIPTION
                      	"802.1x port re-authentication enabled or disabled on the port."
        ::= { portAuthEntry 2 }

        portReAuthEntryTimer OBJECT-TYPE
        SYNTAX  INTEGER
        MAX-ACCESS  read-write
        STATUS  current
        DESCRIPTION
                      	"Re-authentication timer in seconds."
        ::= { portAuthEntry 3 }

-- hardwareInfo
	hwMonitorInfo OBJECT IDENTIFIER ::= { ves1724-56fanless 9 }

-- fabRpmTable

        fanRpmTable	OBJECT-TYPE
        SYNTAX	SEQUENCE OF FanRpmEntry
        MAX-ACCESS  not-accessible
        STATUS  current
        DESCRIPTION
                 	""
        ::= { hwMonitorInfo 1 }

	fanRpmEntry OBJECT-TYPE
        SYNTAX	FanRpmEntry
        MAX-ACCESS	not-accessible
        STATUS	current
        DESCRIPTION    	"An entry in fanRpmTable."
        INDEX          	{ fanRpmIndex }
        ::= { fanRpmTable 1 }

        FanRpmEntry ::=
           SEQUENCE {
        	fanRpmIndex	INTEGER,
        	fanRpmCurValue	INTEGER,
        	fanRpmMaxValue	INTEGER,
        	fanRpmMinValue	INTEGER,
        	fanRpmLowThresh	INTEGER,
        	fanRpmDescr	DisplayString
           }

        fanRpmIndex OBJECT-TYPE
        SYNTAX  INTEGER
        MAX-ACCESS  read-only
        STATUS  current
        DESCRIPTION
                      	"Index of FAN."
        ::= { fanRpmEntry 1 }

        fanRpmCurValue OBJECT-TYPE
        SYNTAX  INTEGER
        MAX-ACCESS  read-only
        STATUS  current
        DESCRIPTION
                      	"Current speed in Revolutions Per Minute (RPM) on the fan."
        ::= { fanRpmEntry 2 }

        fanRpmMaxValue OBJECT-TYPE
        SYNTAX  INTEGER
        MAX-ACCESS  read-only
        STATUS  current
        DESCRIPTION
                      	"Maximum speed measured in Revolutions Per Minute (RPM) on the fan."
        ::= { fanRpmEntry 3 }

        fanRpmMinValue OBJECT-TYPE
        SYNTAX  INTEGER
        MAX-ACCESS  read-only
        STATUS  current
        DESCRIPTION
                      	"Minimum speed measured in Revolutions Per Minute (RPM) on the fan."
        ::= { fanRpmEntry 4 }

        fanRpmLowThresh OBJECT-TYPE
        SYNTAX  INTEGER
        MAX-ACCESS  read-only
        STATUS  current
        DESCRIPTION
                      	"The minimum speed at which a normal fan should work."
        ::= { fanRpmEntry 5 }

        fanRpmDescr OBJECT-TYPE
        SYNTAX  DisplayString
        MAX-ACCESS  read-only
        STATUS  current
        DESCRIPTION
                      	"'Normal' indicates that this fan is functioning above the minimum speed.
                      	'Error' indicates that this fan is functioning below the minimum speed."
        ::= { fanRpmEntry 6 }

-- tempTable

        tempTable	OBJECT-TYPE
        SYNTAX	SEQUENCE OF TempEntry
        MAX-ACCESS  not-accessible
        STATUS  current
        DESCRIPTION
                 	""
        ::= { hwMonitorInfo 2 }

	tempEntry OBJECT-TYPE
        SYNTAX	TempEntry
        MAX-ACCESS	not-accessible
        STATUS	current
        DESCRIPTION    	"An entry in tempTable."
        INDEX          	{ tempIndex }
        ::= { tempTable 1 }

        TempEntry ::=
           SEQUENCE {
        	tempIndex	INTEGER,
        	tempCurValue	INTEGER,
        	tempMaxValue	INTEGER,
        	tempMinValue	INTEGER,
        	tempHighThresh	INTEGER,
        	tempDescr	DisplayString
           }

        tempIndex OBJECT-TYPE
        SYNTAX  INTEGER {
        	mac (1),
        	cpu (2),
        	phy (3)
        }
        MAX-ACCESS  read-only
        STATUS  current
        DESCRIPTION
                      	"Index of temperature unit. 1:MAC, 2:CPU, 3:PHY"
        ::= { tempEntry 1 }

        tempCurValue OBJECT-TYPE
        SYNTAX  INTEGER
        MAX-ACCESS  read-only
        STATUS  current
        DESCRIPTION
                      	"The current temperature measured at this sensor."
        ::= { tempEntry 2 }

        tempMaxValue OBJECT-TYPE
        SYNTAX  INTEGER
        MAX-ACCESS  read-only
        STATUS  current
        DESCRIPTION
                      	"The maximum temperature measured at this sensor."
        ::= { tempEntry 3 }

        tempMinValue OBJECT-TYPE
        SYNTAX  INTEGER
        MAX-ACCESS  read-only
        STATUS  current
        DESCRIPTION
                      	"The minimum temperature measured at this sensor."
        ::= { tempEntry 4 }

        tempHighThresh OBJECT-TYPE
        SYNTAX  INTEGER
        MAX-ACCESS  read-only
        STATUS  current
        DESCRIPTION
                      	"The upper temperature limit at this sensor."
        ::= { tempEntry 5 }

        tempDescr OBJECT-TYPE
        SYNTAX  DisplayString
        MAX-ACCESS  read-only
        STATUS  current
        DESCRIPTION
                      	"'Normal' indicates temperatures below the threshold and 'Error' for those above."
        ::= { tempEntry 6 }

-- voltageTable

        voltageTable	OBJECT-TYPE
        SYNTAX	SEQUENCE OF VoltageEntry
        MAX-ACCESS  not-accessible
        STATUS  current
        DESCRIPTION
                 	""
        ::= { hwMonitorInfo 3 }

	voltageEntry OBJECT-TYPE
        SYNTAX	VoltageEntry
        MAX-ACCESS	not-accessible
        STATUS	current
        DESCRIPTION    	"An entry in voltageTable."
        INDEX          	{ voltageIndex }
        ::= { voltageTable 1 }

        VoltageEntry ::=
           SEQUENCE {
        	voltageIndex		INTEGER,
        	voltageCurValue		INTEGER,
        	voltageMaxValue		INTEGER,
        	voltageMinValue		INTEGER,
        	voltageNominalValue	INTEGER,
        	voltageLowThresh	INTEGER,
        	voltageDescr		DisplayString
           }

        voltageIndex OBJECT-TYPE
        SYNTAX  INTEGER {
        	vin14(1),
        	vs2_5(2),
        	cpu_dsp_afe(3)
        }        
        MAX-ACCESS  read-only
        STATUS  current
        DESCRIPTION
                      	"Index of voltage. (1) 14VIN (2) 2.5VS (3) CPU/DSP/AFE"
        ::= { voltageEntry 1 }

        voltageCurValue OBJECT-TYPE
        SYNTAX  INTEGER
        MAX-ACCESS  read-only
        STATUS  current
        DESCRIPTION
                      	"The current voltage reading."
        ::= { voltageEntry 2 }

        voltageMaxValue OBJECT-TYPE
        SYNTAX  INTEGER
        MAX-ACCESS  read-only
        STATUS  current
        DESCRIPTION
                      	"The maximum voltage measured at this point."
        ::= { voltageEntry 3 }

        voltageMinValue OBJECT-TYPE
        SYNTAX  INTEGER
        MAX-ACCESS  read-only
        STATUS  current
        DESCRIPTION
                      	"The minimum voltage measured at this point."
        ::= { voltageEntry 4 }

        voltageNominalValue OBJECT-TYPE
        SYNTAX  INTEGER
        MAX-ACCESS  read-only
        STATUS  current
        DESCRIPTION
                      	"The normal voltage at wchich the switch work."
        ::= { voltageEntry 5 }

        voltageLowThresh OBJECT-TYPE
        SYNTAX  INTEGER
        MAX-ACCESS  read-only
        STATUS  current
        DESCRIPTION
                      	"The minimum voltage at which the switch should work."
        ::= { voltageEntry 6 }

        voltageDescr OBJECT-TYPE
        SYNTAX  DisplayString
        MAX-ACCESS  read-only
        STATUS  current
        DESCRIPTION
                      	"'Normal' indicates that the voltage is within an acceptable operating range
                      	at this point; otherwise 'Error' is displayed."
        ::= { voltageEntry 7 }

-- snmpSetup
	snmpSetup OBJECT IDENTIFIER ::= { ves1724-56fanless 10 }

        snmpGetCommunity OBJECT-TYPE
        SYNTAX  DisplayString
        MAX-ACCESS  read-write
        STATUS  current
        DESCRIPTION
                      	""
        ::= { snmpSetup 1 }

        snmpSetCommunity OBJECT-TYPE
        SYNTAX  DisplayString
        MAX-ACCESS  read-write
        STATUS  current
        DESCRIPTION
                      	""
        ::= { snmpSetup 2 }

        snmpTrapCommunity OBJECT-TYPE
        SYNTAX  DisplayString
        MAX-ACCESS  read-write
        STATUS  current
        DESCRIPTION
                      	""
        ::= { snmpSetup 3 }

--  snmpTrapDestTable
        snmpTrapDestTable	OBJECT-TYPE
        SYNTAX	SEQUENCE OF SnmpTrapDestEntry
        MAX-ACCESS  not-accessible
        STATUS  current
        DESCRIPTION
                 	""
        ::= { snmpSetup 4 }

	snmpTrapDestEntry OBJECT-TYPE
        SYNTAX	SnmpTrapDestEntry
        MAX-ACCESS	not-accessible
        STATUS	current
        DESCRIPTION    	"An entry in snmpTrapDestTable."
        INDEX          	{ snmpTrapDestIP }
        ::= { snmpTrapDestTable 1 }

        SnmpTrapDestEntry ::=
           SEQUENCE {
        	snmpTrapDestIP	IpAddress,
        	snmpTrapDestRowStatus RowStatus,
        	snmpTrapDestPort		INTEGER,
        	snmpTrapVersion			INTEGER,
        	snmpTrapUserName		DisplayString  
           }

        snmpTrapDestIP OBJECT-TYPE
        SYNTAX  IpAddress
        MAX-ACCESS  read-only
        STATUS  current
        DESCRIPTION
                      	"IP address of trap destination."
        ::= { snmpTrapDestEntry 1 }

        snmpTrapDestRowStatus OBJECT-TYPE
        SYNTAX  RowStatus
        MAX-ACCESS  read-create
        STATUS  current
        DESCRIPTION
                      	""
        ::= { snmpTrapDestEntry 2 }

        snmpTrapDestPort OBJECT-TYPE
        SYNTAX INTEGER
        MAX-ACCESS read-write
        STATUS  current
        DESCRIPTION
                      	"The UDP port of the trap destination."
        ::= { snmpTrapDestEntry 3 }
        
        snmpTrapVersion OBJECT-TYPE
        SYNTAX  INTEGER {
			v1(0),
			v2c(1),
			v3(2)
		}
        MAX-ACCESS read-write
        STATUS  current
        DESCRIPTION
                      	"The SNMP protocol version to send traps."
        ::= { snmpTrapDestEntry 4 }

        snmpTrapUserName OBJECT-TYPE
        SYNTAX DisplayString
        MAX-ACCESS read-write
        STATUS  current
        DESCRIPTION
                      	"The user name for sending SNMPv3 traps."
        ::= { snmpTrapDestEntry 5 }   

--  snmpTrapGroupTable
        snmpTrapGroupTable	OBJECT-TYPE
        SYNTAX	SEQUENCE OF SnmpTrapGroupEntry
        MAX-ACCESS  not-accessible
        STATUS  current
        DESCRIPTION
                 	""
        ::= { snmpSetup 5 }
	snmpTrapGroupEntry OBJECT-TYPE
        SYNTAX	SnmpTrapGroupEntry
        MAX-ACCESS	not-accessible
        STATUS	current
        DESCRIPTION    	"An entry in snmpTrapGroupTable."
        INDEX          	{ snmpTrapDestIP }
        ::= { snmpTrapGroupTable 1 }

        SnmpTrapGroupEntry ::=
           SEQUENCE {
        	snmpTrapSystemGroup	 BITS,
        	snmpTrapInterfaceGroup	 BITS,
        	snmpTrapAAAGroup  BITS,
        	snmpTrapSwitchGroup	 BITS,
        	snmpTrapVdslGroup	 BITS
           }

        snmpTrapSystemGroup OBJECT-TYPE
        	SYNTAX	BITS {
		coldStart(0),
		warmStart(1),
--		fanSpeed(2),
		temperature(3),
		voltage(4),
		reset (5),
--		timeSync (6),
		externalalarm(7),
--		instrusionlock (8),
		loopguard (9),
		lpr (10),
		hwInformation (11),
		rxcrc (16),
		errdisable (17)
	}
        MAX-ACCESS  read-write
        STATUS  current
        DESCRIPTION
                      	""
        ::= { snmpTrapGroupEntry 1 }
        
        snmpTrapInterfaceGroup OBJECT-TYPE
               	SYNTAX	BITS {
		linkup(0),
		linkdown(1),
		autonegotiation(2),
		sfp(4)
	}
        MAX-ACCESS  read-write
        STATUS  current
        DESCRIPTION
                      	""
        ::= { snmpTrapGroupEntry 2 }
        
        snmpTrapAAAGroup OBJECT-TYPE
               	SYNTAX	BITS {
		authentication(0),
		accounting(1)  
	}
        MAX-ACCESS  read-write
        STATUS  current
        DESCRIPTION
                      	""
        ::= { snmpTrapGroupEntry 3 }        
        
        
        snmpTrapSwitchGroup OBJECT-TYPE
               	SYNTAX	BITS {
		stp(0),
		mactable(1),
		rmon(2)
	}
        MAX-ACCESS  read-write
        STATUS  current
        DESCRIPTION
                      	""
        ::= { snmpTrapGroupEntry 5 }       
        
        snmpTrapVdslGroup OBJECT-TYPE
               	SYNTAX	BITS {
		alarmprofile(0),
		others(1)
	}
        MAX-ACCESS  read-write
        STATUS  current
        DESCRIPTION
                      	""
        ::= { snmpTrapGroupEntry 6 } 

--snmpVersion
        snmpVersion OBJECT-TYPE
		SYNTAX 	INTEGER {
			v2c(0),
			v3(1),
			v3v2c(2)
		}
        MAX-ACCESS  read-write
        STATUS  current
        DESCRIPTION
		"The SNMP version to be used. v3v2c means that the manager 
		can get/set by SNMPv3 and can get by SNMPv2c."
        ::= { snmpSetup 6 }

-- snmpUserTable
	
	snmpUserTable OBJECT-TYPE
    	SYNTAX SEQUENCE OF SnmpUserEntry
    	MAX-ACCESS not-accessible
    	STATUS current
    	DESCRIPTION
                "A table that contains SNMPv3 user information."
    	::= { snmpSetup 7 }

    	snmpUserEntry OBJECT-TYPE
        SYNTAX SnmpUserEntry
        MAX-ACCESS not-accessible
        STATUS current
        DESCRIPTION
        	"An entry of snmpUserTable."
        INDEX { snmpUserName }
        ::= { snmpUserTable 1 }

   	SnmpUserEntry ::=
        	SEQUENCE {
            		snmpUserName		DisplayString,
            		snmpUserSecurityLevel	INTEGER,
            		snmpUserAuthProtocol	INTEGER,
            		snmpUserPrivProtocol	INTEGER
    	   	} 

	snmpUserName OBJECT-TYPE
	SYNTAX DisplayString
	MAX-ACCESS read-only
	STATUS current
	DESCRIPTION
		"The user name."
	::= { snmpUserEntry 1 }

	snmpUserSecurityLevel OBJECT-TYPE
	SYNTAX  INTEGER {
			noAuthNoPriv(0),
			authNoPriv(1),
			authPriv(2)
		}
	MAX-ACCESS read-write
	STATUS current
	DESCRIPTION
		"The level of security at which SNMP messages can be sent or 
		with which operations are being processed."
	::= { snmpUserEntry 2 }	

	snmpUserAuthProtocol OBJECT-TYPE
	SYNTAX  INTEGER {
			md5(0),
			sha(1)
		}
	MAX-ACCESS read-write
	STATUS current
	DESCRIPTION
		"The type of authentication protocol to be used."
	::= { snmpUserEntry 3 }

	snmpUserPrivProtocol OBJECT-TYPE
	SYNTAX 	INTEGER {
			des(0),
			aes(1)
		}
	MAX-ACCESS read-write
	STATUS current
	DESCRIPTION
		"The type of privacy protocol to be used."
	::= { snmpUserEntry 4 }

--  snmpTrapDestInfoTable
    snmpTrapDestInfoTable	OBJECT-TYPE
        SYNTAX	SEQUENCE OF SnmpTrapDestInfoEntry
        MAX-ACCESS  not-accessible
        STATUS  current
        DESCRIPTION
                 	""
        ::= { snmpSetup 8 }
           
	snmpTrapDestInfoEntry OBJECT-TYPE
        SYNTAX	SnmpTrapDestInfoEntry
        MAX-ACCESS	not-accessible
        STATUS	current
        DESCRIPTION    	"An entry in snmpTrapDestInfoTable."
        INDEX          	{ snmpTrapDestInfoIpAddrType, snmpTrapDestInfoIpAddr }
        ::= { snmpTrapDestInfoTable 1 }

        SnmpTrapDestInfoEntry ::=
            SEQUENCE {
           		snmpTrapDestInfoIpAddrType	InetAddressType,
        		snmpTrapDestInfoIpAddr		InetAddress,
        		snmpTrapDestInfoRowStatus	RowStatus,
        		snmpTrapDestInfoPort		INTEGER,
        		snmpTrapDestInfoVersion		INTEGER,
        		snmpTrapDestInfoUserName	DisplayString  
			}
        
        snmpTrapDestInfoIpAddrType OBJECT-TYPE
        SYNTAX  InetAddressType { ipv4(1), ipv6(2) }
        MAX-ACCESS  read-only
        STATUS  current
        DESCRIPTION
                      	"IP address of trap destination."
        ::= { snmpTrapDestInfoEntry 1 }
           
        snmpTrapDestInfoIpAddr OBJECT-TYPE
        SYNTAX  InetAddress
        MAX-ACCESS  read-only
        STATUS  current
        DESCRIPTION
                      	"IP address of trap destination."
        ::= { snmpTrapDestInfoEntry 2 }

        snmpTrapDestInfoRowStatus OBJECT-TYPE
        SYNTAX  RowStatus
        MAX-ACCESS  read-create
        STATUS  current
        DESCRIPTION
                      	""
        ::= { snmpTrapDestInfoEntry 3 }
           
        snmpTrapDestInfoPort OBJECT-TYPE
        SYNTAX INTEGER
        MAX-ACCESS read-write
        STATUS  current
        DESCRIPTION
                      	"The UDP port of the trap destination."
        ::= { snmpTrapDestInfoEntry 4 }
           
        snmpTrapDestInfoVersion OBJECT-TYPE
        SYNTAX  INTEGER {
			v1(0),
			v2c(1),
			v3(2)
		}
        MAX-ACCESS read-write
        STATUS  current
        DESCRIPTION
                      	"The SNMP protocol version to send traps."
        ::= { snmpTrapDestInfoEntry 5 }

        snmpTrapDestInfoUserName OBJECT-TYPE
        SYNTAX DisplayString
        MAX-ACCESS read-write
        STATUS  current
        DESCRIPTION
                      	"The user name for sending SNMPv3 traps."
        ::= { snmpTrapDestInfoEntry 6 }           

--  snmpTrapGroupInfoTable
        snmpTrapGroupInfoTable	OBJECT-TYPE
        SYNTAX	SEQUENCE OF SnmpTrapGroupInfoEntry
        MAX-ACCESS  not-accessible
        STATUS  current
        DESCRIPTION
                 	""
        ::= { snmpSetup 9 }

	snmpTrapGroupInfoEntry OBJECT-TYPE
        SYNTAX	SnmpTrapGroupInfoEntry
        MAX-ACCESS	not-accessible
        STATUS	current
        DESCRIPTION    	"An entry in snmpTrapGroupInfoTable."
        INDEX          	{ snmpTrapDestInfoIpAddrType, snmpTrapDestInfoIpAddr }
        ::= { snmpTrapGroupInfoTable 1 }

        SnmpTrapGroupInfoEntry ::=
           SEQUENCE {
        	snmpTrapGroupInfoSystemGroup	 BITS,
        	snmpTrapGroupInfoInterfaceGroup	 BITS,
        	snmpTrapGroupInfoAAAGroup  BITS,
        	snmpTrapGroupInfoSwitchGroup	 BITS,
        	snmpTrapGroupInfoVdslGroup	 BITS
           }

        snmpTrapGroupInfoSystemGroup OBJECT-TYPE
        	SYNTAX	BITS {
		coldStart(0),
		warmStart(1),
--		fanSpeed(2),
		temperature(3),
		voltage(4),
		reset (5),
--		timeSync (6),
		externalalarm(7),
--		instrusionlock (8),
		loopguard (9),
		lpr (10),
		hwInformation (11),
		rxcrc (16),
		errdisable (17)
	}
        MAX-ACCESS  read-write
        STATUS  current
        DESCRIPTION
                      	""
        ::= { snmpTrapGroupInfoEntry 1 }
        
        snmpTrapGroupInfoInterfaceGroup OBJECT-TYPE
               	SYNTAX	BITS {
		linkup(0),
		linkdown(1),
		autonegotiation(2),
		sfp(4)
	}
        MAX-ACCESS  read-write
        STATUS  current
        DESCRIPTION
                      	""
        ::= { snmpTrapGroupInfoEntry 2 }
           
        snmpTrapGroupInfoAAAGroup OBJECT-TYPE
               	SYNTAX	BITS {
		authentication(0),
		accounting(1)  
	}
        MAX-ACCESS  read-write
        STATUS  current
        DESCRIPTION
                      	""
        ::= { snmpTrapGroupInfoEntry 3 }        
           

        snmpTrapGroupInfoSwitchGroup OBJECT-TYPE
               	SYNTAX	BITS {
		stp(0),
		mactable(1),
		rmon(2)
	}
        MAX-ACCESS  read-write
        STATUS  current
        DESCRIPTION
                      	""
        ::= { snmpTrapGroupInfoEntry 5 }       

        snmpTrapGroupInfoVdslGroup OBJECT-TYPE
               	SYNTAX	BITS {
		alarmprofile(0),
		others(1)
	}
        MAX-ACCESS  read-write
        STATUS  current
        DESCRIPTION
                      	""
        ::= { snmpTrapGroupInfoEntry 6 }         

--  dateTimeServerSetup
	dateTimeServerSetup     	OBJECT IDENTIFIER ::= { ves1724-56fanless 11 }

        dateTimeServerType OBJECT-TYPE
        SYNTAX  INTEGER {
        		none(1),
			daytime(2),
			time(3),
			ntp(4)
        }
        MAX-ACCESS  read-write
        STATUS  current
        DESCRIPTION
                      "The time service protocol."
        ::= { dateTimeServerSetup 1 }

        dateTimeServerIP OBJECT-TYPE
        SYNTAX  IpAddress
        MAX-ACCESS  read-write
        STATUS  current
        DESCRIPTION
                      "IP address of time server, IPv4 only."
        ::= { dateTimeServerSetup 2 }

        dateTimeZone OBJECT-TYPE
        SYNTAX  INTEGER
        MAX-ACCESS  read-write
        STATUS  current
        DESCRIPTION
                      "The time difference between UTC. Ex: +01"
        ::= { dateTimeServerSetup 3 }

        dateTimeNewDateYear OBJECT-TYPE
        SYNTAX  INTEGER
        MAX-ACCESS  read-write
        STATUS  current
        DESCRIPTION
                      "The new date in year."
        ::= { dateTimeServerSetup 4 }

        dateTimeNewDateMonth OBJECT-TYPE
        SYNTAX  INTEGER
        MAX-ACCESS  read-write
        STATUS  current
        DESCRIPTION
                      "The new date in month."
        ::= { dateTimeServerSetup 5 }

        dateTimeNewDateDay OBJECT-TYPE
        SYNTAX  INTEGER
        MAX-ACCESS  read-write
        STATUS  current
        DESCRIPTION
                      "The new date in day."
        ::= { dateTimeServerSetup 6 }

        dateTimeNewTimeHour OBJECT-TYPE
        SYNTAX  INTEGER
        MAX-ACCESS  read-write
        STATUS  current
        DESCRIPTION
                      "The new time in hour."
        ::= { dateTimeServerSetup 7 }

        dateTimeNewTimeMinute OBJECT-TYPE
        SYNTAX  INTEGER
        MAX-ACCESS  read-write
        STATUS  current
        DESCRIPTION
                      "The new time in minute."
        ::= { dateTimeServerSetup 8 }

        dateTimeNewTimeSecond OBJECT-TYPE
        SYNTAX  INTEGER
        MAX-ACCESS  read-write
        STATUS  current
        DESCRIPTION
                      "The new time in second."
        ::= { dateTimeServerSetup 9 }

-- dateTimeDaylightSavingTimeSetup OBJECT-TYPE
	dateTimeDaylightSavingTimeSetup     	OBJECT IDENTIFIER ::= { dateTimeServerSetup 10 }
	
        daylightSavingTimeState OBJECT-TYPE
        SYNTAX  EnabledStatus
        MAX-ACCESS  read-write
        STATUS  current
        DESCRIPTION
                      "Daylight saving time service enabled/disabled for the switch."
        ::= { dateTimeDaylightSavingTimeSetup 1 }

        daylightSavingTimeStartDateWeek OBJECT-TYPE
        SYNTAX  INTEGER {
         		first(1),
         		second(2),
         		third(3),
         		fourth(4),
         		last(5)
        }
        MAX-ACCESS  read-write
        STATUS  current
        DESCRIPTION
                      "Daylight saving time service start week."
        ::= { dateTimeDaylightSavingTimeSetup 2 }

        daylightSavingTimeStartDateDay OBJECT-TYPE
        SYNTAX  INTEGER {
         		sunday(0),
         		monday(1),
         		tuesday(2),
         		wednesday(3),
         		thursday(4),
         		friday(5),
         		saturday(6)         		
        }
        MAX-ACCESS  read-write
        STATUS  current
        DESCRIPTION
                      "Daylight saving time service start day."
        ::= { dateTimeDaylightSavingTimeSetup 3 }

        daylightSavingTimeStartDateMonth OBJECT-TYPE
        SYNTAX  INTEGER {
         		january(1),
         		february(2),
         		march(3),
         		april(4),
         		may(5),
         		june(6),
         		july(7),
         		august(8),
         		september(9),
         		october(10),
         		november(11),
         		december(12)
        }
        MAX-ACCESS  read-write
        STATUS  current
        DESCRIPTION
                      "Daylight saving time service start month."
        ::= { dateTimeDaylightSavingTimeSetup 4 }

        daylightSavingTimeStartDateHour OBJECT-TYPE
        SYNTAX  INTEGER 
        MAX-ACCESS  read-write
        STATUS  current
        DESCRIPTION
                      "Daylight saving time service start time."
        ::= { dateTimeDaylightSavingTimeSetup 5 }

        daylightSavingTimeEndDateWeek OBJECT-TYPE
        SYNTAX  INTEGER {
         		first(1),
         		second(2),
         		third(3),
         		fourth(4),
         		last(5)
        }
        MAX-ACCESS  read-write
        STATUS  current
        DESCRIPTION
                      "Daylight saving time service end week."
        ::= { dateTimeDaylightSavingTimeSetup 6 }

        daylightSavingTimeEndDateDay OBJECT-TYPE
        SYNTAX  INTEGER {
         		sunday(0),
         		monday(1),
         		tuesday(2),
         		wednesday(3),
         		thursday(4),
         		friday(5),
         		saturday(6)         		
        }
        MAX-ACCESS  read-write
        STATUS  current
        DESCRIPTION
                      "Daylight saving time service end day."
        ::= { dateTimeDaylightSavingTimeSetup 7 }

        daylightSavingTimeEndDateMonth OBJECT-TYPE
        SYNTAX  INTEGER {
         		january(1),
         		february(2),
         		march(3),
         		april(4),
         		may(5),
         		june(6),
         		july(7),
         		august(8),
         		september(9),
         		october(10),
         		november(11),
         		december(12)
        }
        MAX-ACCESS  read-write
        STATUS  current
        DESCRIPTION
                      "Daylight saving time service end month."
        ::= { dateTimeDaylightSavingTimeSetup 8 }

        daylightSavingTimeEndDateHour OBJECT-TYPE
        SYNTAX  INTEGER 
        MAX-ACCESS  read-write
        STATUS  current
        DESCRIPTION
                      "Daylight saving time service end time."
        ::= { dateTimeDaylightSavingTimeSetup 9 }
    
        dateTimeServerIPAddrType OBJECT-TYPE
        SYNTAX  InetAddressType { ipv4(1), ipv6(2) }
        MAX-ACCESS  read-write
        STATUS  current
        DESCRIPTION
                      "The address type of dateTimeServerIPAddr."
        ::= { dateTimeServerSetup 11 }
        
        dateTimeServerIPAddr OBJECT-TYPE
        SYNTAX  InetAddress
        MAX-ACCESS  read-write
        STATUS  current
        DESCRIPTION
                      "The IP address of time server."
        ::= { dateTimeServerSetup 12 }
    
--  sysMgmt
	sysMgmt     	OBJECT IDENTIFIER ::= { ves1724-56fanless 12 }

        sysMgmtConfigSave OBJECT-TYPE
        SYNTAX  INTEGER {
         		config_1(1),
         		config_2(2)
        }
        MAX-ACCESS  read-write
        STATUS  current
        DESCRIPTION
                      "If setting value is given, the variable write index will be set and running-config will be written to the assigned configuration file.
                      If not, running-config will be written to the booting one."
        ::= { sysMgmt 1 }

        sysMgmtBootupConfig OBJECT-TYPE
        SYNTAX  INTEGER {
         		config_1(1),
         		config_2(2)
        }
        MAX-ACCESS  read-write
        STATUS  current
        DESCRIPTION
                      "The setting value (read index) will be written into non-volatile memory.
                      While rebooting, the variable write index is equal to read index initially.
                      You can change the value of write index by CLI / MIB."
        ::= { sysMgmt 2 }

        sysMgmtReboot OBJECT-TYPE
        SYNTAX  INTEGER {
        		nothing(0),
        		reboot(1),
				warmstart(2)
        }
        MAX-ACCESS  read-write
        STATUS  current
        DESCRIPTION
                      "Reboot switch from SNMP. 1:Reboot, 0:Nothing, 2:Warmstart"
        ::= { sysMgmt 3 }

	sysMgmtDefaultConfig OBJECT-TYPE
        SYNTAX  INTEGER {
        		nothing(0),
        		reset_to_default(1),
        		reset_to_default_keep_ip(2)
        }
        MAX-ACCESS  read-write
        STATUS  current
        DESCRIPTION
                      "Erase running config and reset to default."
        ::= { sysMgmt 4 }

	sysMgmtLastActionStatus OBJECT-TYPE
        SYNTAX  INTEGER {
        		none(0),
        		success(1),
        		fail(2)
        }
        MAX-ACCESS  read-only
        STATUS  current
        DESCRIPTION
                      "Display status of last mgmt action."
        ::= { sysMgmt 5 }

	sysMgmtSystemStatus OBJECT-TYPE
	SYNTAX	BITS {
		sysAlarmDetected(0),
		sysTemperatureError(1),
		sysFanRPMError(2),
		sysVoltageRangeError(3),
		sysExternalAlarm(4)
	}
        MAX-ACCESS  read-only
        STATUS  current
        DESCRIPTION
		"This variable indicates the status of the system.
 		The sysMgmtAlarmStatus is a bit map represented
 		a sum, therefore, it can represent multiple defects
 		simultaneously. The sysNoDefect should be set if and only if
 		no other flag is set.

	 	The various bit positions are:
			0   sysAlarmDetected
			1   sysTemperatureError
			2   sysFanRPMError
			3   sysVoltageRangeError
			4   sysExternalAlarm"
        ::= { sysMgmt 6 }

	sysMgmtCPUUsage OBJECT-TYPE
		SYNTAX  INTEGER
		MAX-ACCESS  read-only
		STATUS  current
		DESCRIPTION
			"Show device CPU load in %, it's the snapshot of CPU load when
			getting the values."
		::= { sysMgmt 7 }

	sysMgmtBootupImage OBJECT-TYPE
        SYNTAX  INTEGER {
         		image_1(1),
         		image_2(2)
        }
        MAX-ACCESS  read-write
        STATUS  current
        DESCRIPTION
                      "The setting value (read index) will be written into non-volatile memory.
                      When rebooting, the selected image will be used.
                      You can change the value of write index by CLI / MIB."
        ::= { sysMgmt 8 }

	sysMgmtCounterReset OBJECT-TYPE
        SYNTAX  INTEGER {
         		enable(1),
         		disable(2)
        }
        MAX-ACCESS  read-write
        STATUS  current
        DESCRIPTION
                      "Reset all port counters."
        ::= { sysMgmt 9 }

-- Tftp service                                                      
        sysMgmtTftpServiceSetup OBJECT IDENTIFIER ::= { sysMgmt 10 }                      

        sysMgmtTftpServerIp OBJECT-TYPE
        SYNTAX  IpAddress
        MAX-ACCESS  read-write
        STATUS  current
        DESCRIPTION
                      	" IP address of TFTP server"
        ::= { sysMgmtTftpServiceSetup 1 }
        
        sysMgmtTftpRemoteFileName OBJECT-TYPE
        SYNTAX  DisplayString
        MAX-ACCESS  read-write
        STATUS  current
        DESCRIPTION
                      	"The file name that you want to backup to or restore from TFTP server"
        ::= { sysMgmtTftpServiceSetup 2 }     
        
        sysMgmtTftpConfigIndex OBJECT-TYPE
        SYNTAX  INTEGER {
        	    config1(1),
        	    config2(2)
        }
        MAX-ACCESS  read-write
        STATUS  current
        DESCRIPTION
                      	"Index of system configuration which you want to restore."
        ::= { sysMgmtTftpServiceSetup 3 }               
                               
        sysMgmtTftpAction OBJECT-TYPE
        SYNTAX  INTEGER {         
        		none(0),
         		backup_config(1),
         		restore_config(2)       		
        }
        MAX-ACCESS  read-write
        STATUS  current        
                DESCRIPTION
                      	" Action of tftp service. 1: Backup running-config to tftp server, 2: Restore config from tftp server."
        ::= { sysMgmtTftpServiceSetup 4 }
        
	sysMgmtTftpActionStatus OBJECT-TYPE
        SYNTAX  INTEGER {
        		none(0),
        		success(1),
        		fail(2),
        		under_action(3)
        }
        MAX-ACCESS  read-only
        STATUS  current
        DESCRIPTION
                      "Display status of mgmt action."
        ::= { sysMgmtTftpServiceSetup 5 }   
        
	sysMgmtTftpActionErrorInfo OBJECT-TYPE
        SYNTAX  DisplayString
        MAX-ACCESS  read-only
        STATUS  current
        DESCRIPTION
                      "Display error information of mgmt action."
        ::= { sysMgmtTftpServiceSetup 6 }                 	
        
        sysMgmtTftpServerAddressType OBJECT-TYPE
        SYNTAX  InetAddressType { ipv4(1), ipv6(2) }
        MAX-ACCESS  read-write
        STATUS  current
        DESCRIPTION
              "The address type of the sysMgmtTftpServerAddress entry."
        ::= { sysMgmtTftpServiceSetup 7 }                 	

        sysMgmtTftpServerAddress OBJECT-TYPE
        SYNTAX  InetAddress (SIZE(4|16))
        MAX-ACCESS  read-write
        STATUS  current
        DESCRIPTION
                      	"IPv4/IPv6 address of TFTP server"
        ::= { sysMgmtTftpServiceSetup 8 }                 	
        
-- Remote FW upgrade
	sysMgmtRmtFwUpgradeSetup OBJECT IDENTIFIER ::= { sysMgmt 11 }  
	
	sysMgmtRmtFwUpgradeOp OBJECT-TYPE
        SYNTAX INTEGER {
        	    idle(1),
        	    upgrade(2)
        }
        MAX-ACCESS  read-write
        STATUS  current
        DESCRIPTION
                      	"Specify remote FW upgrade operation"
        ::= { sysMgmtRmtFwUpgradeSetup 1 }
        
        sysMgmtRmtFwUpgradeTarget OBJECT-TYPE
        SYNTAX  PortList
        MAX-ACCESS  read-write
        STATUS  current
        DESCRIPTION
                      	"Specify remote FW upgrade target CPEs"
        ::= { sysMgmtRmtFwUpgradeSetup 2 }    
                
        -- sysMgmtRmtFwUpgradeStatus
		sysMgmtRmtFwUpgradeStatus     	OBJECT IDENTIFIER ::= { sysMgmtRmtFwUpgradeSetup 3 }

	-- rmtFwUpgradeStatusTable

        rmtFwUpgradeStatusTable OBJECT-TYPE
        SYNTAX	SEQUENCE OF RmtFwUpgradeStatusEntry
        MAX-ACCESS  not-accessible
        STATUS  current
        DESCRIPTION
                 	""
        ::= { sysMgmtRmtFwUpgradeStatus 1 }

	rmtFwUpgradeStatusEntry OBJECT-TYPE
        SYNTAX	RmtFwUpgradeStatusEntry
        MAX-ACCESS	not-accessible
        STATUS	current
        DESCRIPTION    	"An entry in rmtFwUpgradeStatusTable."
        INDEX          	{ dot1dBasePort }
        ::= { rmtFwUpgradeStatusTable 1 }

        RmtFwUpgradeStatusEntry ::=
        SEQUENCE {
        	rmtFwUpgradeStatus	INTEGER
        }

        rmtFwUpgradeStatus OBJECT-TYPE
        SYNTAX INTEGER {
        	    idle(1),
        	    upgrading(2),
        	    success(3),
        	    fail(4)
        }
        MAX-ACCESS  read-only
        STATUS  current
        DESCRIPTION
                      	""
        ::= { rmtFwUpgradeStatusEntry 1 }                                                                   

        -- sysMgmtRmtFwStatus
	sysMgmtRmtFwScheduleUpgrade     	OBJECT IDENTIFIER ::= { sysMgmtRmtFwUpgradeSetup 4 }

	sysMgmtRmtFwModel OBJECT-TYPE
        SYNTAX  DisplayString
        MAX-ACCESS  read-write
        STATUS  current
        DESCRIPTION
                      	"FW model for upgrade periodically"
        ::= { sysMgmtRmtFwScheduleUpgrade 1 }
        
        sysMgmtRmtFwVersion OBJECT-TYPE
        SYNTAX  DisplayString
        MAX-ACCESS  read-write
        STATUS  current
        DESCRIPTION
                      	"FW version for upgrade periodically"
        ::= { sysMgmtRmtFwScheduleUpgrade 2 }    

	-- rmtFwStatusTable

        rmtFwStatusTable OBJECT-TYPE
        SYNTAX	SEQUENCE OF RmtFwStatusEntry
        MAX-ACCESS  not-accessible
        STATUS  current
        DESCRIPTION
                 	""
        ::= { sysMgmtRmtFwScheduleUpgrade 3 }

	rmtFwStatusEntry OBJECT-TYPE
        SYNTAX	RmtFwStatusEntry
        MAX-ACCESS	not-accessible
        STATUS	current
        DESCRIPTION    	"An entry in rmtFwStatusTable."
        INDEX          	{ dot1dBasePort }
        ::= { rmtFwStatusTable 1 }

        RmtFwStatusEntry ::=
        SEQUENCE {
        	rmtFwStatus	DisplayString
        }

        rmtFwStatus OBJECT-TYPE
        SYNTAX  DisplayString
        MAX-ACCESS  read-only
        STATUS  current
        DESCRIPTION
                      	""
        ::= { rmtFwStatusEntry 1 }                                                                   

	sysMgmtPacketBufferUsage OBJECT-TYPE
		SYNTAX  INTEGER
		MAX-ACCESS  read-only
		STATUS  current
		DESCRIPTION
			"Show device packet buffer usage in %, it's the snapshot of packet buffer usage ratio when
			getting the values."
		::= { sysMgmt 12 }
		
	sysMgmtMemoryUsage OBJECT-TYPE
		SYNTAX  INTEGER
		MAX-ACCESS  read-only
		STATUS  current
		DESCRIPTION
			"Show device memory usage in %, it's the snapshot of the device memory usage ratio when
			getting the values."
		::= { sysMgmt 13 }		
--------------		
--  sysLoginSetup
	sysLoginSetup     	OBJECT IDENTIFIER ::= { sysMgmt 14 }

	loginLimitMaxNumberOfUser OBJECT-TYPE
        SYNTAX  INTEGER
        MAX-ACCESS  read-only
        STATUS  current
        DESCRIPTION
                      	""
        ::= { sysLoginSetup 1 }

        sysLoginSetupTable	OBJECT-TYPE
        SYNTAX	SEQUENCE OF SysLoginSetupEntry
        MAX-ACCESS  not-accessible
        STATUS  current
        DESCRIPTION
                 	""
        ::= { sysLoginSetup 2 }

	sysLoginSetupEntry OBJECT-TYPE
        SYNTAX	SysLoginSetupEntry
        MAX-ACCESS	not-accessible
        STATUS	current
        DESCRIPTION    	"An entry in LoginLimitMaxNumberOfUser."
        INDEX          	{ sysLoginName }
        ::= { sysLoginSetupTable 1 }

        SysLoginSetupEntry ::=
	SEQUENCE {
        	sysLoginName		DisplayString,
        	sysLoginPassword	DisplayString,
        	sysLoginPrivilege	INTEGER,
        	sysLoginRowStatus	RowStatus
        }

        sysLoginName OBJECT-TYPE
        SYNTAX  DisplayString
        MAX-ACCESS  read-only
        STATUS  current
        DESCRIPTION
                      	""
        ::= { sysLoginSetupEntry 1 }

        sysLoginPassword OBJECT-TYPE
        SYNTAX  DisplayString
        MAX-ACCESS  read-write
        STATUS  current
        DESCRIPTION
	""
        ::= { sysLoginSetupEntry 2 }

        sysLoginPrivilege OBJECT-TYPE
        SYNTAX  INTEGER
        MAX-ACCESS  read-write
        STATUS  current
        DESCRIPTION
        ""
        ::= { sysLoginSetupEntry 3 }
        

        sysLoginRowStatus OBJECT-TYPE
        SYNTAX  RowStatus
        MAX-ACCESS  read-create
        STATUS  current
        DESCRIPTION
                      	""
        ::= { sysLoginSetupEntry 4 }
        
-- ExternalAlarmSetup
                                                      
        sysMgmtExternalAlarmSetup OBJECT IDENTIFIER ::= { sysMgmt 15 }                      

       	externalAlarmTable	OBJECT-TYPE
        SYNTAX	SEQUENCE OF ExternalAlarmEntry
        MAX-ACCESS  not-accessible
        STATUS  current
        DESCRIPTION
                 	""
        ::= { sysMgmtExternalAlarmSetup 1 }
        
				externalAlarmEntry OBJECT-TYPE
        SYNTAX	ExternalAlarmEntry
        MAX-ACCESS	not-accessible
        STATUS	current
        DESCRIPTION    	"An entry in externalAlarmTable."
        INDEX          	{ externalAlarmIndex }
        ::= { externalAlarmTable 1 }

        ExternalAlarmEntry ::=
				SEQUENCE {
					externalAlarmIndex		INTEGER,
        	externalAlarmSwitch		EnabledStatus,
        	externalAlarmName			DisplayString
        }
        
        
        externalAlarmIndex OBJECT-TYPE
        SYNTAX  INTEGER
        MAX-ACCESS  read-only
        STATUS  current
        DESCRIPTION
                      	""
        ::= { externalAlarmEntry 1 } 
        
        externalAlarmSwitch OBJECT-TYPE
        SYNTAX  EnabledStatus
        MAX-ACCESS  read-write
        STATUS  current
        DESCRIPTION
						"externalalarm switch on/off"
        ::= { externalAlarmEntry 2 } 
                               
        externalAlarmName OBJECT-TYPE
        SYNTAX  DisplayString
        MAX-ACCESS  read-write
        STATUS  current
        DESCRIPTION
              "externalalarm name setting"
        ::= { externalAlarmEntry 3 }         
        

        
        sysMgmtExternalAlarmCurrentStatus OBJECT-TYPE
        SYNTAX  DisplayString
        MAX-ACCESS  read-only
        STATUS  current
        DESCRIPTION
                      	" externalalarm current status. The first to fourth bit represent externalalarm1 to 4 current status."
        ::= { sysMgmtExternalAlarmSetup 5 }
        
	sysMgmtMacFlush OBJECT-TYPE
        SYNTAX  INTEGER {
         		mac_flush(1)
        }
		MAX-ACCESS  read-write
		STATUS  current
		DESCRIPTION
			" Set 1 to execute mac flush operation, read value will always return 0"
		::= { sysMgmt 16 }        
		
	sysMgmtCPUUsageThreshold OBJECT-TYPE
        SYNTAX  INTEGER 
	MAX-ACCESS  read-write
	STATUS  current
	DESCRIPTION
		" Set CPU Threshold value"
	::= { sysMgmt 17 }   		
	
	sysMgmtPacketBufferThreshold OBJECT-TYPE
        SYNTAX  INTEGER 
	MAX-ACCESS  read-write
	STATUS  current
	DESCRIPTION
		" Set packet buffer usage Threshold value"
	::= { sysMgmt 18 }   		

	sysMgmtMemoryUsageThreshold OBJECT-TYPE
        SYNTAX  INTEGER 
	MAX-ACCESS  read-write
	STATUS  current
	DESCRIPTION
		" Set memory usage Threshold value"
	::= { sysMgmt 19 }   		
		
-- MonitorItemSetup

        sysMgmtMonitorItemSetup OBJECT IDENTIFIER ::= { sysMgmt 21 }                      

       	monitorItemTable	OBJECT-TYPE
        SYNTAX	SEQUENCE OF MonitorItemEntry
        MAX-ACCESS  not-accessible
        STATUS  current
        DESCRIPTION
                 	""
        ::= { sysMgmtMonitorItemSetup 1 }

				monitorItemEntry OBJECT-TYPE
        SYNTAX	MonitorItemEntry
        MAX-ACCESS	not-accessible
        STATUS	current
        DESCRIPTION    	"An entry in monitorItemTable."
        INDEX          	{ monitorItemIndex }
        ::= { monitorItemTable 1 }

        MonitorItemEntry ::=
				SEQUENCE {
					monitorItemIndex			INTEGER,
        	monitorItemName				DisplayString,
        	monitorItemThreshold	INTEGER
        }
        
        
        monitorItemIndex OBJECT-TYPE
        SYNTAX  INTEGER
        MAX-ACCESS  read-only
        STATUS  current
        DESCRIPTION
                      	""
        ::= { monitorItemEntry 1 } 

        monitorItemName OBJECT-TYPE
        SYNTAX  DisplayString
        MAX-ACCESS  read-only
        STATUS  current
        DESCRIPTION
              "Name of Monitor Item"
        ::= { monitorItemEntry 2 }       

        monitorItemThreshold OBJECT-TYPE
        SYNTAX  INTEGER
        MAX-ACCESS  read-write
        STATUS  current
        DESCRIPTION
						"Monitor Item Threshold.
						The value of High temperature threshold should be between 30~95"
        ::= { monitorItemEntry 3 } 

------------------------	
       
--  layer2Setup
	layer2Setup     	OBJECT IDENTIFIER ::= { ves1724-56fanless 13 }

        vlanTypeSetup OBJECT-TYPE
        SYNTAX  INTEGER {
         		dot1Q(1),
         		port_based(2)
        }
        MAX-ACCESS  read-write
        STATUS  current
        DESCRIPTION
                      ""
        ::= { layer2Setup 1 }

        igmpSnoopingStateSetup OBJECT-TYPE
        SYNTAX  INTEGER {
         		disabled(1),
         		enable_igmp_snooping(2),
         		enable_igmp_proxying(3)
        }
        MAX-ACCESS  read-write
        STATUS  current
        DESCRIPTION
                      ""
        ::= { layer2Setup 2 }

        tagVlanPortIsolationState OBJECT-TYPE
        SYNTAX  INTEGER
        MAX-ACCESS  read-write
        STATUS  current
        DESCRIPTION
                      "This item always returns 0. Set 1(port isolation) or 2 (all-connected) to this item to quickly setup port-based VLAN members. "
        ::= { layer2Setup 3 }

        stpState OBJECT-TYPE
        SYNTAX  EnabledStatus
        MAX-ACCESS  read-write
        STATUS  current
        DESCRIPTION
                      ""
        ::= { layer2Setup 4 }

        igmpFilteringStateSetup OBJECT-TYPE
        SYNTAX  EnabledStatus
        MAX-ACCESS  read-write
        STATUS  current
        DESCRIPTION
                      ""
        ::= { layer2Setup 5 }

        unknownMulticastFrameForwarding OBJECT-TYPE
        SYNTAX  INTEGER {
         	flooding(1),
         	drop(2)
        }
        MAX-ACCESS  read-write
        STATUS  current
        DESCRIPTION
                      ""
        ::= { layer2Setup 6 }

        multicastGrpHostTimeout OBJECT-TYPE
        SYNTAX  INTEGER 
        MAX-ACCESS  read-write
        STATUS  current
        DESCRIPTION
                      "Specify host timeout for all multicast groups when the specific port is in auto mode."
        ::= { layer2Setup 7 }
        
        multicastGrpLeaveTimeout OBJECT-TYPE
        SYNTAX  INTEGER 
        MAX-ACCESS  read-write
        STATUS  current
        DESCRIPTION
                      "Specify leave timeout for all multicast groups."
        ::= { layer2Setup 8 }

        reservedMulticastFrameForwarding OBJECT-TYPE
        SYNTAX  INTEGER {
         	flooding(1),
         	drop(2)
        }
        MAX-ACCESS  read-write
        STATUS  current
        DESCRIPTION
                      ""
        ::= { layer2Setup 9 }  

        igmpsnp8021pPriority OBJECT-TYPE
        SYNTAX  INTEGER
        MAX-ACCESS  read-write
        STATUS  current
        DESCRIPTION
                      "Set the 802.1p priority of control messages for igmp-snooping(0~8, 8-No Change)"
        ::= { layer2Setup 10 }  
 
        portBasedVlanPortIsolationState OBJECT-TYPE
        SYNTAX  INTEGER
        MAX-ACCESS  read-write
        STATUS  current
        DESCRIPTION
                      "This item always returns 0. Set 1(port isolation) or 2 (all-connected) to this item to quickly setup port-based VLAN members. "
        ::= { layer2Setup 11 }
        

        igmpsnpVlanMode OBJECT-TYPE
        SYNTAX  INTEGER {
         	auto(1),
         	fixed(2)
        }
        MAX-ACCESS  read-write
        STATUS  current
        DESCRIPTION
                      ""
        ::= { layer2Setup 12 }                
        
        
        stpMode OBJECT-TYPE
        SYNTAX  INTEGER {
         	rstp(1),
         	mrstp(2),
         	mstp (3)
        }
        MAX-ACCESS  read-write
        STATUS  current
        DESCRIPTION
                      ""
        ::= { layer2Setup 13 }                               
        
	mgmdMLDsupport OBJECT-TYPE
	SYNTAX  EnabledStatus
	MAX-ACCESS  read-write
	STATUS  current
	DESCRIPTION
		"Enable MLD / Disable MLD"
	::= { layer2Setup 17 }
        
        mgmdv3mode OBJECT-TYPE
				SYNTAX  EnabledStatus
				MAX-ACCESS  read-write
				STATUS  current
				DESCRIPTION
				"Enable MLDv2 and IGMPv3 mode / Disable MLDv2 and IGMPv3 mode"
				::= { layer2Setup 18 }
				
--  igmpsnpVlanTable
        igmpsnpVlanTable	OBJECT-TYPE
        SYNTAX	SEQUENCE OF IgmpsnpVlanEntry
        MAX-ACCESS  not-accessible
        STATUS  current
        DESCRIPTION
                 	""
        ::= { layer2Setup 14 }
        
	igmpsnpVlanEntry OBJECT-TYPE
        SYNTAX	IgmpsnpVlanEntry
        MAX-ACCESS	not-accessible
        STATUS	current
        DESCRIPTION    	"An entry in IgmpsnpVlanTable."
        INDEX          	{ igmpsnpVid }
        ::= { igmpsnpVlanTable 1 }

        IgmpsnpVlanEntry ::=
           SEQUENCE {
			igmpsnpVid		INTEGER,
        	igmpsnpVlanName	DisplayString,        	
        	igmpsnpVlanRowStatus RowStatus
           }
           
   
        igmpsnpVid OBJECT-TYPE
        SYNTAX  INTEGER
        MAX-ACCESS  read-only
        STATUS  current
        DESCRIPTION
                      	""
        ::= { igmpsnpVlanEntry 1 }        


     igmpsnpVlanName OBJECT-TYPE
        SYNTAX  DisplayString
        MAX-ACCESS  read-write
        STATUS  current
        DESCRIPTION
                      	""
        ::= { igmpsnpVlanEntry 2 }
        
        
        igmpsnpVlanRowStatus OBJECT-TYPE
        SYNTAX  RowStatus
        MAX-ACCESS  read-create
        STATUS  current
        DESCRIPTION
                      	""
        ::= {  igmpsnpVlanEntry 3 }

--  ipSetup
	ipSetup     	OBJECT IDENTIFIER ::= { ves1724-56fanless 14 }

        dnsIpAddress OBJECT-TYPE
        SYNTAX  IpAddress
        MAX-ACCESS  read-write
        STATUS  current
        DESCRIPTION
                      ""
        ::= { ipSetup 1 }

        defaultMgmt OBJECT-TYPE
        SYNTAX  INTEGER {
        	in_band(0),
        	out_of_band(1)
        }
        MAX-ACCESS  read-write
        STATUS  current
        DESCRIPTION
                      ""
        ::= { ipSetup 2 }

	inbandIpSetup     	OBJECT IDENTIFIER ::= { ipSetup 3 }

        inbandIpType OBJECT-TYPE
        SYNTAX  INTEGER {
        	dhcp_client(0),
        	static_ip(1)
        }
        MAX-ACCESS  read-write
        STATUS  current
        DESCRIPTION
                      ""
        ::= { inbandIpSetup 1 }

        inbandVid OBJECT-TYPE
        SYNTAX  INTEGER
        MAX-ACCESS  read-write
        STATUS  current
        DESCRIPTION
                      ""
        ::= { inbandIpSetup 2 }

        inbandStaticIp OBJECT-TYPE
        SYNTAX  IpAddress
        MAX-ACCESS  read-write
        STATUS  current
        DESCRIPTION
                      ""
        ::= { inbandIpSetup 3 }

        inbandStaticSubnetMask OBJECT-TYPE
        SYNTAX  IpAddress
        MAX-ACCESS  read-write
        STATUS  current
        DESCRIPTION
                      ""
        ::= { inbandIpSetup 4 }

        inbandStaticGateway OBJECT-TYPE
        SYNTAX  IpAddress
        MAX-ACCESS  read-write
        STATUS  current
        DESCRIPTION
                      ""
        ::= { inbandIpSetup 5 }

        dhcpOption12 OBJECT-TYPE
        SYNTAX  EnabledStatus
        MAX-ACCESS  read-write
        STATUS  current
        DESCRIPTION
                      	"enable/disable DHCP option 12"
        ::= { inbandIpSetup 6 }
        
        dhcpOption12Hostname OBJECT-TYPE
        SYNTAX  DisplayString
        MAX-ACCESS  read-write
        STATUS  current
        DESCRIPTION
                      	"setup DHCP option 12 hostname"
        ::= { inbandIpSetup 7 }
        
        dhcpOption60 OBJECT-TYPE
        SYNTAX  EnabledStatus
        MAX-ACCESS  read-write
        STATUS  current
        DESCRIPTION
                      	"enable/disable DHCP option 60"
        ::= { inbandIpSetup 8 }
        
        dhcpOption60VendorClassID OBJECT-TYPE
        SYNTAX  DisplayString
        MAX-ACCESS  read-write
        STATUS  current
        DESCRIPTION
                      	"setup DHCP option 60 vendor class identifier"
        ::= { inbandIpSetup 9 }

	outOfBandIpSetup     	OBJECT IDENTIFIER ::= { ipSetup 4 }

        outOfBandIp OBJECT-TYPE
        SYNTAX  IpAddress
        MAX-ACCESS  read-write
        STATUS  current
        DESCRIPTION
                      ""
        ::= { outOfBandIpSetup 1 }

        outOfBandSubnetMask OBJECT-TYPE
        SYNTAX  IpAddress
        MAX-ACCESS  read-write
        STATUS  current
        DESCRIPTION
                      ""
        ::= { outOfBandIpSetup 2 }

        outOfBandGateway OBJECT-TYPE
        SYNTAX  IpAddress
        MAX-ACCESS  read-write
        STATUS  current
        DESCRIPTION
                      ""
        ::= { outOfBandIpSetup 3 }

        maxNumOfInbandIp OBJECT-TYPE
        SYNTAX  INTEGER
        MAX-ACCESS  read-only
        STATUS  current
        DESCRIPTION
                      	""
        ::= { ipSetup 5 }

--  inbandIpTable
        inbandIpTable	OBJECT-TYPE
        SYNTAX	SEQUENCE OF InbandIpEntry
        MAX-ACCESS  not-accessible
        STATUS  current
        DESCRIPTION
                 	""
        ::= { ipSetup 6 }

	inbandIpEntry OBJECT-TYPE
        SYNTAX	InbandIpEntry
        MAX-ACCESS	not-accessible
        STATUS	current
        DESCRIPTION    	"An entry in inbandIpTable."
        INDEX          	{ inbandEntryIp, inbandEntryVid }
        ::= { inbandIpTable 1 }

        InbandIpEntry ::=
	SEQUENCE {
        	inbandEntryIp		IpAddress,
        	inbandEntrySubnetMask	IpAddress,
        	inbandEntryGateway	IpAddress,
        	inbandEntryVid		INTEGER,
        	inbandEntryManageable	EnabledStatus,
        	inbandEntryRowStatus	RowStatus
        }

        inbandEntryIp OBJECT-TYPE
        SYNTAX  IpAddress
        MAX-ACCESS  read-only
        STATUS  current
        DESCRIPTION
                      	""
        ::= { inbandIpEntry 1 }

        inbandEntrySubnetMask OBJECT-TYPE
        SYNTAX  IpAddress
        MAX-ACCESS  read-write
        STATUS  current
        DESCRIPTION
                      	""
        ::= { inbandIpEntry 2 }

        inbandEntryGateway OBJECT-TYPE
        SYNTAX  IpAddress
        MAX-ACCESS  read-write
        STATUS  current
        DESCRIPTION
                      	""
        ::= { inbandIpEntry 3 }

        inbandEntryVid OBJECT-TYPE
        SYNTAX  INTEGER
        MAX-ACCESS  read-only
        STATUS  current
        DESCRIPTION
                      	""
        ::= { inbandIpEntry 4 }

        inbandEntryManageable OBJECT-TYPE
        SYNTAX  EnabledStatus
        MAX-ACCESS  read-write
        STATUS  current
        DESCRIPTION
                      	""
        ::= { inbandIpEntry 5 }

        inbandEntryRowStatus OBJECT-TYPE
        SYNTAX  RowStatus
        MAX-ACCESS  read-create
        STATUS  current
        DESCRIPTION
                      	""
        ::= { inbandIpEntry 6 }

--  filterSetup
	filterSetup     	OBJECT IDENTIFIER ::= { ves1724-56fanless 15 }

--  filterTable
       	filterTable	OBJECT-TYPE
        SYNTAX	SEQUENCE OF FilterEntry
        MAX-ACCESS  not-accessible
        STATUS  current
        DESCRIPTION
                 	""
        ::= { filterSetup 1 }

	filterEntry OBJECT-TYPE
        SYNTAX	FilterEntry
        MAX-ACCESS	not-accessible
        STATUS	current
        DESCRIPTION    	"An entry in filterTable."
        INDEX          	{ filterMacAddr, filterVid }
        ::= { filterTable 1 }

        FilterEntry ::=
           SEQUENCE {
         	filterName		DisplayString,
        	filterActionState	INTEGER,
        	filterMacAddr		MacAddress,
        	filterVid		INTEGER,
        	filterRowStatus		RowStatus
           }

        filterName OBJECT-TYPE
        SYNTAX  DisplayString
        MAX-ACCESS  read-write
        STATUS  current
        DESCRIPTION
                      	""
        ::= { filterEntry 1 }

        filterActionState OBJECT-TYPE
        SYNTAX  INTEGER {
		discard_source(1),
		discard_destination(2),
		both(3)
	}
        MAX-ACCESS  read-write
        STATUS  current
        DESCRIPTION
                      	""
        ::= { filterEntry 2 }

        filterMacAddr OBJECT-TYPE
        SYNTAX  MacAddress
        MAX-ACCESS  read-only
        STATUS  current
        DESCRIPTION
                      	""
        ::= { filterEntry 3 }

   	filterVid OBJECT-TYPE
        SYNTAX  INTEGER
        MAX-ACCESS  read-only
        STATUS  current
        DESCRIPTION
                      	""
        ::= { filterEntry 4 }

   	filterRowStatus OBJECT-TYPE
        SYNTAX  RowStatus
        MAX-ACCESS  read-create
        STATUS  current
        DESCRIPTION
                      	""
        ::= { filterEntry 5 }

--  mirrorSetup
	mirrorSetup     	OBJECT IDENTIFIER ::= { ves1724-56fanless 16 }

--  mirrorState
        mirrorState OBJECT-TYPE
        SYNTAX  EnabledStatus
        MAX-ACCESS  read-write
        STATUS  current
        DESCRIPTION
                      	""
        ::= { mirrorSetup 1 }

        mirrorMonitorPort OBJECT-TYPE
        SYNTAX  INTEGER
        MAX-ACCESS  read-write
        STATUS  current
        DESCRIPTION
                      	""
        ::= { mirrorSetup 2 }

        mirrorRspanVid OBJECT-TYPE
        SYNTAX  INTEGER
        MAX-ACCESS  read-write
        STATUS  current
        DESCRIPTION
                      	""
        ::= { mirrorSetup 7 }
        
-- mirrorTable

        mirrorTable OBJECT-TYPE
        SYNTAX	SEQUENCE OF MirrorEntry
        MAX-ACCESS  not-accessible
        STATUS  current
        DESCRIPTION
                 	""
        ::= { mirrorSetup 3 }

	mirrorEntry OBJECT-TYPE
        SYNTAX	MirrorEntry
        MAX-ACCESS	not-accessible
        STATUS	current
        DESCRIPTION    	"An entry in mirrorTable."
        INDEX          	{ dot1dBasePort }
        ::= { mirrorTable 1 }

        MirrorEntry ::=
           SEQUENCE {
        	mirrorMirroredState	EnabledStatus,
        	mirrorDirection		INTEGER
           }

        mirrorMirroredState OBJECT-TYPE
        SYNTAX  EnabledStatus
        MAX-ACCESS  read-write
        STATUS  current
        DESCRIPTION
                      	""
        ::= { mirrorEntry 1 }

        mirrorDirection OBJECT-TYPE
        SYNTAX  INTEGER {
        	ingress(0),
        	egress(1),
        	both(2)
        }
        MAX-ACCESS  read-write
        STATUS  current
        DESCRIPTION
                      	""
        ::= { mirrorEntry 2 }


-- aggrSetup
	aggrSetup     	OBJECT IDENTIFIER ::= { ves1724-56fanless 17 }

        aggrState OBJECT-TYPE
        SYNTAX  EnabledStatus
        MAX-ACCESS  read-write
        STATUS  current
        DESCRIPTION
                      	""
        ::= { aggrSetup 1 }

        aggrSystemPriority OBJECT-TYPE
        SYNTAX  INTEGER
        MAX-ACCESS  read-write
        STATUS  current
        DESCRIPTION
                      	""
        ::= { aggrSetup 2 }

-- aggrGroupTable

        aggrGroupTable OBJECT-TYPE
        SYNTAX	SEQUENCE OF AggrGroupEntry
        MAX-ACCESS  not-accessible
        STATUS  current
        DESCRIPTION
                 	""
        ::= { aggrSetup 3 }

	aggrGroupEntry OBJECT-TYPE
        SYNTAX	AggrGroupEntry
        MAX-ACCESS	not-accessible
        STATUS	current
        DESCRIPTION    	"An entry in aggrGroupTable."
        INDEX          	{ aggrGroupIndex }
        ::= { aggrGroupTable 1 }

        AggrGroupEntry ::=
           SEQUENCE {
        	aggrGroupIndex		INTEGER,
        	aggrGroupState		EnabledStatus,
        	aggrGroupDynamicState	EnabledStatus
           }

        aggrGroupIndex OBJECT-TYPE
        SYNTAX  INTEGER
        MAX-ACCESS  read-only
        STATUS  current
        DESCRIPTION
                      	""
        ::= { aggrGroupEntry 1 }

        aggrGroupState OBJECT-TYPE
        SYNTAX  EnabledStatus
        MAX-ACCESS  read-write
        STATUS  current
        DESCRIPTION
                     	""
        ::= { aggrGroupEntry 2 }

        aggrGroupDynamicState OBJECT-TYPE
        SYNTAX  EnabledStatus
        MAX-ACCESS  read-write
        STATUS  current
        DESCRIPTION
                     	""
        ::= { aggrGroupEntry 3 }

-- aggrPortTable

        aggrPortTable OBJECT-TYPE
        SYNTAX	SEQUENCE OF AggrPortEntry
        MAX-ACCESS  not-accessible
        STATUS  current
        DESCRIPTION
                 	""
        ::= { aggrSetup 4 }

	aggrPortEntry OBJECT-TYPE
        SYNTAX	AggrPortEntry
        MAX-ACCESS	not-accessible
        STATUS	current
        DESCRIPTION    	"An entry in aggrPortTable."
        INDEX          	{ dot1dBasePort }
        ::= { aggrPortTable 1 }

        AggrPortEntry ::=
           SEQUENCE {
        	aggrPortGroup			INTEGER,
        	aggrPortDynamicStateTimeout	INTEGER
           }

        aggrPortGroup OBJECT-TYPE
        SYNTAX  INTEGER {
        	none(0),
        	t1(1)
        }
        MAX-ACCESS  read-write
        STATUS  current
        DESCRIPTION
                      	""
        ::= { aggrPortEntry 1 }

        aggrPortDynamicStateTimeout OBJECT-TYPE
        SYNTAX  INTEGER
        MAX-ACCESS  read-write
        STATUS  current
        DESCRIPTION
                     	""
        ::= { aggrPortEntry 2 }


-- accessCtlSetup
	accessCtlSetup     	OBJECT IDENTIFIER ::= { ves1724-56fanless 18 }

-- accessCtlTable

        accessCtlTable OBJECT-TYPE
        SYNTAX	SEQUENCE OF AccessCtlEntry
        MAX-ACCESS  not-accessible
        STATUS  current
        DESCRIPTION
                 	""
        ::= { accessCtlSetup 1 }

	accessCtlEntry OBJECT-TYPE
        SYNTAX	AccessCtlEntry
        MAX-ACCESS	not-accessible
        STATUS	current
        DESCRIPTION    	"An entry in accessCtlTable."
        INDEX          	{ accessCtlService }
        ::= { accessCtlTable 1 }

        AccessCtlEntry ::=
           SEQUENCE {
        	accessCtlService	INTEGER,
        	accessCtlEnable	EnabledStatus,
        	accessCtlServicePort	INTEGER,
        	accessCtlTimeout	INTEGER
           }

        accessCtlService OBJECT-TYPE
        SYNTAX  INTEGER {
        	telnet(1),
        	ssh(2),
        	ftp(3),
        	http(4),
        	https(5),
        	icmp(6),
        	snmp(7)
        }
        MAX-ACCESS  read-only
        STATUS  current
        DESCRIPTION
                      	""
        ::= { accessCtlEntry 1 }

        accessCtlEnable OBJECT-TYPE
        SYNTAX  EnabledStatus
        MAX-ACCESS  read-write
        STATUS  current
        DESCRIPTION
                     	""
        ::= { accessCtlEntry 2 }

        accessCtlServicePort OBJECT-TYPE
        SYNTAX  INTEGER
        MAX-ACCESS  read-write
        STATUS  current
        DESCRIPTION
                     	""
        ::= { accessCtlEntry 3 }

        accessCtlTimeout OBJECT-TYPE
        SYNTAX  INTEGER
        MAX-ACCESS  read-write
        STATUS  current
        DESCRIPTION
                     	""
        ::= { accessCtlEntry 4 }

--  securedClientTable
        securedClientTable OBJECT-TYPE
        SYNTAX	SEQUENCE OF SecuredClientEntry
        MAX-ACCESS  not-accessible
        STATUS  current
        DESCRIPTION
                 	""
        ::= { accessCtlSetup 2 }

	securedClientEntry OBJECT-TYPE
        SYNTAX	SecuredClientEntry
        MAX-ACCESS	not-accessible
        STATUS	current
        DESCRIPTION    	"An entry in securedClientTable."
        INDEX          	{ securedClientIndex }
        ::= { securedClientTable 1 }

        SecuredClientEntry ::=
           SEQUENCE {
           	securedClientIndex	INTEGER,
           	securedClientEnable	EnabledStatus,
        	securedClientStartIp	IpAddress,
        	securedClientEndIp	IpAddress,
        	securedClientService			BITS,
        	securedClientIpAddrType			InetAddressType,
        	securedClientStartIpAddr		InetAddress,
        	securedClientEndIpAddr			InetAddress
           }

        securedClientIndex OBJECT-TYPE
        SYNTAX  INTEGER
        MAX-ACCESS  read-only
        STATUS  current
        DESCRIPTION
                      	""
        ::= { securedClientEntry 1 }

        securedClientEnable OBJECT-TYPE
        SYNTAX  EnabledStatus
        MAX-ACCESS  read-write
        STATUS  current
        DESCRIPTION
                      	""
        ::= { securedClientEntry 2 }

        securedClientStartIp OBJECT-TYPE
        SYNTAX  IpAddress
        MAX-ACCESS  read-write
        STATUS  current
        DESCRIPTION
                      	"IPv4 only"
        ::= { securedClientEntry 3 }

        securedClientEndIp OBJECT-TYPE
        SYNTAX  IpAddress
        MAX-ACCESS  read-write
        STATUS  current
        DESCRIPTION
                     	"IPv4 only"
        ::= { securedClientEntry 4 }

        securedClientService OBJECT-TYPE
        SYNTAX	BITS {
			telnet(0),
			ftp(1),
			http(2),
			icmp(3),
			snmp(4),
			ssh(5),
			https(6)
		}
        MAX-ACCESS  read-write
        STATUS  current
        DESCRIPTION
                     	""
        ::= { securedClientEntry 5 }

        securedClientIpAddrType OBJECT-TYPE
        SYNTAX  InetAddressType { ipv4(1), ipv6(2) }
        MAX-ACCESS  read-write
        STATUS  current
        DESCRIPTION
                      	""
        ::= { securedClientEntry 6 }
        
        securedClientStartIpAddr OBJECT-TYPE
        SYNTAX  InetAddress
        MAX-ACCESS  read-write
        STATUS  current
        DESCRIPTION
                      	""
        ::= { securedClientEntry 7 }
        
        securedClientEndIpAddr OBJECT-TYPE
        SYNTAX  InetAddress
        MAX-ACCESS  read-write
        STATUS  current
        DESCRIPTION
                      	""
        ::= { securedClientEntry 8 }

--  queuingMethodSetup
	queuingMethodSetup     	OBJECT IDENTIFIER ::= { ves1724-56fanless 19 }

        queuingMethodType OBJECT-TYPE
        SYNTAX  INTEGER {
        	strictly_priority(0),
        	weighted_fair_scheduling(1),
        	weighted_round_robin(2)
        }
        MAX-ACCESS  read-write
        STATUS  current
        DESCRIPTION
                      	""
        ::= { queuingMethodSetup 1 }



-- portQueuingMethodTable
        portQueuingMethodTable OBJECT-TYPE
        SYNTAX	SEQUENCE OF PortQueuingMethodEntry
        MAX-ACCESS  not-accessible
        STATUS  current
        DESCRIPTION
                 	""
        ::= { queuingMethodSetup 2 }

	portQueuingMethodEntry OBJECT-TYPE
        SYNTAX	PortQueuingMethodEntry
        MAX-ACCESS	not-accessible
        STATUS	current
        DESCRIPTION    	"An entry in portQueuingMethodTable."
        INDEX          	{ dot1dBasePort, portQueuingMethodQueue }
        ::= {portQueuingMethodTable 1}

        PortQueuingMethodEntry ::=
           SEQUENCE {
        	portQueuingMethodQueue	INTEGER,
        	portQueuingMethodWeight	INTEGER
           }

        portQueuingMethodQueue OBJECT-TYPE
        SYNTAX  INTEGER
        MAX-ACCESS  read-only
        STATUS  current
        DESCRIPTION
                      	"0...7"
        ::= { portQueuingMethodEntry 1 }

        portQueuingMethodWeight OBJECT-TYPE
        SYNTAX  INTEGER
        MAX-ACCESS  read-write
        STATUS  current
        DESCRIPTION
                     	"0...15"
        ::= { portQueuingMethodEntry 2 }

 -- queuingMethodFeSpq
		queuingMethodFeSpq OBJECT-TYPE
        SYNTAX  INTEGER {
        	none(0),
        	q0(1),
        	q1(2),
        	q2(3),
        	q3(4),
        	q4(5),
        	q5(6),
        	q6(7),
        	q7(8)
        }
        MAX-ACCESS  read-write
        STATUS  current
        DESCRIPTION
                      	"VDSL port SPQ enable. Qx and higher is SPQ, and the rest of the others are WFQ."
        ::= { queuingMethodSetup 3 }

-- portQueuingMethodGeSpqTable
        portQueuingMethodGeSpqTable OBJECT-TYPE
        SYNTAX	SEQUENCE OF PortQueuingMethodGeSpqEntry
        MAX-ACCESS  not-accessible
        STATUS  current
        DESCRIPTION
                 	""
        ::= { queuingMethodSetup 4 }
        
	portQueuingMethodGeSpqEntry OBJECT-TYPE
        SYNTAX	PortQueuingMethodGeSpqEntry
        MAX-ACCESS	not-accessible
        STATUS	current
        DESCRIPTION    	"An entry in portQueuingMethodGeSpqTable."
        INDEX          	{ dot1dBasePort }
        ::= {portQueuingMethodGeSpqTable 1}

        PortQueuingMethodGeSpqEntry ::=
           SEQUENCE {
        	portQueuingMethodGeSpq	INTEGER
           }

        portQueuingMethodGeSpq OBJECT-TYPE
		SYNTAX  INTEGER {
        	none(0),
        	q0(1),
        	q1(2),
        	q2(3),
        	q3(4),
        	q4(5),
        	q5(6),
        	q6(7),
        	q7(8)
        }

        MAX-ACCESS  read-write
        STATUS  current
        DESCRIPTION
                      	"GE port SPQ enable. Qx and higher is SPQ, and the rest of the others are WFQ."
        ::= { portQueuingMethodGeSpqEntry 1 }

--  dhcpSetup
	dhcpSetup     	OBJECT IDENTIFIER ::= { ves1724-56fanless 20 }

        globalDhcpRelay OBJECT IDENTIFIER ::= { dhcpSetup 1 }

        globalDhcpRelayEnable OBJECT-TYPE
        SYNTAX  EnabledStatus
        MAX-ACCESS  read-write
        STATUS  current
        DESCRIPTION
                      	""
        ::= { globalDhcpRelay 1 }

        globalDhcpRelayOption82Enable OBJECT-TYPE
        SYNTAX  EnabledStatus
        MAX-ACCESS  read-write
        STATUS  current
        DESCRIPTION
                      	""
        ::= { globalDhcpRelay 2 }

        globalDhcpRelayInfoData OBJECT-TYPE
        SYNTAX  DisplayString
        MAX-ACCESS  read-write
        STATUS  current
        DESCRIPTION
                      	""
        ::= { globalDhcpRelay 4 }

--  globalDhcpRelayRemoteServer

        maxNumberOfGlobalDhcpRelayRemoteServer OBJECT-TYPE
        SYNTAX  INTEGER
        MAX-ACCESS  read-only
        STATUS  current
        DESCRIPTION
                      	""
        ::= { globalDhcpRelay 5 }

-- globalDhcpRelayRemoteServerTable
        globalDhcpRelayRemoteServerTable OBJECT-TYPE
        SYNTAX	SEQUENCE OF GlobalDhcpRelayRemoteServerEntry
        MAX-ACCESS  not-accessible
        STATUS  current
        DESCRIPTION
                 	""
        ::= { globalDhcpRelay 6 }

	globalDhcpRelayRemoteServerEntry OBJECT-TYPE
        SYNTAX	GlobalDhcpRelayRemoteServerEntry
        MAX-ACCESS	not-accessible
        STATUS	current
        DESCRIPTION    	"An entry in globalDhcpRelayRemoteServerTable."
        INDEX          	{ globalDhcpRelayRemoteServerIp }
        ::= { globalDhcpRelayRemoteServerTable 1 }

        GlobalDhcpRelayRemoteServerEntry ::=
           SEQUENCE {
        	globalDhcpRelayRemoteServerIp		IpAddress,
        	globalDhcpRelayRemoteServerRowStatus	RowStatus
           }

        globalDhcpRelayRemoteServerIp OBJECT-TYPE
        SYNTAX  IpAddress
        MAX-ACCESS  read-only
        STATUS  current
        DESCRIPTION
                      	""
        ::= { globalDhcpRelayRemoteServerEntry 1 }

        globalDhcpRelayRemoteServerRowStatus OBJECT-TYPE
        SYNTAX  RowStatus
        MAX-ACCESS  read-create
        STATUS  current
        DESCRIPTION
                     	""
        ::= { globalDhcpRelayRemoteServerEntry 2 }

--- dhcp option82 remote id field
        globalDhcpRelayRemoteIDEnable OBJECT-TYPE
        SYNTAX  EnabledStatus
        MAX-ACCESS  read-write
        STATUS  current
        DESCRIPTION
                      	""
        ::= { globalDhcpRelay 7 }

        globalDhcpRelayRemoteIDData OBJECT-TYPE
        SYNTAX  DisplayString
        MAX-ACCESS  read-write
        STATUS  current
        DESCRIPTION
                      	""
        ::= { globalDhcpRelay 8 }

        globalDhcpRelayInfoType OBJECT-TYPE
        SYNTAX  INTEGER{
        	system(1),
        	hostname(2),
			all(3)        	
        }
        MAX-ACCESS  read-write
        STATUS  current
        DESCRIPTION
                      	""
        ::= { globalDhcpRelay 9 }
        
        globalDhcpRelayRemoteIDType OBJECT-TYPE
        SYNTAX  INTEGER{
        	system(1),
        	portname(2),
			all(3)        
        }
        MAX-ACCESS  read-write
        STATUS  current
        DESCRIPTION
                      	""
        ::= { globalDhcpRelay 10 }
        
		globalDhcpRelaySpv OBJECT-TYPE
        SYNTAX  INTEGER   
        {
        	private(0),
 			sp(1),
			sv(2),
     		pv(3),
      		spv(4)
        }
        MAX-ACCESS  read-write
        STATUS  current
        DESCRIPTION
        	"Tag option setting for global DHCP relay. private(0), SP(1), SV(2), PV(3), SPV(4)."
        ::= { globalDhcpRelay 11 }        
        
        globalDhcpRelayDelim OBJECT-TYPE
        SYNTAX  INTEGER   
        {
        	none(0),
      		pound(1),
 			semicolon(2),
			dot(3),
     		comma(4),
     		slash(5),
     		space(6)
        }
        MAX-ACCESS  read-write
        STATUS  current
        DESCRIPTION
        	"Delimiter setting for global DHCP relay. none(0), pound[#](1), semicolon[;](2), dot[.](3), comma[,](4), slash[/](5), space[ ](6)."
        ::= { globalDhcpRelay 12 }
        
        globalDhcpRelayRIDDelim OBJECT-TYPE
        SYNTAX  DisplayString
        MAX-ACCESS  read-write
        STATUS  current
        DESCRIPTION
                      	""
        ::= { globalDhcpRelay 13 }
		
		globalDhcpRelaySwapOpt82 OBJECT-TYPE
        SYNTAX  EnabledStatus
        MAX-ACCESS  read-write
        STATUS  current
        DESCRIPTION
                      	""
        ::= { globalDhcpRelay 14 }
        

--
	dhcpRelay OBJECT IDENTIFIER ::= { dhcpSetup 3 }

	 maxNumberOfDhcpRelay OBJECT-TYPE
        SYNTAX  INTEGER
        MAX-ACCESS  read-only
        STATUS  current
        DESCRIPTION
                      	"The maximum number of DHCP relay entries that can be created. 
                      	A value of 0 for this object implies that there exists settings for 
                      	global DHCP relay."
        ::= { dhcpRelay 1 }
        
     maxNumberOfDhcpRelayRemoteServer OBJECT-TYPE
        SYNTAX  INTEGER
        MAX-ACCESS  read-only
        STATUS  current
        DESCRIPTION
                      	""
        ::= { dhcpRelay 2 }
 
 -- dhcpRelayTable   
        
        dhcpRelayTable OBJECT-TYPE
        SYNTAX	SEQUENCE OF DhcpRelayEntry
        MAX-ACCESS  not-accessible
        STATUS  current
        DESCRIPTION
                 	""
        ::= { dhcpRelay 3 }  	


	dhcpRelayEntry OBJECT-TYPE
        SYNTAX	DhcpRelayEntry
        MAX-ACCESS	not-accessible
        STATUS	current
        DESCRIPTION    	"An entry in dhcpRelayTable."
        INDEX          	{ dhcpRelayVid }
        ::= { dhcpRelayTable 1 }

        DhcpRelayEntry ::=
           SEQUENCE {
        	dhcpRelayOption82Enable   EnabledStatus,
        	dhcpRelayInfoData   DisplayString,
        	dhcpRelayRemoteIDEnable   EnabledStatus,
        	dhcpRelayRemoteIDData       DisplayString,
        	dhcpRelayInfoType           INTEGER,
        	dhcpRelayRemoteIDType       INTEGER
			,dhcpRelaySpv				INTEGER,
			dhcpRelayDelim				INTEGER,
			dhcpRelayRIDDelim			DisplayString,
   			dhcpRelaySwapOpt82			EnabledStatus
           }
        
        dhcpRelayOption82Enable OBJECT-TYPE
        SYNTAX  EnabledStatus
        MAX-ACCESS  read-write
        STATUS  current
        DESCRIPTION
                      	""
        ::= { dhcpRelayEntry 1 }

        dhcpRelayInfoData OBJECT-TYPE
        SYNTAX  DisplayString
        MAX-ACCESS  read-write
        STATUS  current
        DESCRIPTION
                      	""
        ::= { dhcpRelayEntry 3 }   

--- dhcp option82 remote id field
        dhcpRelayRemoteIDEnable OBJECT-TYPE
        SYNTAX  EnabledStatus
        MAX-ACCESS  read-write
        STATUS  current
        DESCRIPTION
                      	""
        ::= { dhcpRelayEntry 4 }

        dhcpRelayRemoteIDData OBJECT-TYPE
        SYNTAX  DisplayString
        MAX-ACCESS  read-write
        STATUS  current
        DESCRIPTION
                      	""
        ::= { dhcpRelayEntry 5 }

        dhcpRelayInfoType OBJECT-TYPE
        SYNTAX  INTEGER{
        	system(1),
        	hostname(2)
        }
        MAX-ACCESS  read-write
        STATUS  current
        DESCRIPTION
                      	""
        ::= { dhcpRelayEntry 6 }

        dhcpRelayRemoteIDType OBJECT-TYPE
        SYNTAX  INTEGER{
        	system(1),
        	portname(2),
			all(3)        	
        }
        MAX-ACCESS  read-write
        STATUS  current
        DESCRIPTION
                      	""
        ::= { dhcpRelayEntry 7 }
        
		dhcpRelaySpv OBJECT-TYPE
        SYNTAX  INTEGER   
        {
        	private(0),
 			sp(1),
			sv(2),
     		pv(3),
      		spv(4)
        }
        MAX-ACCESS  read-write
        STATUS  current
        DESCRIPTION
        	"Tag option setting for global DHCP relay. private(0), SP(1), SV(2), PV(3), SPV(4)."
        ::= { dhcpRelayEntry 8 }        
        
        dhcpRelayDelim OBJECT-TYPE
        SYNTAX  INTEGER   
        {
        	none(0),
      		pound(1),
 			semicolon(2),
			dot(3),
     		comma(4),
     		slash(5),
     		space(6)
        }
        MAX-ACCESS  read-write
        STATUS  current
        DESCRIPTION
        	"Delimiter setting for global DHCP relay. none(0), pound[#](1), semicolon[;](2), dot[.](3), comma[,](4), slash[/](5), space[ ](6)."
        ::= { dhcpRelayEntry 9 }
        
        dhcpRelayRIDDelim OBJECT-TYPE
        SYNTAX  DisplayString
        MAX-ACCESS  read-write
        STATUS  current
        DESCRIPTION
                      	""
        ::= { dhcpRelayEntry 10 }
		
		dhcpRelaySwapOpt82 OBJECT-TYPE
        SYNTAX  EnabledStatus
        MAX-ACCESS  read-write
        STATUS  current
        DESCRIPTION
                      	""
        ::= { dhcpRelayEntry 11 }
--end ab4daa   
        
        
     -- dhcpRelayRemoteServerTable
        dhcpRelayRemoteServerTable OBJECT-TYPE
        SYNTAX	SEQUENCE OF DhcpRelayRemoteServerEntry
        MAX-ACCESS  not-accessible
        STATUS  current
        DESCRIPTION
                 	""
        ::= { dhcpRelay 4 }
        
	dhcpRelayRemoteServerEntry OBJECT-TYPE
        SYNTAX	DhcpRelayRemoteServerEntry
        MAX-ACCESS	not-accessible
        STATUS	current
        DESCRIPTION    	"An entry in dhcpRelayRemoteServerTable."
        INDEX          	{  dhcpRelayVid, dhcpRelayRemoteServerIp }
        ::= { dhcpRelayRemoteServerTable 1 }

        DhcpRelayRemoteServerEntry ::=
           SEQUENCE {
            dhcpRelayVid		          INTEGER,
           	dhcpRelayRemoteServerIp		IpAddress,
        	dhcpRelayRemoteServerRowStatus	RowStatus
           }

        dhcpRelayVid OBJECT-TYPE
        SYNTAX  INTEGER
        MAX-ACCESS  read-only
        STATUS  current
        DESCRIPTION
                      	""
        ::= { dhcpRelayRemoteServerEntry 1 }   
        
        dhcpRelayRemoteServerIp OBJECT-TYPE
        SYNTAX  IpAddress
        MAX-ACCESS  read-only
        STATUS  current
        DESCRIPTION
                      	""
        ::= { dhcpRelayRemoteServerEntry 2 }

        dhcpRelayRemoteServerRowStatus OBJECT-TYPE
        SYNTAX  RowStatus
        MAX-ACCESS  read-create
        STATUS  current
        DESCRIPTION
                     	""
        ::= { dhcpRelayRemoteServerEntry 3 }

--  staticRouteSetup
	staticRouteSetup     	OBJECT IDENTIFIER ::= { ves1724-56fanless 21 }

        maxNumberOfStaticRoutes OBJECT-TYPE
        SYNTAX  INTEGER
        MAX-ACCESS  read-only
        STATUS  current
        DESCRIPTION
                      	""
        ::= { staticRouteSetup 1 }

-- staticRouteTable
        staticRouteTable OBJECT-TYPE
        SYNTAX	SEQUENCE OF StaticRouteEntry
        MAX-ACCESS  not-accessible
        STATUS  current
        DESCRIPTION
                 	""
        ::= { staticRouteSetup 2 }

	staticRouteEntry OBJECT-TYPE
        SYNTAX	StaticRouteEntry
        MAX-ACCESS	not-accessible
        STATUS	current
        DESCRIPTION    	"An entry in staticRouteTable."
        INDEX          	{ staticRouteIp, staticRouteMask }
        ::= { staticRouteTable 1 }

        StaticRouteEntry ::=
           SEQUENCE {
           	staticRouteName		DisplayString,
        	staticRouteIp		IpAddress,
        	staticRouteMask		IpAddress,
        	staticRouteGateway	IpAddress,
        	staticRouteMetric	INTEGER,
        	staticRouteRowStatus	RowStatus
           }

        staticRouteName OBJECT-TYPE
        SYNTAX  DisplayString
        MAX-ACCESS  read-write
        STATUS  current
        DESCRIPTION
                      	""
        ::= { staticRouteEntry 1 }

        staticRouteIp OBJECT-TYPE
        SYNTAX  IpAddress
        MAX-ACCESS  read-only
        STATUS  current
        DESCRIPTION
                     	""
        ::= { staticRouteEntry 2 }

        staticRouteMask OBJECT-TYPE
        SYNTAX  IpAddress
        MAX-ACCESS  read-only
        STATUS  current
        DESCRIPTION
                     	""
        ::= { staticRouteEntry 3 }

        staticRouteGateway OBJECT-TYPE
        SYNTAX  IpAddress
        MAX-ACCESS  read-write
        STATUS  current
        DESCRIPTION
                     	""
        ::= { staticRouteEntry 4 }

        staticRouteMetric OBJECT-TYPE
        SYNTAX  INTEGER
        MAX-ACCESS  read-write
        STATUS  current
        DESCRIPTION
                     	""
        ::= { staticRouteEntry 5 }

        staticRouteRowStatus OBJECT-TYPE
        SYNTAX  RowStatus
        MAX-ACCESS  read-create
        STATUS  current
        DESCRIPTION
                     	""
        ::= { staticRouteEntry 6 }

--  arpInfo
	arpInfo     	OBJECT IDENTIFIER ::= { ves1724-56fanless 22 }

--  arpTable
      	arpTable	OBJECT-TYPE
        SYNTAX	SEQUENCE OF ArpEntry
        MAX-ACCESS  not-accessible
        STATUS  current
        DESCRIPTION
                 	""
        ::= { arpInfo 1 }

		arpEntry OBJECT-TYPE
        SYNTAX	ArpEntry
        MAX-ACCESS	not-accessible
        STATUS	current
        DESCRIPTION    	"An entry in arpTable."
        INDEX          	{ arpIpAddr, arpMacVid }
        ::= { arpTable 1 }

        ArpEntry ::=
           SEQUENCE {
           	arpIndex	INTEGER,
        	arpIpAddr	IpAddress,
        	arpMacAddr	MacAddress,
        	arpMacVid	INTEGER,
        	arpType		INTEGER
           }

        arpIndex OBJECT-TYPE
        SYNTAX  INTEGER
        MAX-ACCESS  read-only
        STATUS  current
        DESCRIPTION
                      	""
        ::= { arpEntry 1 }

        arpIpAddr OBJECT-TYPE
        SYNTAX  IpAddress
        MAX-ACCESS  read-only
        STATUS  current
        DESCRIPTION
                      	""
        ::= { arpEntry 2 }

        arpMacAddr OBJECT-TYPE
        SYNTAX  MacAddress
        MAX-ACCESS  read-only
        STATUS  current
        DESCRIPTION
                      	""
        ::= { arpEntry 3 }

        arpMacVid OBJECT-TYPE
        SYNTAX  INTEGER
        MAX-ACCESS  read-only
        STATUS  current
        DESCRIPTION
                      	""
        ::= { arpEntry 4 }

        arpType OBJECT-TYPE
        SYNTAX  INTEGER {
        	static(1),
        	dynamic(2)
        }
        MAX-ACCESS  read-only
        STATUS  current
        DESCRIPTION
                      	"1-static, 2-dynamic"
        ::= { arpEntry 5 }

        arpflush OBJECT-TYPE
        SYNTAX  INTEGER {
        	enable(1),
        	disable(2)
        }
        MAX-ACCESS  read-write
        STATUS  current
        DESCRIPTION
               "ARP table flush."
        ::= { arpInfo 2 }


-- portOpModeSetup
	portOpModeSetup     	OBJECT IDENTIFIER ::= { ves1724-56fanless 24 }

-- portOpModePortTable

        portOpModePortTable  OBJECT-TYPE
        SYNTAX	SEQUENCE OF PortOpModePortEntry
        MAX-ACCESS  not-accessible
        STATUS  current
        DESCRIPTION
                 	""
        ::= { portOpModeSetup 1 }

	portOpModePortEntry  OBJECT-TYPE
        SYNTAX	PortOpModePortEntry
        MAX-ACCESS	not-accessible
        STATUS	current
        DESCRIPTION    	"An entry in portOpModePortTable."
        INDEX          	{ dot1dBasePort }
        ::= { portOpModePortTable 1 }

        PortOpModePortEntry ::=
           SEQUENCE {
        	portOpModePortSpeedDuplex	INTEGER,
        	portOpModePortFlowCntl	INTEGER,
        	portOpModePortName	OCTET STRING,
        	portOpModePortModuleType	INTEGER,
        	portOpModePortLinkUpType	INTEGER,
        	portOpModePortIntrusionLock	EnabledStatus,
        	portOpModePortLBTestSetup	INTEGER,
        	portOpModePortLBTestStatus	INTEGER,
        	portOpModePortSwCounterReset	INTEGER,
        	portOpModePortVdslCounterReset  INTEGER,
        	portOpModePortVdslStatus  		INTEGER,
        	portOpModePortVdslUptime	OCTET STRING
			,portOpModePortTelephone	OCTET STRING,
                portOpModePortForceOption82	INTEGER
           }

        portOpModePortSpeedDuplex OBJECT-TYPE
        SYNTAX  INTEGER {
        	auto(0),
        	speed_10_half(1),
        	speed_10_full(2),
        	speed_100_half(3),
        	speed_100_full(4),
        	speed_1000_full(5)
        }
        MAX-ACCESS  read-write
        STATUS  current
        DESCRIPTION
                      	""
        ::= { portOpModePortEntry 1 }

        portOpModePortFlowCntl OBJECT-TYPE
        SYNTAX  INTEGER {
        	off(0),
        	on(1)
        }
        MAX-ACCESS  read-write
        STATUS  current
        DESCRIPTION
                     	""
        ::= { portOpModePortEntry 2 }

        portOpModePortName  OBJECT-TYPE
        SYNTAX  OCTET STRING (SIZE(0..9))
        MAX-ACCESS  read-write
        STATUS  current
        DESCRIPTION
                      	""
        ::= { portOpModePortEntry 3 }

        portOpModePortModuleType  OBJECT-TYPE
        SYNTAX  INTEGER {
        	fast_ethernet_10_100(0),
        	gigabit_ethernet_100_1000(1)
        }
        MAX-ACCESS  read-only
        STATUS  current
        DESCRIPTION
                      	""
        ::= { portOpModePortEntry 4 }

        portOpModePortLinkUpType  OBJECT-TYPE
        SYNTAX  INTEGER {
        	down(0),
        	copper(1),
        	fiber(2)
        }
        MAX-ACCESS  read-only
        STATUS  current
        DESCRIPTION
                      	""
        ::= { portOpModePortEntry 5 }

	portOpModePortIntrusionLock OBJECT-TYPE
        SYNTAX  EnabledStatus
        MAX-ACCESS  read-write
        STATUS  current
        DESCRIPTION
                      	""
        ::= { portOpModePortEntry 6 }

   portOpModePortLBTestSetup OBJECT-TYPE
        SYNTAX  INTEGER {
        	internal_loopback_test(1),
        	external_loopback_test(2),
        	vtur_to_vtuo_loopback(3)
        }
        MAX-ACCESS  read-write
        STATUS  current
        DESCRIPTION
               "This entry display latest loopback test status of port while performing loopback test."
        ::= { portOpModePortEntry 7 }

   portOpModePortLBTestStatus OBJECT-TYPE
        SYNTAX  INTEGER {
        	none(0),
        	under_testing(1),
        	success(2),
        	fail(3)
        }
        MAX-ACCESS  read-only
        STATUS  current
        DESCRIPTION
               "This entry display latest loopback test status of port while performing loopback test."
        ::= { portOpModePortEntry 8 }

	portOpModePortSwCounterReset OBJECT-TYPE
        SYNTAX  INTEGER {
        	enable(1),
        	disable(2)
        }
        MAX-ACCESS  read-write
        STATUS  current
        DESCRIPTION
               "This entry resets port SW counter."
        ::= { portOpModePortEntry 9 }

    portOpModePortVdslCounterReset OBJECT-TYPE
        SYNTAX  INTEGER {
        	enable(1),
        	disable(2)
        }
        MAX-ACCESS  read-write
        STATUS  current
        DESCRIPTION
               "This entry resets port VDSL counter."
        ::= { portOpModePortEntry 10 }  
     
     portOpModePortVdslStatus OBJECT-TYPE
        SYNTAX INTEGER {
        	idle(1),
        	standby(2),
        	showtime(3)
        }
        MAX-ACCESS  read-only
        STATUS  current
        DESCRIPTION
               "This entry reports VDSL link current status."
        ::= { portOpModePortEntry 11 }  

     portOpModePortVdslUptime OBJECT-TYPE
        SYNTAX OCTET STRING
        MAX-ACCESS  read-only
        STATUS  current
        DESCRIPTION
               "This entry reports VDSL link current link up time."
        ::= { portOpModePortEntry 12 }          

	portOpModePortTelephone  OBJECT-TYPE
        SYNTAX  OCTET STRING 
        MAX-ACCESS  read-write
        STATUS  current
        DESCRIPTION
                      	"This entry reports port telephone number"
        ::= { portOpModePortEntry 13 }

    portOpModePortForceOption82 OBJECT-TYPE
        SYNTAX  INTEGER {
        	force(1),
        	transparent(2)
        }
        MAX-ACCESS  read-write
        STATUS  current
        DESCRIPTION
               "This entry display the Force Option82 while performing DHCP snooping/DHCP relay/PPPoE option82 service.
               1. force: remove the original option82 and tag option82 in DHCP/PPPoE packets
               2. transparent: transparent DHCP/PPPoE packets"
        ::= { portOpModePortEntry 14 }

-- portOpModePortLBTable

        portOpModePortLBTable  OBJECT-TYPE
        SYNTAX	SEQUENCE OF PortOpModePortLBEntry
        MAX-ACCESS  not-accessible
        STATUS  current
        DESCRIPTION
                 	""
        ::= { portOpModeSetup 2 }

	portOpModePortLBEntry  OBJECT-TYPE
        SYNTAX	PortOpModePortLBEntry
        MAX-ACCESS	not-accessible
        STATUS	current
        DESCRIPTION    	"An entry in portOpModePortLBTable."
        INDEX          	{ dot1dBasePort }
        ::= { portOpModePortLBTable 1 }

        PortOpModePortLBEntry ::=
           SEQUENCE {
        	portOpModePortLBActive	INTEGER,
        	portOpModePortLBNumber	INTEGER,
        	portOpModePortLBCount	INTEGER,
        	portOpModePortLBPktSize	INTEGER
           }

        portOpModePortLBActive OBJECT-TYPE
        SYNTAX  INTEGER {
        	active(1)
        }
        MAX-ACCESS  read-write
        STATUS  current
        DESCRIPTION
                      	""
        ::= { portOpModePortLBEntry 1 }

        portOpModePortLBNumber OBJECT-TYPE
        SYNTAX  INTEGER
        MAX-ACCESS  read-write
        STATUS  current
        DESCRIPTION
                     	""
        ::= { portOpModePortLBEntry 2 }

        portOpModePortLBCount  OBJECT-TYPE
        SYNTAX  INTEGER
        MAX-ACCESS  read-write
        STATUS  current
        DESCRIPTION
                      	""
        ::= { portOpModePortLBEntry 3 }

        portOpModePortLBPktSize  OBJECT-TYPE
        SYNTAX  INTEGER
        MAX-ACCESS  read-write
        STATUS  current
        DESCRIPTION
                      	"Packet size range from 64 bytes to 1518 bytes"
        ::= { portOpModePortLBEntry 4 }


-- portOpModePortLBResultTable

        portOpModePortLBResultTable  OBJECT-TYPE
        SYNTAX	SEQUENCE OF PortOpModePortLBResultEntry
        MAX-ACCESS  not-accessible
        STATUS  current
        DESCRIPTION
                 	""
        ::= { portOpModeSetup 3 }

	portOpModePortLBResultEntry  OBJECT-TYPE
        SYNTAX	PortOpModePortLBResultEntry
        MAX-ACCESS	not-accessible
        STATUS	current
        DESCRIPTION    	"An entry in portOpModePortLBResultTable."
        INDEX          	{ dot1dBasePort }
        ::= { portOpModePortLBResultTable 1 }

        PortOpModePortLBResultEntry ::=
           SEQUENCE {
        	portOpModePortLBMaxRTT	INTEGER,
        	portOpModePortLBMinRTT	INTEGER,
        	portOpModePortLBAvgRTT	INTEGER,
        	portOpModePortLBPktLossRate	INTEGER,
        	portOpModePortLBStatus	INTEGER
           }

        portOpModePortLBMaxRTT OBJECT-TYPE
        SYNTAX  INTEGER
        MAX-ACCESS  read-only
        STATUS  current
        DESCRIPTION
                      	""
        ::= { portOpModePortLBResultEntry 1 }

        portOpModePortLBMinRTT OBJECT-TYPE
        SYNTAX  INTEGER
        MAX-ACCESS  read-only
        STATUS  current
        DESCRIPTION
                     	""
        ::= { portOpModePortLBResultEntry 2 }

        portOpModePortLBAvgRTT  OBJECT-TYPE
        SYNTAX  INTEGER
        MAX-ACCESS  read-only
        STATUS  current
        DESCRIPTION
                      	""
        ::= { portOpModePortLBResultEntry 3 }

        portOpModePortLBPktLossRate  OBJECT-TYPE
        SYNTAX  INTEGER
        MAX-ACCESS  read-only
        STATUS  current
        DESCRIPTION
                      	"Loopback Packet loss rate"
        ::= { portOpModePortLBResultEntry 4 }

        portOpModePortLBStatus OBJECT-TYPE
        SYNTAX  INTEGER {
        	idle(0),
        	in_progress(1),
        	complete(2)
        }
        MAX-ACCESS  read-only
        STATUS  current
        DESCRIPTION
                      	""
        ::= { portOpModePortLBResultEntry 5 }


-- portBasedVlanSetup
	portBasedVlanSetup     	OBJECT IDENTIFIER ::= { ves1724-56fanless 25 }

-- portBasedVlanPortListTable

        portBasedVlanPortListTable  OBJECT-TYPE
        SYNTAX	SEQUENCE OF PortBasedVlanPortListEntry
        MAX-ACCESS  not-accessible
        STATUS  current
        DESCRIPTION
                 	""
        ::= { portBasedVlanSetup 1 }

	portBasedVlanPortListEntry  OBJECT-TYPE
        SYNTAX	PortBasedVlanPortListEntry
        MAX-ACCESS	not-accessible
        STATUS	current
        DESCRIPTION    	"An entry in portBasedVlanPortListTable."
        INDEX          	{ dot1dBasePort }
        ::= { portBasedVlanPortListTable 1 }

        PortBasedVlanPortListEntry ::=
           SEQUENCE {
        	portBasedVlanPortListMembers	OCTET STRING
           }

        portBasedVlanPortListMembers OBJECT-TYPE
        SYNTAX  PortList
        MAX-ACCESS  read-write
        STATUS  current
        DESCRIPTION
                      	""
        ::= { portBasedVlanPortListEntry 1 }


--fault MIB
faultMIB        OBJECT IDENTIFIER ::= { ves1724-56fanless 26 }


-- **************************************************************************
-- Local Textual Conventions
-- **************************************************************************

UtcTimeStamp ::= TEXTUAL-CONVENTION
    STATUS current
    DESCRIPTION
           "Universal Time Coordinated as a 32-bit value that designates
            the number of seconds since Jan 1, 1970 12:00AM."
    SYNTAX  Unsigned32

EventIdNumber ::= TEXTUAL-CONVENTION
   STATUS current
   DESCRIPTION
          "This textual convention describes the index that uniquely
           identifies a fault event type in the entire system. Every fault
           event type, e.g. link down, has a unique EventIdNumber."
   SYNTAX  Integer32

EventSeverity ::= TEXTUAL-CONVENTION
   STATUS current
   DESCRIPTION
          "This textual convention describes the severity of a fault event.
           The decreasing order of severity is shown in the textual
           convention."
   SYNTAX  INTEGER{
             critical (1),
             major (2),
             minor (3),
             informational (4)
           }

EventServiceAffective ::= TEXTUAL-CONVENTION
   STATUS current
   DESCRIPTION
          "This textual convention indicates whether an event is immediately
           service affecting or not."
   SYNTAX  INTEGER{
   	     noServiceAffected (1),
	     serviceAffected (2)
           }


InstanceType ::= TEXTUAL-CONVENTION
    STATUS current
    DESCRIPTION
           "This textual convention describes the type of an instanceId
            associated with each event and by that means specifies how
            the instanceId variable should be intepreted.

            Various instanceId types are specified below to enable fault
            monitoring for different kind of devices from fixed
            configuration pizza boxes to multi chassis nodes. All
            instanceId types may not need to be used in every device
            type.

            Note also that instanceId semantics are element type dependent
            (e.g. different kind of interface naming conventions may be used)
            and thus instanceId usage may vary from element to element.

    =========================================================================
    Type            Description                                 Example form
                                                                of InstanceId
    =========================================================================
    unknown    (1)  unknown type                               - Irrelevant-
    -------------------------------------------------------------------------
    node       (2)  Associated with events originating from          1
                    the node. Used for general events that     (Node number)
                    can not be associated with any specific
                    block. InstanceId value 1 is used for
                    single node equipment.
    -------------------------------------------------------------------------
    shelf      (3)  Associated with events originating from          1
                    the shelf. In the case of fixed       	(shelf number)
                    configuration devices this type is used
                    for events that are associated with the
                    physical enclosure, e.g. faults related
                    to fan etc. InstanceId value 1 is used
                    for single self equipment.
    -------------------------------------------------------------------------
    line       (4)  Associated with events originating from
                    physical interfaces or associated
                    components such as line cards.
                    InstanceId usage examples for faults
                    originating from:
                    - Physical port: Simply port number, e.g. .......1
    -------------------------------------------------------------------------
    switch     (5)  Associated with events originating from          1
                    from a switch chip or a switch card.      (switch number)
                    For single switch equipment InstanceId
                    value 1 is used, for multi swich nodes
                    InstanceId semantics if for further
                    study.
    -------------------------------------------------------------------------
    lsp        (6)  Associated with events originating from          1
                    a particular lsp.                           (lsp index)
                    NOTE: In this case the InstanceName
                    contains the lsp name and InstanceId
                    contains lsp index.
    -------------------------------------------------------------------------
    l2Interface(7)  Associated with events originating from        - TBD -
                    a particular layer 2 interface. Used for
                    layer 2 related events such as L2 control
                    protocol faults. InstanceId semantics is
                    for further study.
    -------------------------------------------------------------------------
    l3Interface(8)  Associated with events originating from        - TBD -
                    a particular layer 3 interface. Used for
                    layer 3 related events such as L3 control
                    protocol faults. InstanceId semantics is
                    for further study.
    -------------------------------------------------------------------------
    rowIndex  (9)   Associated with events reporting about a
                    'logical' or conceptual table that consists
                    of rows.  The Instance Id is the index/key
                    for a row in the table.  The format of the
                    Instance Id will simply be a series of decimal
                    numbers seperated by a '.':
    ========================================================================="

    SYNTAX  INTEGER {
              unknown (1),
              node (2),
              shelf (3),
              line (4),
              switch (5),
              lsp (6),
              l2Interface(7),
              l3Interface(8),
              rowIndex(9)
            }


-- *****************************************************************************
-- Top level structure of this MIB.
-- *****************************************************************************

eventObjects        OBJECT IDENTIFIER ::= { faultMIB  1 }


-- *****************************************************************************
-- Event Table
--
-- Event table reports all currently active fault events. Only normal type of
-- faults (i.e. faults that are not automatically and immediately cleared) are
-- present in the event table. Delta faults (i.e. faults that are automatically
-- cleared) are reported only by using trap messages.
-- *****************************************************************************

eventTable OBJECT-TYPE
    SYNTAX      SEQUENCE OF EventEntry
    MAX-ACCESS  not-accessible
    STATUS      current
    DESCRIPTION
            "A list of currently active fault events. All faults
             of normal type regardless of their severity level
             are recorded in the event table. When a normal
             type fault is cleared it is deleted from the event
             table."
    ::= { eventObjects 1 }

eventEntry OBJECT-TYPE
    SYNTAX      EventEntry
    MAX-ACCESS  not-accessible
    STATUS      current
    DESCRIPTION
            "An entry containing information about an
             event in the event table."
    INDEX   { eventSeqNum }
    ::= { eventTable 1 }

EventEntry ::=
    SEQUENCE {
      eventSeqNum           Integer32,
      eventEventId          EventIdNumber,
      eventName             DisplayString,
      eventInstanceType     InstanceType,
      eventInstanceId       DisplayString,
      eventInstanceName     DisplayString,
      eventSeverity         EventSeverity,
      eventSetTime          UtcTimeStamp,
      eventDescription      DisplayString,
      eventServAffective    EventServiceAffective, 
      eventInstanceIdNumber Integer32 
   }

eventSeqNum OBJECT-TYPE
    SYNTAX      Integer32
    MAX-ACCESS  read-only
    STATUS      current
    DESCRIPTION
            "This variable represents the sequence number of an event.
             Sequence number is incremented monotonically starting
             from 0 until it reaches its maximum and wraps around back
             to 0.

             Sequence number is incremented when
             - the state of a normal type fault is set on (the same sequence
             number is present in the events table as well as in the trap
             that is sent to notify about the fault on event)
             - delta event occurs (sequence number present in trap message)
             - the state of a normal type fault is set off (sequence number
             present in trap that is sent to notify for clearing)."
    ::= { eventEntry 1 }

eventEventId OBJECT-TYPE
    SYNTAX      EventIdNumber
    MAX-ACCESS  read-only
    STATUS      current
    DESCRIPTION
            "This variable represents the event ID which uniquely
             identifies the event in the entire system."
    ::= { eventEntry 2 }

eventName OBJECT-TYPE
    SYNTAX      DisplayString (SIZE (0..40))
    MAX-ACCESS  read-only
    STATUS      current
    DESCRIPTION
            "This variable represents the name of the event, for
             example 'Ethernet Link Down'"
    ::= { eventEntry 3 }

eventInstanceType OBJECT-TYPE
    SYNTAX      InstanceType
    MAX-ACCESS  read-only
    STATUS      current
    DESCRIPTION
            "This variable represents the type of InstanceId of a
             particular event in the event table. In brief
             the instanceType refers to the type of sub-component
             generating this event in the system, for example
             switch (5). For more details see the textual
             conventions section.

             AFFECTS:   eventInstanceId,
                        eventInstanceName"
    ::= { eventEntry 4 }

eventInstanceId OBJECT-TYPE
    SYNTAX  DisplayString
    MAX-ACCESS  read-only
    STATUS      current
    DESCRIPTION
            "This variable represents the InstanceId of a particular
             event in the event current table. In brief the instanceId
             refers to the sub-component generating this event in the
             system, for example '1' for port 1. For more details see
             the textual conventions section.

             DEPENDS ON:  eventInstanceType"
    ::= { eventEntry 5 }

eventInstanceName OBJECT-TYPE
    SYNTAX      DisplayString
    MAX-ACCESS  read-only
    STATUS      current
    DESCRIPTION
            "This variable is mainly used to store additional information
             about the sub-component that is generating an event. For
             example this field may specify what cooling fan is faulty.

             DEPENDS ON:  eventInstanceType"
    ::= { eventEntry 6 }

eventSeverity OBJECT-TYPE
    SYNTAX      EventSeverity
    MAX-ACCESS  read-only
    STATUS      current
    DESCRIPTION
            "This variable dictates the urgency of action when a event
             occurs. There are four severity levels - Critical, Major,
             Minor, and Informational.  Critical events are those, which
             require immediate operator intervention to prevent/reduce
             system down time. Major events require quick attention and
             Minor events possibly require some attention. Informational
             events indicate the occurrence of events that may need to be
             investigated."
    ::= { eventEntry 7 }

eventSetTime OBJECT-TYPE
    SYNTAX      UtcTimeStamp
    MAX-ACCESS  read-only
    STATUS      current
    DESCRIPTION
            "This table contains only normal events and this variable
             represents the time when the event become active, i.e. the
             number of seconds since Jan 1, 1970 12:00AM."
    ::= { eventEntry 8 }


eventDescription OBJECT-TYPE
    SYNTAX      DisplayString (SIZE (0..255))
    MAX-ACCESS  read-only
    STATUS      current
    DESCRIPTION
            "This variable contains a description of the event and reasons
             behind the event. This is a free format alpha-numeric string
             that is set by the entity generating this event. This variable
             may be empty if there is no usefull information to report.
             The maximum length of this string is 255 characters."
    ::= { eventEntry 9 }

eventServAffective OBJECT-TYPE
    SYNTAX      EventServiceAffective
    MAX-ACCESS  read-only
    STATUS      current
    DESCRIPTION
            "This variable indicates whether the event is service affective or not"
    ::= { eventEntry 10 }

eventInstanceIdNumber OBJECT-TYPE
    SYNTAX  Integer32
    MAX-ACCESS  read-only
    STATUS      current
    DESCRIPTION
            "This variable represents the InstanceId of a particular 
             event in the event current table. In brief the instanceId 
             refers to the sub-component generating this event in the 
             system, for example '1' for port 1. For more details see 
             the textual conventions section.

             DEPENDS ON:  eventInstanceType"
    ::= { eventEntry 11 }


-- fault Trap MIB
faultTrapsMIB        OBJECT IDENTIFIER ::= { ves1724-56fanless 27 }

trapInfoObjects             OBJECT IDENTIFIER ::= { faultTrapsMIB 1}
trapNotifications           OBJECT IDENTIFIER ::= { faultTrapsMIB 2}


-- **************************************************************************
-- Local Textual Conventions
-- **************************************************************************

EventPersistence ::= TEXTUAL-CONVENTION
   STATUS current
   DESCRIPTION
          "This textual convention indicates whether the event is delta
           (automatically and immediately cleared) or normal (not
           automatically cleared)."
   SYNTAX  INTEGER{
   	     normal (1),
	     delta (2)
           }


-- **************************************************************************
-- Trap information object definitions
-- **************************************************************************

trapRefSeqNum OBJECT-TYPE
    SYNTAX      Integer32
    MAX-ACCESS  read-only
    STATUS      current
    DESCRIPTION
            "Indicates the former sequence number of a cleared event
             in the event table. Not intended to read but only used in
             trap notifications."
    ::= { trapInfoObjects 1 }

trapPersistence OBJECT-TYPE
    SYNTAX      EventPersistence
    MAX-ACCESS  read-only
    STATUS      current
    DESCRIPTION
            "Indicates whether the event is delta (automatically and
             immediately cleared) or normal (not automatically cleared).
             Not intended to read but only used in trap notifications."
    ::= { trapInfoObjects 2 }

trapSenderNodeId OBJECT-TYPE
    SYNTAX      Integer32
    MAX-ACCESS  read-only
    STATUS      current
    DESCRIPTION
            "Represents the node ID of the sending network element. If not
             supported should be set to 0. Not intended to read but only
             used in trap notifications."
    ::= { trapInfoObjects 3 }

trapSenderStatus OBJECT-TYPE
    SYNTAX      Integer32
    MAX-ACCESS  read-only
    STATUS      current
    DESCRIPTION
            "Represents the trap status. 0 means cleared, 1 means happened."
    ::= { trapInfoObjects 4 }
    


-- ***************************************************************************
-- Trap definitions
-- ***************************************************************************

eventOnTrap NOTIFICATION-TYPE
         OBJECTS {
                  eventSeqNum,
                  eventEventId,
                  eventName,
                  eventSetTime,
                  eventSeverity,
                  eventInstanceType,
                  eventInstanceId,
                  eventInstanceName,
                  eventServAffective,
                  eventDescription,
                  eventInstanceIdNumber,
                  trapPersistence,
                  trapSenderNodeId,
                  trapSenderStatus,                   
                  sysObjectID}
         STATUS current
         DESCRIPTION
           "This trap is used to inform network management system that a delta
           fault event (events that are automatically cleared) has occured
           or a normal fault event (not automatically cleared) state has
           been set on.

           Objects are used as follows:
           - eventSeqNum is the sequence number of the event. For normal
           type of events must equal to the sequence number of the event
           in the events table.
           - eventEventId specifies what fault event has occured.
           - eventName specifies the name of the fault event.
           - eventSetTime indicates when fault event has occured
           (delta events) or when fault has been set on (normal events).
           - eventSeverity reports the severity level of the event.
           - eventInstanceType indicates what kind of object is faulty.
           - eventInstanceId specifies what instance is faulty.
           - eventInstanceName may contain textual description for
           the faulty object.
           - eventServAffective specifies whether the event is
           immediately service affcetive.
           - eventDescription reports possible additional information about the event.
           - trapPersistence tells whether this event is a delta or normal event.
           - trapSenderNodeId specifies the node ID of the sending network element if
           configuring it is supported for the network element, otherwise 0.
           - trapSenderStatus specifes the trap status. 
           - sysObjectID specifies what kind of equipment reports the fault event.

           For more information see the eventTable specification"
         ::= { trapNotifications 1 }

eventClearedTrap NOTIFICATION-TYPE
         OBJECTS {
                  eventSeqNum,
                  eventEventId,
                  eventSetTime,
                  eventInstanceType,
                  eventInstanceId,
                  eventInstanceIdNumber,
                  trapRefSeqNum,
                  trapSenderNodeId,
                  trapSenderStatus,
                  sysObjectID}
         STATUS current
         DESCRIPTION
           "This trap is used to inform network management system that a normal
           type fault event has been cleared (state set off).

           Objects are used as follows:
           - eventSeqNum is the sequence number of the this clearing event. Note that
           the sequence number of the cleared event is reported in the trapRefSeqNum
           object.
           - eventEventId specifies what event has been cleared.
           - eventSetTime indicates when fault event has been cleared.
           - eventInstanceType indicates what kind of object has been
           faulty.
           - eventInstanceId specifies what instance has been faulty.
           - trapRefSeqNum specifies the sequence number of the cleared event (i.e.
           the sequence number was assigned for the event in the events table).
           - trapSenderNodeId specifies the node ID of the sending network element if
           configuring it is supported for the network element, otherwise 0.
           - sysObjectID specifies what kind of equipment reports the clearing event.

           For more information see the eventTable specification"
         ::= { trapNotifications 2 }




--  multicastPortSetup
	multicastPortSetup     	OBJECT IDENTIFIER ::= { ves1724-56fanless 28 }

        multicastPortTable	OBJECT-TYPE
        SYNTAX	SEQUENCE OF MulticastPortEntry
        MAX-ACCESS  not-accessible
        STATUS  current
        DESCRIPTION
                 	""
        ::= { multicastPortSetup 1 }

	multicastPortEntry OBJECT-TYPE
        SYNTAX	MulticastPortEntry
        MAX-ACCESS	not-accessible
        STATUS	current
        DESCRIPTION    	"An entry in multicastPortTable."
        INDEX          	{ dot1dBasePort }
        ::= { multicastPortTable 1 }

        MulticastPortEntry ::=
	SEQUENCE {
        	multicastPortImmediateLeave		EnabledStatus,
        	multicastPortMaxGroupLimited		EnabledStatus,
        	multicastPortMaxOfGroup			INTEGER,
        	multicastPortIgmpFilteringProfile	DisplayString,
        	multicastPortQueryMode			INTEGER,
		igmpMsgMaxLimited			EnabledStatus,        	
        	igmpMsgLimit				INTEGER
        }

        multicastPortImmediateLeave OBJECT-TYPE
        SYNTAX  EnabledStatus
        MAX-ACCESS  read-write
        STATUS  current
        DESCRIPTION
                      	""
        ::= { multicastPortEntry 1 }

        multicastPortMaxGroupLimited OBJECT-TYPE
        SYNTAX  EnabledStatus
        MAX-ACCESS  read-write
        STATUS  current
        DESCRIPTION
                      	""
        ::= { multicastPortEntry 2 }

        multicastPortMaxOfGroup OBJECT-TYPE
        SYNTAX  INTEGER
        MAX-ACCESS  read-write
        STATUS  current
        DESCRIPTION
                      	"0..255"
        ::= { multicastPortEntry 3 }

        multicastPortIgmpFilteringProfile OBJECT-TYPE
        SYNTAX  DisplayString
        MAX-ACCESS  read-write
        STATUS  current
        DESCRIPTION
                      	""
        ::= { multicastPortEntry 4 }
        
        
        multicastPortQueryMode OBJECT-TYPE
        SYNTAX  INTEGER {
        	auto_mode(1),
        	fix_mode(2),
        	edge_mode(3)
        }
        MAX-ACCESS  read-write
        STATUS  current
        DESCRIPTION
                      	"Specify query mode for each port"
        ::= { multicastPortEntry 5 }

        igmpMsgMaxLimited OBJECT-TYPE
        SYNTAX  EnabledStatus
        MAX-ACCESS  read-write
        STATUS  current
        DESCRIPTION
                      	""
        ::= { multicastPortEntry 6 }

        igmpMsgLimit OBJECT-TYPE
        SYNTAX  INTEGER
        MAX-ACCESS  read-write
        STATUS  current
        DESCRIPTION
                      	"0..255"
        ::= { multicastPortEntry 7 }        

-- multicastStatus
	multicastStatus    	OBJECT IDENTIFIER ::= { ves1724-56fanless 29 }

        multicastStatusTable	OBJECT-TYPE
        SYNTAX	SEQUENCE OF MulticastStatusEntry
        MAX-ACCESS  not-accessible
        STATUS  current
        DESCRIPTION
                 	""
        ::= { multicastStatus 1 }

	multicastStatusEntry OBJECT-TYPE
        SYNTAX	MulticastStatusEntry
        MAX-ACCESS	not-accessible
        STATUS	current
        DESCRIPTION    	"An entry in multicastStatusTable."
        INDEX          	{ multicastStatusVlanID, multicastStatusPort, multicastStatusGroup }
        ::= { multicastStatusTable 1 }

        MulticastStatusEntry ::=
	SEQUENCE {
        	multicastStatusIndex    INTEGER,
        	multicastStatusVlanID	INTEGER,
        	multicastStatusPort	INTEGER,
        	multicastStatusGroup	IpAddress,
        	multicastStatusJoinCounter    INTEGER,
        	multicastStatusLeaveCounter    INTEGER
         }

        multicastStatusIndex OBJECT-TYPE
        SYNTAX  INTEGER
        MAX-ACCESS  read-only
        STATUS  current
        DESCRIPTION
                      	""
        ::= { multicastStatusEntry 1 }

        multicastStatusVlanID OBJECT-TYPE
        SYNTAX  INTEGER
        MAX-ACCESS  read-only
        STATUS  current
        DESCRIPTION
                      	""
        ::= { multicastStatusEntry 2 }

        multicastStatusPort OBJECT-TYPE
        SYNTAX  INTEGER
        MAX-ACCESS  read-only
        STATUS  current
        DESCRIPTION
                      	""
        ::= { multicastStatusEntry 3 }

        multicastStatusGroup OBJECT-TYPE
        SYNTAX  IpAddress
        MAX-ACCESS  read-only
        STATUS  current
        DESCRIPTION
                      	""
        ::= { multicastStatusEntry 4 }

        multicastStatusJoinCounter OBJECT-TYPE
        SYNTAX  INTEGER
        MAX-ACCESS  read-only
        STATUS  current
        DESCRIPTION
                      	""
        ::= { multicastStatusEntry 5 }
        
        multicastStatusLeaveCounter OBJECT-TYPE
        SYNTAX  INTEGER
        MAX-ACCESS  read-only
        STATUS  current
        DESCRIPTION
                      	""
        ::= { multicastStatusEntry 6 }        

        igmpCountTable	OBJECT-TYPE
        SYNTAX	SEQUENCE OF IgmpCountEntry
        MAX-ACCESS  not-accessible
        STATUS  current
        DESCRIPTION
                 	"A count table of igmp query/report/leave message."
        ::= { multicastStatus 2 }    
             
-- igmpCountStatus     
	igmpCountEntry OBJECT-TYPE
        SYNTAX	IgmpCountEntry
        MAX-ACCESS	not-accessible
        STATUS	current
        DESCRIPTION    	"An entry in igmpCountTable."
        INDEX          	{ igmpCountIndex }
        ::= { igmpCountTable 1 }

        IgmpCountEntry ::=
		SEQUENCE {
        	igmpCountIndex    		INTEGER,
        	igmpCountInQuery		INTEGER,
        	igmpCountInReport		INTEGER,
        	igmpCountInLeave		INTEGER,        	
        	igmpCountInQueryDrop   	INTEGER,
        	igmpCountInReportDrop   INTEGER,
        	igmpCountInLeaveDrop   	INTEGER,
        	igmpCountOutQuery   	INTEGER,
        	igmpCountOutReport   	INTEGER,
        	igmpCountOutLeave   	INTEGER
        }

        igmpCountIndex OBJECT-TYPE
        SYNTAX  INTEGER
        MAX-ACCESS  read-only
        STATUS  current
        DESCRIPTION
                      	"Index of IgmpCountEntry. 0 means total count in whole system"
        ::= { igmpCountEntry 1 }

        igmpCountInQuery OBJECT-TYPE
        SYNTAX  INTEGER
        MAX-ACCESS  read-only
        STATUS  current
        DESCRIPTION
                      	""
        ::= { igmpCountEntry 2 }

        igmpCountInReport OBJECT-TYPE
        SYNTAX  INTEGER
        MAX-ACCESS  read-only
        STATUS  current
        DESCRIPTION
                      	""
        ::= { igmpCountEntry 3 }

        igmpCountInLeave OBJECT-TYPE
        SYNTAX  INTEGER
        MAX-ACCESS  read-only
        STATUS  current
        DESCRIPTION
                      	""
        ::= { igmpCountEntry 4 }
        
        igmpCountInQueryDrop OBJECT-TYPE
        SYNTAX  INTEGER
        MAX-ACCESS  read-only
        STATUS  current
        DESCRIPTION
                      	""
        ::= { igmpCountEntry 5 }
        
        igmpCountInReportDrop OBJECT-TYPE
        SYNTAX  INTEGER
        MAX-ACCESS  read-only
        STATUS  current
        DESCRIPTION
                      	""
        ::= { igmpCountEntry 6 }        
        
        igmpCountInLeaveDrop OBJECT-TYPE
        SYNTAX  INTEGER
        MAX-ACCESS  read-only
        STATUS  current
        DESCRIPTION
                      	""
        ::= { igmpCountEntry 7 }                

        igmpCountOutQuery OBJECT-TYPE
        SYNTAX  INTEGER
        MAX-ACCESS  read-only
        STATUS  current
        DESCRIPTION
                      	""
        ::= { igmpCountEntry 8 }                
        
        igmpCountOutReport OBJECT-TYPE
        SYNTAX  INTEGER
        MAX-ACCESS  read-only
        STATUS  current
        DESCRIPTION
                      	""
        ::= { igmpCountEntry 9 }          

        igmpCountOutLeave OBJECT-TYPE
        SYNTAX  INTEGER
        MAX-ACCESS  read-only
        STATUS  current
        DESCRIPTION
                      	""
        ::= { igmpCountEntry 10 }     

       multicastVlanStatusTable	OBJECT-TYPE
        SYNTAX	SEQUENCE OF MulticastVlanStatusEntry
        MAX-ACCESS  not-accessible
        STATUS  current
        DESCRIPTION
                 	""
        ::= { multicastStatus 3 }

-- multicastVlanStatusTable
	multicastVlanStatusEntry OBJECT-TYPE
        SYNTAX	MulticastVlanStatusEntry
        MAX-ACCESS	not-accessible
        STATUS	current
        DESCRIPTION    	"An entry in multicastVlanStatusTable."
        INDEX          	{ multicastVlanStatusVlanID }
        ::= { multicastVlanStatusTable 1 }

        MulticastVlanStatusEntry ::=
	SEQUENCE {
        	multicastVlanStatusVlanID    INTEGER,
        	multicastVlanStatusType	INTEGER,
        	multicastVlanQueryPort	PortList,
        	multicastVlanQuerySrcIp	IpAddress
         }

        multicastVlanStatusVlanID OBJECT-TYPE
        SYNTAX  INTEGER
        MAX-ACCESS  read-only
        STATUS  current
        DESCRIPTION
                      	""
        ::= { multicastVlanStatusEntry 1 }

        multicastVlanStatusType OBJECT-TYPE
        SYNTAX  INTEGER {
		   	dynamic(1),
		 	mvr (2),
			static(3)
        }
        MAX-ACCESS  read-only
        STATUS  current
        DESCRIPTION
                      	""
        ::= { multicastVlanStatusEntry 2 }

        multicastVlanQueryPort OBJECT-TYPE
        SYNTAX  PortList
        MAX-ACCESS  read-only
        STATUS  current
        DESCRIPTION
                      	""
        ::= { multicastVlanStatusEntry 3 }

		multicastVlanQuerySrcIp OBJECT-TYPE
		SYNTAX  IpAddress
        MAX-ACCESS  read-only
        STATUS  current
		DESCRIPTION
						""
		::= { multicastVlanStatusEntry 4 }

-- igmpCounterPortTable

        igmpCounterPortTable OBJECT-TYPE
        SYNTAX	SEQUENCE OF IgmpCounterPortEntry
        MAX-ACCESS  not-accessible
        STATUS  current
        DESCRIPTION
                 	""
        ::= { multicastStatus 4 }

	igmpCounterPortEntry OBJECT-TYPE
        SYNTAX	IgmpCounterPortEntry
        MAX-ACCESS	not-accessible
        STATUS	current
        DESCRIPTION    	"An entry in igmpCounterPortTable."
        INDEX          	{ dot1dBasePort }
        ::= { igmpCounterPortTable 1 }

        IgmpCounterPortEntry ::=
           SEQUENCE {
        	igmpCounterPortJoin		Counter32,
		igmpCounterPortLeave		Counter32,
		igmpCounterPortActiveGroup	INTEGER,
		igmpCounterPortQuery		Counter32
           }

        igmpCounterPortJoin OBJECT-TYPE
        SYNTAX  Counter32
        MAX-ACCESS  read-only
        STATUS  current
        DESCRIPTION
                      	"Join counter for the port."
        ::= { igmpCounterPortEntry 1 }

        igmpCounterPortLeave OBJECT-TYPE
        SYNTAX  Counter32
        MAX-ACCESS  read-only
        STATUS  current
        DESCRIPTION
                      	"Leave counter for the port."
        ::= { igmpCounterPortEntry 2 }

        igmpCounterPortActiveGroup OBJECT-TYPE
        SYNTAX  INTEGER
        MAX-ACCESS  read-only
        STATUS  current
        DESCRIPTION
                      	"Current active group for the port"
        ::= { igmpCounterPortEntry 3 }
 
        igmpCounterPortQuery OBJECT-TYPE
        SYNTAX  Counter32
        MAX-ACCESS  read-only
        STATUS  current
        DESCRIPTION
                      	"Query counter for the port."
        ::= { igmpCounterPortEntry 4 } 
------------------------------------------
--  igmp counters for specific vid
-- igmpCounterVlanTable

        igmpCounterVlanTable OBJECT-TYPE
        SYNTAX	SEQUENCE OF IgmpCounterVlanEntry
        MAX-ACCESS  not-accessible
        STATUS  current
        DESCRIPTION
                 	""
        ::= { multicastStatus 5 }

	igmpCounterVlanEntry OBJECT-TYPE
        SYNTAX	IgmpCounterVlanEntry
        MAX-ACCESS	not-accessible
        STATUS	current
        DESCRIPTION    	"An entry in igmpCounterVlanTable."
        INDEX          	{ dot1qVlanIndex  }
        ::= { igmpCounterVlanTable 1 }

        IgmpCounterVlanEntry ::=
           SEQUENCE {
        	igmpCounterVlanJoin		Counter32,
		igmpCounterVlanLeave		Counter32,
		igmpCounterVlanActiveGroup	INTEGER,
		igmpCounterVlanQuery		Counter32
           }

        igmpCounterVlanJoin OBJECT-TYPE
        SYNTAX  Counter32
        MAX-ACCESS  read-only
        STATUS  current
        DESCRIPTION
                      	"Join counter for the Vlan."
        ::= { igmpCounterVlanEntry 1 }

        igmpCounterVlanLeave OBJECT-TYPE
        SYNTAX  Counter32
        MAX-ACCESS  read-only
        STATUS  current
        DESCRIPTION
                      	"Leave counter for the Vlan."
        ::= { igmpCounterVlanEntry 2 }

        igmpCounterVlanActiveGroup OBJECT-TYPE
        SYNTAX  INTEGER
        MAX-ACCESS  read-only
        STATUS  current
        DESCRIPTION
                      	"Current active group for the Vlan"
        ::= { igmpCounterVlanEntry 3 }
 
        igmpCounterVlanQuery OBJECT-TYPE
        SYNTAX  Counter32
        MAX-ACCESS  read-only
        STATUS  current
        DESCRIPTION
                      	"Query counter for the Vlan."
        ::= { igmpCounterVlanEntry 4 }
 
        multicastCurrentGroupStatusTable	OBJECT-TYPE
        SYNTAX	SEQUENCE OF MulticastCurrentGroupStatusEntry
        MAX-ACCESS  not-accessible
        STATUS  current
        DESCRIPTION
                 	""
        ::= { multicastStatus 6 }
             
	multicastCurrentGroupStatusEntry OBJECT-TYPE
        SYNTAX	MulticastCurrentGroupStatusEntry
        MAX-ACCESS	not-accessible
        STATUS	current
        DESCRIPTION    	"An entry in multicastCurrentGroupStatusTable."
        INDEX          	{ multicastStatusVlanID, multicastStatusGroup }
        ::= { multicastCurrentGroupStatusTable 1 }

        MulticastCurrentGroupStatusEntry ::=
	SEQUENCE {
        	multicastCurrentNumberOfActivePort    INTEGER
         }

        multicastCurrentNumberOfActivePort OBJECT-TYPE
        SYNTAX  INTEGER
        MAX-ACCESS  read-only
        STATUS  current
        DESCRIPTION
                      	"Current number Of active port."
        ::= { multicastCurrentGroupStatusEntry 1 }

-- multicastClientSrcIp

        multicastClientSrcIpTable	OBJECT-TYPE
        SYNTAX	SEQUENCE OF MulticastClientSrcIpEntry
        MAX-ACCESS  not-accessible
        STATUS  current
        DESCRIPTION
                 	""
        ::= { multicastStatus 7 }
               
	multicastClientSrcIpEntry OBJECT-TYPE
        SYNTAX	MulticastClientSrcIpEntry
        MAX-ACCESS	not-accessible
        STATUS	current
        DESCRIPTION    	"An entry in multicastClientSrcIpTable."
        INDEX          	{ multicastStatusVlanID, multicastStatusPort, multicastStatusGroup, multicastClientSrcIpIndex }
        ::= { multicastClientSrcIpTable 1 }

        MulticastClientSrcIpEntry ::=
	SEQUENCE {
        	multicastClientSrcIpIndex    INTEGER,
        	multicastClientSrcIpAddress	IpAddress
         }

        multicastClientSrcIpIndex OBJECT-TYPE
        SYNTAX  INTEGER
        MAX-ACCESS  read-only
        STATUS  current
        DESCRIPTION
                      	""
        ::= { multicastClientSrcIpEntry 1 }

        multicastClientSrcIpAddress OBJECT-TYPE
        SYNTAX  IpAddress
        MAX-ACCESS  read-only
        STATUS  current
        DESCRIPTION
                      	""
        ::= { multicastClientSrcIpEntry 2 }
        
-- mgmdStatusTable

        mgmdStatusTable	OBJECT-TYPE
        SYNTAX	SEQUENCE OF MGMDStatusEntry
        MAX-ACCESS  not-accessible
        STATUS  current
        DESCRIPTION
                 	""
        ::= { multicastStatus 8 }   
             
	mgmdStatusEntry OBJECT-TYPE
        SYNTAX	MGMDStatusEntry
        MAX-ACCESS	not-accessible
        STATUS	current
        DESCRIPTION    	"An entry in mgmdStatusTable."
        INDEX          	{ mgmdStatusVlanID, mgmdStatusPort, mgmdStatusGroupAddressType, mgmdStatusGroupAddress }
        ::= { mgmdStatusTable 1 }

        MGMDStatusEntry ::=
	SEQUENCE {
        	mgmdStatusIndex			INTEGER,
        	mgmdStatusVlanID		INTEGER,
        	mgmdStatusPort			INTEGER,
    		mgmdStatusGroupAddressType	InetAddressType,
   		mgmdStatusGroupAddress		InetAddress ,
   			mgmdStatusGroupFilterMode	INTEGER,
   			mgmdStatusGroupUpTime	DisplayString
         }

        mgmdStatusIndex OBJECT-TYPE
        SYNTAX  INTEGER
        MAX-ACCESS  read-only
        STATUS  current
        DESCRIPTION
                      	""
        ::= { mgmdStatusEntry 1 }

        mgmdStatusVlanID OBJECT-TYPE
        SYNTAX  INTEGER
        MAX-ACCESS  read-only
        STATUS  current
        DESCRIPTION
                      	""
        ::= { mgmdStatusEntry 2 }

        mgmdStatusPort OBJECT-TYPE
        SYNTAX  INTEGER
        MAX-ACCESS  read-only
        STATUS  current
        DESCRIPTION
                      	""
        ::= { mgmdStatusEntry 3 }
        
        mgmdStatusGroupAddressType OBJECT-TYPE
        SYNTAX  InetAddressType { ipv4(1), ipv6(2) }
        MAX-ACCESS  read-only
        STATUS  current
        DESCRIPTION
              "The address type of the mgmdStatusGroupAddress entry."
        ::= { mgmdStatusEntry 4 }
        
        mgmdStatusGroupAddress OBJECT-TYPE
        SYNTAX  InetAddress (SIZE(4|16))
        MAX-ACCESS  read-only
        STATUS  current
        DESCRIPTION
                      	""
        ::= { mgmdStatusEntry 5 }
        
 	mgmdStatusGroupFilterMode OBJECT-TYPE
    	SYNTAX     INTEGER {include (1),exclude (2) }
	MAX-ACCESS read-only
	STATUS     current
	DESCRIPTION
            "The current cache state, applicable to MGMDv3-compatible
            nodes.  The value indicates whether the state is INCLUDE or
            EXCLUDE."

	::= { mgmdStatusEntry 6 }
	
	     mgmdStatusGroupUpTime OBJECT-TYPE
    	SYNTAX     DisplayString
		MAX-ACCESS read-only
		STATUS     current
		DESCRIPTION
            "The value specifies the group up time of indicated
            multicast group."

		::= { mgmdStatusEntry 7 }
	
-- mgmdCountTable    
        mgmdCountTable	OBJECT-TYPE
        SYNTAX	SEQUENCE OF MGMDCountEntry
        MAX-ACCESS  not-accessible
        STATUS  current
        DESCRIPTION
                 	"A count table of igmp/MLD query/report/leave message."
        ::= { multicastStatus 9 }    
        
	mgmdCountEntry OBJECT-TYPE
        SYNTAX	MGMDCountEntry
        MAX-ACCESS	not-accessible
        STATUS	current
        DESCRIPTION    	"An entry in mgmdCountTable."
        INDEX          	{ mgmdCountIndex }
        ::= { mgmdCountTable 1 }

        MGMDCountEntry ::=
		SEQUENCE {
        	mgmdCountIndex    		INTEGER,
        	mgmdCountInQuery		INTEGER,
        	mgmdCountInReport		INTEGER,
        	mgmdCountInLeave		INTEGER,        	
        	mgmdCountInQueryDrop   	INTEGER,
        	mgmdCountInReportDrop   INTEGER,
        	mgmdCountInLeaveDrop   	INTEGER,
        	mgmdCountOutQuery   	INTEGER,
        	mgmdCountOutReport   	INTEGER,
        	mgmdCountOutLeave   	INTEGER
        }

        mgmdCountIndex OBJECT-TYPE
        SYNTAX  INTEGER
        MAX-ACCESS  read-only
        STATUS  current
        DESCRIPTION
                      	"Index of mgmdCountEntry. 0 means total count in whole system"
        ::= { mgmdCountEntry 1 }

        mgmdCountInQuery OBJECT-TYPE
        SYNTAX  INTEGER
        MAX-ACCESS  read-only
        STATUS  current
        DESCRIPTION
                      	""
        ::= { mgmdCountEntry 2 }

        mgmdCountInReport OBJECT-TYPE
        SYNTAX  INTEGER
        MAX-ACCESS  read-only
        STATUS  current
        DESCRIPTION
                      	""
        ::= { mgmdCountEntry 3 }

        mgmdCountInLeave OBJECT-TYPE
        SYNTAX  INTEGER
        MAX-ACCESS  read-only
        STATUS  current
        DESCRIPTION
                      	""
        ::= { mgmdCountEntry 4 }
        
        mgmdCountInQueryDrop OBJECT-TYPE
        SYNTAX  INTEGER
        MAX-ACCESS  read-only
        STATUS  current
        DESCRIPTION
                      	""
        ::= { mgmdCountEntry 5 }
        
        mgmdCountInReportDrop OBJECT-TYPE
        SYNTAX  INTEGER
        MAX-ACCESS  read-only
        STATUS  current
        DESCRIPTION
                      	""
        ::= { mgmdCountEntry 6 }        
        
        mgmdCountInLeaveDrop OBJECT-TYPE
        SYNTAX  INTEGER
        MAX-ACCESS  read-only
        STATUS  current
        DESCRIPTION
                      	""
        ::= { mgmdCountEntry 7 }                

        mgmdCountOutQuery OBJECT-TYPE
        SYNTAX  INTEGER
        MAX-ACCESS  read-only
        STATUS  current
        DESCRIPTION
                      	""
        ::= { mgmdCountEntry 8 }                
        
        mgmdCountOutReport OBJECT-TYPE
        SYNTAX  INTEGER
        MAX-ACCESS  read-only
        STATUS  current
        DESCRIPTION
                      	""
        ::= { mgmdCountEntry 9 }          

        mgmdCountOutLeave OBJECT-TYPE
        SYNTAX  INTEGER
        MAX-ACCESS  read-only
        STATUS  current
        DESCRIPTION
                      	""
        ::= { mgmdCountEntry 10 }     
        
-- mgmdVlanStatusTable
       mgmdVlanStatusTable	OBJECT-TYPE
        SYNTAX	SEQUENCE OF MGMDVlanStatusEntry
        MAX-ACCESS  not-accessible
        STATUS  current
        DESCRIPTION
                 	""
        ::= { multicastStatus 10 }


	mgmdVlanStatusEntry OBJECT-TYPE
        SYNTAX	MGMDVlanStatusEntry
        MAX-ACCESS	not-accessible
        STATUS	current
        DESCRIPTION    	"An entry in mgmdVlanStatusTable."
        INDEX          	{ mgmdVlanStatusVlanID }
        ::= { mgmdVlanStatusTable 1 }

        MGMDVlanStatusEntry ::=
	SEQUENCE {
        	mgmdVlanStatusVlanID    INTEGER,
        	mgmdVlanStatusType	INTEGER,
        	mgmdVlanQueryPort	PortList,
        	mgmdVlanQuerySrcIpType	InetAddressType,        	
        	mgmdVlanQuerySrcIp	InetAddress
         }

        mgmdVlanStatusVlanID OBJECT-TYPE
        SYNTAX  INTEGER
        MAX-ACCESS  read-only
        STATUS  current
        DESCRIPTION
                      	""
        ::= { mgmdVlanStatusEntry 1 }

        mgmdVlanStatusType OBJECT-TYPE
        SYNTAX  INTEGER {
			dynamic(1),
			mvr (2),
			static(3)
        }
        MAX-ACCESS  read-only
        STATUS  current
        DESCRIPTION
                      	""
        ::= { mgmdVlanStatusEntry 2 }

        mgmdVlanQueryPort OBJECT-TYPE
        SYNTAX  PortList
        MAX-ACCESS  read-only
        STATUS  current
        DESCRIPTION
                      	""
        ::= { mgmdVlanStatusEntry 3 }
 
        mgmdVlanQuerySrcIpType OBJECT-TYPE
        SYNTAX  InetAddressType { ipv4(1), ipv6(2) }
        MAX-ACCESS  read-only
        STATUS  current
        DESCRIPTION
              "The address type of the mgmdVlanQuerySrcIp entry."
        ::= { mgmdVlanStatusEntry 4 }
               
        mgmdVlanQuerySrcIp OBJECT-TYPE
        SYNTAX  InetAddress (SIZE(4|16))
        MAX-ACCESS  read-only
        STATUS  current
        DESCRIPTION
                      	""
        ::= { mgmdVlanStatusEntry 5 }

-- mgmdCounterPortTable

        mgmdCounterPortTable OBJECT-TYPE
        SYNTAX	SEQUENCE OF MGMDCounterPortEntry
        MAX-ACCESS  not-accessible
        STATUS  current
        DESCRIPTION
                 	""
        ::= { multicastStatus 11 }

	mgmdCounterPortEntry OBJECT-TYPE
        SYNTAX	MGMDCounterPortEntry
        MAX-ACCESS	not-accessible
        STATUS	current
        DESCRIPTION    	"An entry in mgmdCounterPortTable."
        INDEX          	{ dot1dBasePort }
        ::= { mgmdCounterPortTable 1 }

        MGMDCounterPortEntry ::=
           SEQUENCE {
        	mgmdCounterPortV1ReportIn				Counter32,
        	mgmdCounterPortV2ReportIn				Counter32,
        	mgmdCounterPortV3ReportIn				Counter32,
        	mgmdCounterPortLeaveIn		    		Counter32,
        	mgmdCounterPortTotalReportIn			Counter32, 
        	mgmdCounterPortV1ReportOut				Counter32,
        	mgmdCounterPortV2ReportOut				Counter32,
        	mgmdCounterPortV3ReportOut				Counter32,
        	mgmdCounterPortLeaveOut		    		Counter32,
        	mgmdCounterPortTotalReportOut			Counter32,
        	mgmdCounterPortV1QueryIn				Counter32,
        	mgmdCounterPortV2QueryIn				Counter32,
        	mgmdCounterPortV3QueryIn				Counter32,
        	mgmdCounterPortTotalQueryIn				Counter32, 
        	mgmdCounterPortV1QueryOut				Counter32,
        	mgmdCounterPortV2QueryOut				Counter32,
        	mgmdCounterPortV3QueryOut				Counter32,
        	mgmdCounterPortTotalQueryOut			Counter32,
		    mgmdCounterPortRecordDropMaxGrpLimit	Counter32,
		    mgmdCounterPortRecordDropGrpFilter		Counter32,
		    mgmdCounterPortRecordDropMVR	   		Counter32,
		    mgmdCounterPortRecordDropOther	   		Counter32,	
			    mgmdCounterPortDropRateLimit		Counter32,
		    mgmdCounterPortReportDropOther	   		Counter32,
		    mgmdCounterPortQueryDropOther    		Counter32
           }

        mgmdCounterPortV1ReportIn OBJECT-TYPE
        SYNTAX  Counter32
        MAX-ACCESS  read-only
        STATUS  current
        DESCRIPTION
                      	"Received V1 Report counter for indicated port."
        ::= { mgmdCounterPortEntry 1 }

        mgmdCounterPortV2ReportIn OBJECT-TYPE
        SYNTAX  Counter32
        MAX-ACCESS  read-only
        STATUS  current
        DESCRIPTION
                      	"Received V2 Report counter for indicated port."
        ::= { mgmdCounterPortEntry 2 }

        mgmdCounterPortV3ReportIn OBJECT-TYPE
        SYNTAX  Counter32
        MAX-ACCESS  read-only
        STATUS  current
        DESCRIPTION
                      	"Received V3 Report counter for indicated port."
        ::= { mgmdCounterPortEntry 3 }
 
        mgmdCounterPortLeaveIn OBJECT-TYPE
        SYNTAX  Counter32
        MAX-ACCESS  read-only
        STATUS  current
        DESCRIPTION
                      	"Received Leave counter for indicated port."
        ::= { mgmdCounterPortEntry 4 } 

        mgmdCounterPortTotalReportIn OBJECT-TYPE
        SYNTAX  Counter32
        MAX-ACCESS  read-only
        STATUS  current
        DESCRIPTION
                      	"Received total Report counter for indicated port."
        ::= { mgmdCounterPortEntry 5 } 
        
        mgmdCounterPortV1ReportOut OBJECT-TYPE
        SYNTAX  Counter32
        MAX-ACCESS  read-only
        STATUS  current
        DESCRIPTION
                      	"Transmitted V1 Report counter for indicated port."
        ::= { mgmdCounterPortEntry 6 }
        
        mgmdCounterPortV2ReportOut OBJECT-TYPE
        SYNTAX  Counter32
        MAX-ACCESS  read-only
        STATUS  current
        DESCRIPTION
                      	"Transmitted V2 Report counter for indicated port."
        ::= { mgmdCounterPortEntry 7 }
        
        mgmdCounterPortV3ReportOut OBJECT-TYPE
        SYNTAX  Counter32
        MAX-ACCESS  read-only
        STATUS  current
        DESCRIPTION
                      	"Transmitted V3 Report counter for indicated port."
        ::= { mgmdCounterPortEntry 8 }
                
        mgmdCounterPortLeaveOut OBJECT-TYPE
        SYNTAX  Counter32
        MAX-ACCESS  read-only
        STATUS  current
        DESCRIPTION
                      	"Transmitted Leave counter for indicated port."
        ::= { mgmdCounterPortEntry 9 }
			          
        mgmdCounterPortTotalReportOut OBJECT-TYPE
        SYNTAX  Counter32
        MAX-ACCESS  read-only
        STATUS  current
        DESCRIPTION
                      	"Transmitted total Report counter for indicated port."
        ::= { mgmdCounterPortEntry 10 }    
        
        mgmdCounterPortV1QueryIn OBJECT-TYPE
        SYNTAX  Counter32
        MAX-ACCESS  read-only
        STATUS  current
        DESCRIPTION
                      	"Received V1 Query counter for indicated port."
        ::= { mgmdCounterPortEntry 11 }
        
        mgmdCounterPortV2QueryIn OBJECT-TYPE
        SYNTAX  Counter32
        MAX-ACCESS  read-only
        STATUS  current
        DESCRIPTION
                      	"Received V2 Query counter for indicated port."
        ::= { mgmdCounterPortEntry 12 }
        
        mgmdCounterPortV3QueryIn OBJECT-TYPE
        SYNTAX  Counter32
        MAX-ACCESS  read-only
        STATUS  current
        DESCRIPTION
                      	"Received V3 Query counter for indicated port."
        ::= { mgmdCounterPortEntry 13 }
        
        mgmdCounterPortTotalQueryIn OBJECT-TYPE
        SYNTAX  Counter32
        MAX-ACCESS  read-only
        STATUS  current
        DESCRIPTION
                      	"Received total Query counter for indicated port."
        ::= { mgmdCounterPortEntry 14 }  
        
        mgmdCounterPortV1QueryOut OBJECT-TYPE
        SYNTAX  Counter32
        MAX-ACCESS  read-only
        STATUS  current
        DESCRIPTION
                      	"Transmitted V1 Query counter for indicated port."
        ::= { mgmdCounterPortEntry 15 }
        
        mgmdCounterPortV2QueryOut OBJECT-TYPE
        SYNTAX  Counter32
        MAX-ACCESS  read-only
        STATUS  current
        DESCRIPTION
                      	"Transmitted V2 Query counter for indicated port."
        ::= { mgmdCounterPortEntry 16 }
        
        mgmdCounterPortV3QueryOut OBJECT-TYPE
        SYNTAX  Counter32
        MAX-ACCESS  read-only
        STATUS  current
        DESCRIPTION
                      	"Transmitted V3 Query counter for indicated port."
        ::= { mgmdCounterPortEntry 17 }
                
        mgmdCounterPortTotalQueryOut OBJECT-TYPE
        SYNTAX  Counter32
        MAX-ACCESS  read-only
        STATUS  current
        DESCRIPTION
                      	"Transmitted total Query counter for indicated port."
        ::= { mgmdCounterPortEntry 18 }        
             
        mgmdCounterPortRecordDropMaxGrpLimit OBJECT-TYPE
        SYNTAX  Counter32
        MAX-ACCESS  read-only
        STATUS  current
        DESCRIPTION
                      	"Record drop by max group limit counter for indicated port."
        ::= { mgmdCounterPortEntry 19 }      
        
        mgmdCounterPortRecordDropGrpFilter OBJECT-TYPE
        SYNTAX  Counter32
        MAX-ACCESS  read-only
        STATUS  current
        DESCRIPTION
                      	"Record drop by group filter counter for indicated port."
        ::= { mgmdCounterPortEntry 20 }
        
        mgmdCounterPortRecordDropMVR OBJECT-TYPE
        SYNTAX  Counter32
        MAX-ACCESS  read-only
        STATUS  current
        DESCRIPTION
                      	"Record drop by MVR counter for indicated port."
        ::= { mgmdCounterPortEntry 21 }
        
        mgmdCounterPortRecordDropOther OBJECT-TYPE
        SYNTAX  Counter32
        MAX-ACCESS  read-only
        STATUS  current
        DESCRIPTION
                      	"Record drop by other counter for indicated port."
        ::= { mgmdCounterPortEntry 22 }
             
        mgmdCounterPortDropRateLimit OBJECT-TYPE
        SYNTAX  Counter32
        MAX-ACCESS  read-only
        STATUS  current
        DESCRIPTION
                      	"Packet drop by rate limit counter for indicated port."
        ::= { mgmdCounterPortEntry 23 }   
        
        mgmdCounterPortReportDropOther OBJECT-TYPE
        SYNTAX  Counter32
        MAX-ACCESS  read-only
        STATUS  current
        DESCRIPTION
                      	"Report drop by other counter for indicated port."
        ::= { mgmdCounterPortEntry 24 }
        
        
        mgmdCounterPortQueryDropOther OBJECT-TYPE
        SYNTAX  Counter32
        MAX-ACCESS  read-only
        STATUS  current
        DESCRIPTION
                      	"Query drop by other counter for indicated port."
        ::= { mgmdCounterPortEntry 25 }  
        
------------------------------------------
--  mgmd counters for specific vid
-- mgmdCounterVlanTable

        mgmdCounterVlanTable OBJECT-TYPE
        SYNTAX	SEQUENCE OF MGMDCounterVlanEntry
        MAX-ACCESS  not-accessible
        STATUS  current
        DESCRIPTION
                 	""
        ::= { multicastStatus 12 }

	mgmdCounterVlanEntry OBJECT-TYPE
        SYNTAX	MGMDCounterVlanEntry
        MAX-ACCESS	not-accessible
        STATUS	current
        DESCRIPTION    	"An entry in mgmdCounterVlanTable."
        INDEX          	{ dot1qVlanIndex  }
        ::= { mgmdCounterVlanTable 1 }

        MGMDCounterVlanEntry ::=
           SEQUENCE {
        	mgmdCounterVlanV1ReportIn				Counter32,
        	mgmdCounterVlanV2ReportIn				Counter32,
        	mgmdCounterVlanV3ReportIn				Counter32,
        	mgmdCounterVlanLeaveIn		    		Counter32,
        	mgmdCounterVlanTotalReportIn			Counter32, 
        	mgmdCounterVlanV1ReportOut				Counter32,
        	mgmdCounterVlanV2ReportOut				Counter32,
        	mgmdCounterVlanV3ReportOut				Counter32,
        	mgmdCounterVlanLeaveOut				Counter32,
        	mgmdCounterVlanTotalReportOut			Counter32,
        	mgmdCounterVlanV1QueryIn				Counter32,
        	mgmdCounterVlanV2QueryIn				Counter32,
        	mgmdCounterVlanV3QueryIn				Counter32,
        	mgmdCounterVlanTotalQueryIn				Counter32, 
        	mgmdCounterVlanV1QueryOut				Counter32,
        	mgmdCounterVlanV2QueryOut				Counter32,
        	mgmdCounterVlanV3QueryOut				Counter32,
        	mgmdCounterVlanTotalQueryOut			Counter32,
		    mgmdCounterVlanRecordDropMaxGrpLimit	Counter32,
		    mgmdCounterVlanRecordDropGrpFilter		Counter32,
		    mgmdCounterVlanRecordDropMVR	   		Counter32,
		    mgmdCounterVlanRecordDropOther	   		Counter32,	
		    mgmdCounterVlanDropRateLimit		Counter32,
		    mgmdCounterVlanReportDropOther	   		Counter32,	
		    mgmdCounterVlanQueryDropOther    		Counter32
           }

        mgmdCounterVlanV1ReportIn OBJECT-TYPE
        SYNTAX  Counter32
        MAX-ACCESS  read-only
        STATUS  current
        DESCRIPTION
                      	"Received V1 Report counter for indicated Vlan."
        ::= { mgmdCounterVlanEntry 1 }

        mgmdCounterVlanV2ReportIn OBJECT-TYPE
        SYNTAX  Counter32
        MAX-ACCESS  read-only
        STATUS  current
        DESCRIPTION
                      	"Received V2 Report counter for indicated Vlan."
        ::= { mgmdCounterVlanEntry 2 }

        mgmdCounterVlanV3ReportIn OBJECT-TYPE
        SYNTAX  Counter32
        MAX-ACCESS  read-only
        STATUS  current
        DESCRIPTION
                      	"Received V3 Report counter for indicated Vlan."
        ::= { mgmdCounterVlanEntry 3 }
 
        mgmdCounterVlanLeaveIn OBJECT-TYPE
        SYNTAX  Counter32
        MAX-ACCESS  read-only
        STATUS  current
        DESCRIPTION
                      	"Received Leave counter for indicated Vlan."
        ::= { mgmdCounterVlanEntry 4 }
 
        mgmdCounterVlanTotalReportIn OBJECT-TYPE
        SYNTAX  Counter32
        MAX-ACCESS  read-only
        STATUS  current
        DESCRIPTION
                      	"Received total Report counter for indicated Vlan."
        ::= { mgmdCounterVlanEntry 5 }
 
        mgmdCounterVlanV1ReportOut OBJECT-TYPE
        SYNTAX  Counter32
        MAX-ACCESS  read-only        
        STATUS  current
        DESCRIPTION
                      	"Transmitted V1 Report counter for indicated Vlan."
        ::= { mgmdCounterVlanEntry 6 }
        
        mgmdCounterVlanV2ReportOut OBJECT-TYPE
        SYNTAX  Counter32
        MAX-ACCESS  read-only
        STATUS  current
        DESCRIPTION
                      	"Transmitted V2 Report counter for indicated Vlan."
        ::= { mgmdCounterVlanEntry 7 }
        
        mgmdCounterVlanV3ReportOut OBJECT-TYPE
        SYNTAX  Counter32
        MAX-ACCESS  read-only
        STATUS  current
        DESCRIPTION
                      	"Transmitted V3 Report counter for indicated Vlan."
        ::= { mgmdCounterVlanEntry 8 }
                
        mgmdCounterVlanLeaveOut OBJECT-TYPE
        SYNTAX  Counter32
        MAX-ACCESS  read-only
        STATUS  current
        DESCRIPTION
                      	"Transmitted Leave counter for indicated Vlan."
        ::= { mgmdCounterVlanEntry 9 }
		
		            
        mgmdCounterVlanTotalReportOut OBJECT-TYPE
        SYNTAX  Counter32
        MAX-ACCESS  read-only
        STATUS  current
        DESCRIPTION
                      	"Transmitted total Report counter for indicated Vlan."
        ::= { mgmdCounterVlanEntry 10 }    
        
        mgmdCounterVlanV1QueryIn OBJECT-TYPE
        SYNTAX  Counter32
        MAX-ACCESS  read-only
        STATUS  current
        DESCRIPTION
                      	"Received V1 Query counter for indicated Vlan."
        ::= { mgmdCounterVlanEntry 11 }
        
        mgmdCounterVlanV2QueryIn OBJECT-TYPE
        SYNTAX  Counter32
        MAX-ACCESS  read-only
        STATUS  current
        DESCRIPTION
                      	"Received V2 Query counter for indicated Vlan."
        ::= { mgmdCounterVlanEntry 12 }
        
        mgmdCounterVlanV3QueryIn OBJECT-TYPE
        SYNTAX  Counter32
        MAX-ACCESS  read-only
        STATUS  current
        DESCRIPTION
                      	"Received V3 Query counter for indicated Vlan."
        ::= { mgmdCounterVlanEntry 13 }
        
        mgmdCounterVlanTotalQueryIn OBJECT-TYPE
        SYNTAX  Counter32
        MAX-ACCESS  read-only
        STATUS  current
        DESCRIPTION
                      	"Received total Query counter for indicated Vlan."
        ::= { mgmdCounterVlanEntry 14 }  
        
        mgmdCounterVlanV1QueryOut OBJECT-TYPE
        SYNTAX  Counter32
        MAX-ACCESS  read-only
        STATUS  current
        DESCRIPTION
                      	"Transmitted V1 Query counter for indicated Vlan."
        ::= { mgmdCounterVlanEntry 15 }
        
        mgmdCounterVlanV2QueryOut OBJECT-TYPE
        SYNTAX  Counter32
        MAX-ACCESS  read-only
        STATUS  current
        DESCRIPTION
                      	"Transmitted V2 Query counter for indicated Vlan."
        ::= { mgmdCounterVlanEntry 16 }
        
        mgmdCounterVlanV3QueryOut OBJECT-TYPE
        SYNTAX  Counter32
        MAX-ACCESS  read-only
        STATUS  current
        DESCRIPTION
                      	"Transmitted V3 Query counter for indicated Vlan."
        ::= { mgmdCounterVlanEntry 17 }
                
        mgmdCounterVlanTotalQueryOut OBJECT-TYPE
        SYNTAX  Counter32
        MAX-ACCESS  read-only
        STATUS  current
        DESCRIPTION
                      	"Transmitted total Query counter for indicated Vlan."
        ::= { mgmdCounterVlanEntry 18 }        
             
        mgmdCounterVlanRecordDropMaxGrpLimit OBJECT-TYPE
        SYNTAX  Counter32
        MAX-ACCESS  read-only
        STATUS  current
        DESCRIPTION
                      	"Record drop by max group limit counter for indicated Vlan."
        ::= { mgmdCounterVlanEntry 19 }      
        
        mgmdCounterVlanRecordDropGrpFilter OBJECT-TYPE
        SYNTAX  Counter32
        MAX-ACCESS  read-only
        STATUS  current
        DESCRIPTION
                      	"Record drop by group filter counter for indicated Vlan."
        ::= { mgmdCounterVlanEntry 20 }
        
        mgmdCounterVlanRecordDropMVR OBJECT-TYPE
        SYNTAX  Counter32
        MAX-ACCESS  read-only
        STATUS  current
        DESCRIPTION
                      	"Record drop by MVR counter for indicated Vlan."
        ::= { mgmdCounterVlanEntry 21 }
        
        mgmdCounterVlanRecordDropOther OBJECT-TYPE
        SYNTAX  Counter32
        MAX-ACCESS  read-only
        STATUS  current
        DESCRIPTION
                      	"Record drop by other counter for indicated Vlan."
        ::= { mgmdCounterVlanEntry 22 }
             
        mgmdCounterVlanDropRateLimit OBJECT-TYPE
        SYNTAX  Counter32
        MAX-ACCESS  read-only
        STATUS  current
        DESCRIPTION
                      	"Report drop by rate limit counter for indicated Vlan."
        ::= { mgmdCounterVlanEntry 23 }   
        
        mgmdCounterVlanReportDropOther OBJECT-TYPE
        SYNTAX  Counter32
        MAX-ACCESS  read-only
        STATUS  current
        DESCRIPTION
                      	"Report drop by other counter for indicated Vlan."
        ::= { mgmdCounterVlanEntry 24 }
        
        
        mgmdCounterVlanQueryDropOther OBJECT-TYPE
        SYNTAX  Counter32
        MAX-ACCESS  read-only
        STATUS  current
        DESCRIPTION
                      	"Query drop by other counter for indicated Vlan."
        ::= { mgmdCounterVlanEntry 25 }

 -- mgmdCurrentGroupStatusTable

        mgmdCurrentGroupStatusTable	OBJECT-TYPE
        SYNTAX	SEQUENCE OF MGMDCurrentGroupStatusEntry
        MAX-ACCESS  not-accessible
        STATUS  current
        DESCRIPTION
                 	""
        ::= { multicastStatus 13 }
             
	mgmdCurrentGroupStatusEntry OBJECT-TYPE
        SYNTAX	MGMDCurrentGroupStatusEntry
        MAX-ACCESS	not-accessible
        STATUS	current
        DESCRIPTION    	"An entry in mgmdCurrentGroupStatusTable."
        INDEX          	{ mgmdStatusVlanID, mgmdStatusGroupAddressType, mgmdStatusGroupAddress }
        ::= { mgmdCurrentGroupStatusTable 1 }

        MGMDCurrentGroupStatusEntry ::=
	SEQUENCE {
        	mgmdCurrentNumberOfActivePort    INTEGER
         }

        mgmdCurrentNumberOfActivePort OBJECT-TYPE
        SYNTAX  INTEGER
        MAX-ACCESS  read-only
        STATUS  current
        DESCRIPTION
                      	"Current number Of active port."
        ::= { mgmdCurrentGroupStatusEntry 1 }

-- mgmdClientSrcIp

        mgmdClientSrcIpTable	OBJECT-TYPE
        SYNTAX	SEQUENCE OF MGMDClientSrcIpEntry
        MAX-ACCESS  not-accessible
        STATUS  current
        DESCRIPTION
                 	""
        ::= { multicastStatus 14 }
               
	mgmdClientSrcIpEntry OBJECT-TYPE
        SYNTAX	MGMDClientSrcIpEntry
        MAX-ACCESS	not-accessible
        STATUS	current
        DESCRIPTION    	"An entry in mgmdClientSrcIpTable."
        INDEX          	{mgmdClientSrcIpAddressType,mgmdClientSrcIpIndex, mgmdStatusVlanID, mgmdStatusPort,  mgmdStatusGroupAddress}
        ::= { mgmdClientSrcIpTable 1 }

        MGMDClientSrcIpEntry ::=
	SEQUENCE {
        	mgmdClientSrcIpIndex    	INTEGER,
        	mgmdClientSrcIpAddressType	InetAddressType,  	
        	mgmdClientSrcIpAddress		InetAddress
         }

        mgmdClientSrcIpIndex OBJECT-TYPE
        SYNTAX  INTEGER
        MAX-ACCESS  read-only
        STATUS  current
        DESCRIPTION
                      	""
        ::= { mgmdClientSrcIpEntry 1 }

        mgmdClientSrcIpAddressType OBJECT-TYPE
        SYNTAX  InetAddressType { ipv4(1), ipv6(2) }
        MAX-ACCESS  read-only
        STATUS  current
        DESCRIPTION
                      	""
        ::= { mgmdClientSrcIpEntry 2 }       
        
        mgmdClientSrcIpAddress OBJECT-TYPE
        SYNTAX  InetAddress (SIZE(4|16))
        MAX-ACCESS  read-only
        STATUS  current
        DESCRIPTION
                      	""
        ::= { mgmdClientSrcIpEntry 3 }       
        
 -- mgmdSrcListTable
 
	mgmdSrcListTable OBJECT-TYPE
	SYNTAX     SEQUENCE OF MGMDSrcListEntry
	MAX-ACCESS not-accessible
	STATUS     current
   	DESCRIPTION
            "The (conceptual) table listing the Source List entries
             corresponding to each interface and multicast group pair
             on a host."

	::= { multicastStatus 15 }

	mgmdSrcListEntry OBJECT-TYPE
    	SYNTAX     MGMDSrcListEntry
    	MAX-ACCESS not-accessible
    	STATUS     current
    	DESCRIPTION
            "An entry (conceptual row) in the mgmdSrcListTable."
	INDEX      { mgmdSrcListAddressType, mgmdStatusVlanID, mgmdStatusPort, mgmdStatusGroupAddress, mgmdSrcListAddress }

	::= { mgmdSrcListTable 1 }

	MGMDSrcListEntry ::= SEQUENCE {
    		mgmdSrcListAddressType      InetAddressType,
    		mgmdSrcListAddress          InetAddress
--		mgmdSrcListExpire           TimeTicks
	}

	mgmdSrcListAddressType OBJECT-TYPE
    	SYNTAX     InetAddressType { ipv4(1), ipv6(2) }
    	MAX-ACCESS not-accessible
    	STATUS     current
	DESCRIPTION
            "The address type of the InetAddress variables in this
            table.  This value applies to the mgmdStatusGroupAddress
            and mgmdSrcListAddress entries."

	::= { mgmdSrcListEntry 1 }

	mgmdSrcListAddress OBJECT-TYPE
    	SYNTAX      InetAddress (SIZE(4|16))
    	MAX-ACCESS not-accessible
    	STATUS     current
   	DESCRIPTION
            "The IP multicast group address for which this entry
            contains information."

	::= { mgmdSrcListEntry 2 }

 -- mgmdPortCounterResetTable
 
	mgmdPortCounterResetTable OBJECT-TYPE
	SYNTAX     SEQUENCE OF MGMDPortCounterResetEntry
	MAX-ACCESS not-accessible
	STATUS     current
   	DESCRIPTION
            "The (conceptual) table listing all interface entries."

	::= { multicastStatus 16 }

	mgmdPortCounterResetEntry OBJECT-TYPE
    	SYNTAX     MGMDPortCounterResetEntry
    	MAX-ACCESS not-accessible
    	STATUS     current
    	DESCRIPTION
            "An entry (conceptual row) in the mgmdPortCounterResetTable."
	INDEX      { dot1dBasePort }

	::= { mgmdPortCounterResetTable 1 }

	MGMDPortCounterResetEntry ::= SEQUENCE {
    		mgmdPortCounterReset      INTEGER
	}

	mgmdPortCounterReset OBJECT-TYPE
    	SYNTAX     INTEGER { enable(1), disable(2) }
    	MAX-ACCESS read-write
    	STATUS     current
	DESCRIPTION
            "Clear per port mgmd counter, always return disable."

	::= { mgmdPortCounterResetEntry 1 }

	mgmdAnyPortCounterReset OBJECT-TYPE
    	SYNTAX     INTEGER { enable(1), disable(2) }
    	MAX-ACCESS read-write
    	STATUS     current
	DESCRIPTION
            "Clear all mgmd port counter, always return disable"

	::= { multicastStatus 17 }

	mgmdAnyVlanCounterReset OBJECT-TYPE
    	SYNTAX     INTEGER { enable(1), disable(2) }
    	MAX-ACCESS read-write
    	STATUS     current
	DESCRIPTION
            "Clear all mgmd vlan counter, always return disable"

	::= { multicastStatus 18 }
	
	
--	mgmdSrcListExpire OBJECT-TYPE
--    	SYNTAX     TimeTicks
--    	MAX-ACCESS read-only
--    	STATUS     current
--    	DESCRIPTION
--            "This value indicates the relevance of the SrcList entry,
--            whereby a non-zero value indicates this is an INCLUDE state
--            value, and a zero value indicates this to be an EXCLUDE
--            state value."

--	::= { mgmdHostSrcListEntry 3 }
	
------------------------------------------
--  igmpFilteringProfileSetup
	igmpFilteringProfileSetup     	OBJECT IDENTIFIER ::= { ves1724-56fanless 30 }

	igmpFilteringMaxNumberOfProfile OBJECT-TYPE
        SYNTAX  INTEGER
        MAX-ACCESS  read-only
        STATUS  current
        DESCRIPTION
                      	""
        ::= { igmpFilteringProfileSetup 1 }

        igmpFilteringProfileTable	OBJECT-TYPE
        SYNTAX	SEQUENCE OF IgmpFilteringProfileEntry
        MAX-ACCESS  not-accessible
        STATUS  current
        DESCRIPTION
                 	""
        ::= { igmpFilteringProfileSetup 2 }

	igmpFilteringProfileEntry OBJECT-TYPE
        SYNTAX	IgmpFilteringProfileEntry
        MAX-ACCESS	not-accessible
        STATUS	current
        DESCRIPTION    	"An entry in igmpFilteringProfileTable."
        INDEX          	{ igmpFilteringProfileName, igmpFilteringProfileStartAddress, igmpFilteringProfileEndAddress }
        ::= { igmpFilteringProfileTable 1 }

        IgmpFilteringProfileEntry ::=
	SEQUENCE {
        	igmpFilteringProfileName		DisplayString,
        	igmpFilteringProfileStartAddress	IpAddress,
        	igmpFilteringProfileEndAddress		IpAddress,
        	igmpFilteringProfileRowStatus		RowStatus
        }

        igmpFilteringProfileName OBJECT-TYPE
        SYNTAX  DisplayString
        MAX-ACCESS  read-only
        STATUS  current
        DESCRIPTION
                      	""
        ::= { igmpFilteringProfileEntry 1 }

        igmpFilteringProfileStartAddress OBJECT-TYPE
        SYNTAX  IpAddress
        MAX-ACCESS  read-only
        STATUS  current
        DESCRIPTION
                      	""
        ::= { igmpFilteringProfileEntry 2 }

        igmpFilteringProfileEndAddress OBJECT-TYPE
        SYNTAX  IpAddress
        MAX-ACCESS  read-only
        STATUS  current
        DESCRIPTION
                      	""
        ::= { igmpFilteringProfileEntry 3 }

        igmpFilteringProfileRowStatus OBJECT-TYPE
        SYNTAX  RowStatus
        MAX-ACCESS  read-create
        STATUS  current
        DESCRIPTION
                      	""
        ::= { igmpFilteringProfileEntry 4 }

        mgmdFilterProfileTable	OBJECT-TYPE
        SYNTAX	SEQUENCE OF MgmdFilterProfileEntry
        MAX-ACCESS  not-accessible
        STATUS  current
        DESCRIPTION
                 	""
        ::= { igmpFilteringProfileSetup 3 }
        
	mgmdFilterProfileEntry OBJECT-TYPE
        SYNTAX	MgmdFilterProfileEntry
        MAX-ACCESS	not-accessible
        STATUS	current
        DESCRIPTION    	"An entry in mgmdFilterProfileTable.For v4 and v6 address"
        INDEX          	{ 
        		mgmdFilterProfileName, 
        		mgmdFilterProfileAddressType, 
        		mgmdFilterProfileStartAddress,
        		mgmdFilterProfileEndAddress }        		
        ::= { mgmdFilterProfileTable 1 }

        MgmdFilterProfileEntry ::=
	SEQUENCE {
        	mgmdFilterProfileName			DisplayString,
        	mgmdFilterProfileAddressType		InetAddressType,
        	mgmdFilterProfileStartAddress		InetAddress,
        	mgmdFilterProfileEndAddress		InetAddress,
        	mgmdFilterProfileRowStatus		RowStatus
        }

        mgmdFilterProfileName OBJECT-TYPE
        SYNTAX  DisplayString
        MAX-ACCESS  read-only
        STATUS  current
        DESCRIPTION
                      	""
        ::= { mgmdFilterProfileEntry 1 }
        
        mgmdFilterProfileAddressType OBJECT-TYPE
        SYNTAX  InetAddressType
        MAX-ACCESS  read-only
        STATUS  current
        DESCRIPTION
		"The type of the mgmdFilterProfileStartAddress and mgmdFilterProfileEndAddress address, as defined
            in the InetAddress MIB."
            
        ::= { mgmdFilterProfileEntry 2 }
        
        mgmdFilterProfileStartAddress OBJECT-TYPE
        SYNTAX  InetAddress
        MAX-ACCESS  read-only
        STATUS  current
        DESCRIPTION
		"The Start IP address of this profile."
        ::= { mgmdFilterProfileEntry 3 }

        
        mgmdFilterProfileEndAddress OBJECT-TYPE
        SYNTAX  InetAddress
        MAX-ACCESS  read-only
        STATUS  current
        DESCRIPTION
		"The End IP address of this profile."
        ::= { mgmdFilterProfileEntry 4 }

        mgmdFilterProfileRowStatus OBJECT-TYPE
        SYNTAX  RowStatus
        MAX-ACCESS  read-create
        STATUS  current
        DESCRIPTION
                      	""
        ::= { mgmdFilterProfileEntry 5 }



--  MVRSetup
	mvrSetup     	OBJECT IDENTIFIER ::= { ves1724-56fanless 31 }

	maxNumberOfMVR OBJECT-TYPE
        SYNTAX  INTEGER
        MAX-ACCESS  read-only
        STATUS  current
        DESCRIPTION
                      	""
        ::= { mvrSetup 1 }

        mvrTable	OBJECT-TYPE
        SYNTAX	SEQUENCE OF MvrEntry
        MAX-ACCESS  not-accessible
        STATUS  current
        DESCRIPTION
                 	""
        ::= { mvrSetup 2 }

	mvrEntry OBJECT-TYPE
        SYNTAX	MvrEntry
        MAX-ACCESS	not-accessible
        STATUS	current
        DESCRIPTION    	"An entry in mvrTable."
        INDEX          	{ mvrVlanID }
        ::= { mvrTable 1 }

        MvrEntry ::=
	SEQUENCE {
        	mvrVlanID	INTEGER,
        	mvrName		DisplayString,
        	mvrMode		INTEGER,
        	mvrRowStatus	RowStatus,
        	mvr8021pPriority	INTEGER
        	
        }

        mvrVlanID OBJECT-TYPE
        SYNTAX  INTEGER
        MAX-ACCESS  read-only
        STATUS  current
        DESCRIPTION
                      	"1..4094"
        ::= { mvrEntry 1 }

        mvrName OBJECT-TYPE
        SYNTAX  DisplayString
        MAX-ACCESS  read-write
        STATUS  current
        DESCRIPTION
                      	""
        ::= { mvrEntry 2 }

        mvrMode OBJECT-TYPE
        SYNTAX  INTEGER {
        	dynamic(0),
        	compatible(1)
        	}
        MAX-ACCESS  read-write
        STATUS  current
        DESCRIPTION
                      	""
        ::= { mvrEntry 3 }

        mvrRowStatus OBJECT-TYPE
        SYNTAX  RowStatus
        MAX-ACCESS  read-create
        STATUS  current
        DESCRIPTION
                      	""
        ::= { mvrEntry 4 }

        mvr8021pPriority OBJECT-TYPE
        SYNTAX  INTEGER
        MAX-ACCESS  read-write
        STATUS  current
        DESCRIPTION
                      	"Set the 802.1p priority of control messages within MVR (0~7)"
        ::= { mvrEntry 5 }
        

        mvrPortTable	OBJECT-TYPE
        SYNTAX	SEQUENCE OF MvrPortEntry
        MAX-ACCESS  not-accessible
        STATUS  current
        DESCRIPTION
                 	""
        ::= { mvrSetup 3 }

	mvrPortEntry OBJECT-TYPE
        SYNTAX	MvrPortEntry
        MAX-ACCESS	not-accessible
        STATUS	current
        DESCRIPTION    	"An entry in mvrPortTable."
        INDEX          	{ mvrVlanID, dot1dBasePort }
        ::= { mvrPortTable 1 }

        MvrPortEntry ::=
	SEQUENCE {
        	mvrPortRole	INTEGER,
        	mvrPortTagging	EnabledStatus
        }

        mvrPortRole OBJECT-TYPE
        SYNTAX  INTEGER {
        	none(1),
        	source_port(2),
        	receiver_port(3)
        }
        MAX-ACCESS  read-write
        STATUS  current
        DESCRIPTION
                      	""
        ::= { mvrPortEntry 1 }

        mvrPortTagging OBJECT-TYPE
        SYNTAX  EnabledStatus
        MAX-ACCESS  read-write
        STATUS  current
        DESCRIPTION
                      	""
        ::= { mvrPortEntry 2 }

	maxNumberOfMvrGroup OBJECT-TYPE
        SYNTAX  INTEGER
        MAX-ACCESS  read-only
        STATUS  current
        DESCRIPTION
                      	""
        ::= { mvrSetup 4 }

        mvrGroupTable	OBJECT-TYPE
        SYNTAX	SEQUENCE OF MvrGroupEntry
        MAX-ACCESS  not-accessible
        STATUS  current
        DESCRIPTION
                 	""
        ::= { mvrSetup 5 }

	mvrGroupEntry OBJECT-TYPE
        SYNTAX	MvrGroupEntry
        MAX-ACCESS	not-accessible
        STATUS	current
        DESCRIPTION    	"An entry in mvrGroupTable."
        INDEX          	{ mvrVlanID, mvrGroupName }
        ::= { mvrGroupTable 1 }

        MvrGroupEntry ::=
	SEQUENCE {
        	mvrGroupName		DisplayString,
        	mvrGroupStartAddress	IpAddress,
        	mvrGroupEndAddress	IpAddress,
        	mvrGroupRowStatus	RowStatus
        }

        mvrGroupName OBJECT-TYPE
        SYNTAX  DisplayString
        MAX-ACCESS  read-only
        STATUS  current
        DESCRIPTION
                      	""
        ::= { mvrGroupEntry 1 }

        mvrGroupStartAddress OBJECT-TYPE
        SYNTAX  IpAddress
        MAX-ACCESS  read-write
        STATUS  current
        DESCRIPTION
                      	""
        ::= { mvrGroupEntry 2 }

        mvrGroupEndAddress OBJECT-TYPE
        SYNTAX  IpAddress
        MAX-ACCESS  read-write
        STATUS  current
        DESCRIPTION
                      	""
        ::= { mvrGroupEntry 3 }

        mvrGroupRowStatus OBJECT-TYPE
        SYNTAX  RowStatus
        MAX-ACCESS  read-create
        STATUS  current
        DESCRIPTION
                      	""
        ::= { mvrGroupEntry 4 }

    mvrBehavior OBJECT-TYPE
        SYNTAX  INTEGER {
         		igmp_snooping(1),
         		igmp_proxy(2)
        }
        MAX-ACCESS  read-write
        STATUS  current
        DESCRIPTION
                      ""
        ::= { mvrSetup 6 }


        mvrMgmdGroupTable	OBJECT-TYPE
        SYNTAX	SEQUENCE OF MvrMgmdGroupEntry
        MAX-ACCESS  not-accessible
        STATUS  current
        DESCRIPTION
                 	""
        ::= { mvrSetup 7 }

	mvrMgmdGroupEntry OBJECT-TYPE
        SYNTAX	MvrMgmdGroupEntry
        MAX-ACCESS	not-accessible
        STATUS	current
        DESCRIPTION    	"An entry in mvrMgmdGroupTable."
        INDEX          	{ mvrVlanID, mvrMgmdGroupName }
        ::= { mvrMgmdGroupTable 1 }

        MvrMgmdGroupEntry ::=
	SEQUENCE {
        	mvrMgmdGroupName		DisplayString,
        	mvrMgmdGroupAddressType		InetAddressType,
        	mvrMgmdGroupStartAddress	InetAddress,
        	mvrMgmdGroupEndAddress		InetAddress,
        	mvrMgmdGroupRowStatus		RowStatus
        }

        mvrMgmdGroupName OBJECT-TYPE
        SYNTAX  DisplayString
        MAX-ACCESS  read-only
        STATUS  current
        DESCRIPTION
                      	""
        ::= { mvrMgmdGroupEntry 1 }

        mvrMgmdGroupAddressType OBJECT-TYPE
        SYNTAX  InetAddressType
        MAX-ACCESS  read-write
        STATUS  current
        DESCRIPTION
                      	""
        ::= { mvrMgmdGroupEntry 2 }


        mvrMgmdGroupStartAddress OBJECT-TYPE
        SYNTAX  InetAddress
        MAX-ACCESS  read-write
        STATUS  current
        DESCRIPTION
                      	""
        ::= { mvrMgmdGroupEntry 3 }

        mvrMgmdGroupEndAddress OBJECT-TYPE
        SYNTAX  InetAddress
        MAX-ACCESS  read-write
        STATUS  current
        DESCRIPTION
                      	""
        ::= { mvrMgmdGroupEntry 4 }

        mvrMgmdGroupRowStatus OBJECT-TYPE
        SYNTAX  RowStatus
        MAX-ACCESS  read-create
        STATUS  current
        DESCRIPTION
                      	""
        ::= { mvrMgmdGroupEntry 5 }

--  sysLogSetup
	sysLogSetup     	OBJECT IDENTIFIER ::= { ves1724-56fanless 33 }
	
	sysLogState OBJECT-TYPE
        SYNTAX  EnabledStatus
        MAX-ACCESS  read-write
        STATUS  current
        DESCRIPTION
                      	"sysLog enabled/disabled for the switch."
        ::= { sysLogSetup 1 }
            	
--  sysLogTypeTable
       	sysLogTypeTable	OBJECT-TYPE
        SYNTAX	SEQUENCE OF SysLogTypeEntry
        MAX-ACCESS  not-accessible
        STATUS  current
        DESCRIPTION
                 	""
        ::= { sysLogSetup 2 }
        
	sysLogTypeEntry OBJECT-TYPE
        SYNTAX	SysLogTypeEntry
        MAX-ACCESS	not-accessible
        STATUS	current
        DESCRIPTION    	"An entry in sysLogTypeTable."
        INDEX          	{ sysLogTypeIndex }
        ::= { sysLogTypeTable 1 }

        SysLogTypeEntry ::=
           SEQUENCE {
         	sysLogTypeIndex		INTEGER,
        	sysLogTypeName		DisplayString,
        	sysLogTypeState		EnabledStatus,
        	sysLogTypeFacility	INTEGER
           }
       
        sysLogTypeIndex OBJECT-TYPE
        SYNTAX  INTEGER
        MAX-ACCESS  not-accessible
        STATUS  current
        DESCRIPTION
                      	""
        ::= { sysLogTypeEntry 1 }

        sysLogTypeName OBJECT-TYPE
        SYNTAX  DisplayString 
        MAX-ACCESS  read-only
        STATUS  current
        DESCRIPTION
                      	""
        ::= { sysLogTypeEntry 2 }

        sysLogTypeState OBJECT-TYPE
        SYNTAX  EnabledStatus
        MAX-ACCESS  read-write
        STATUS  current
        DESCRIPTION
                      	""
        ::= { sysLogTypeEntry 3 }

   	sysLogTypeFacility OBJECT-TYPE
        SYNTAX  INTEGER {
        	local_user0(0),
        	local_user1(1),
        	local_user2(2),
        	local_user3(3),
        	local_user4(4),
        	local_user5(5),
        	local_user6(6),
        	local_user7(7)
        }
        MAX-ACCESS  read-write
        STATUS  current
        DESCRIPTION
                      	""
        ::= { sysLogTypeEntry 4 }

--  sysLogServerTable
       	sysLogServerTable	OBJECT-TYPE
        SYNTAX	SEQUENCE OF SysLogServerEntry
        MAX-ACCESS  not-accessible
        STATUS  current
        DESCRIPTION
                 	""
        ::= { sysLogSetup 3 }
        
	sysLogServerEntry OBJECT-TYPE
        SYNTAX	SysLogServerEntry
        MAX-ACCESS	not-accessible
        STATUS	current
        DESCRIPTION    	"An entry in sysLogServerTable."
        INDEX          	{ sysLogServerAddress }
        ::= { sysLogServerTable 1 }

        SysLogServerEntry ::=
           SEQUENCE {
         	sysLogServerAddress		IpAddress,
        	sysLogServerLogLevel	INTEGER,
        	sysLogServerRowStatus	RowStatus
           }
       
        sysLogServerAddress OBJECT-TYPE
        SYNTAX  IpAddress
        MAX-ACCESS  not-accessible
        STATUS  current
        DESCRIPTION
                      	""
        ::= { sysLogServerEntry 1 }

        sysLogServerLogLevel OBJECT-TYPE
        SYNTAX  INTEGER {
        	level0(0),
        	level0_1(1),
        	level0_2(2),
        	level0_3(3),
        	level0_4(4),
        	level0_5(5),
        	level0_6(6),
        	level0_7(7)
        }
        MAX-ACCESS  read-write
        STATUS  current
        DESCRIPTION
                      	""
        ::= { sysLogServerEntry 2 }

        sysLogServerRowStatus OBJECT-TYPE
        SYNTAX  RowStatus
        MAX-ACCESS  read-create
        STATUS  current
        DESCRIPTION
                      	""
        ::= { sysLogServerEntry 3 }
                                             
--  sysLogServerInfoTable
   	sysLogServerInfoTable	OBJECT-TYPE
        SYNTAX	SEQUENCE OF SysLogServerInfoEntry
        MAX-ACCESS  not-accessible
        STATUS  current
        DESCRIPTION
                 	""
        ::= { sysLogSetup 4 }
        
	sysLogServerInfoEntry OBJECT-TYPE
        SYNTAX	SysLogServerInfoEntry
        MAX-ACCESS	not-accessible
        STATUS	current
        DESCRIPTION    	"An entry in sysLogServerInfoTable."
        INDEX          	{ sysLogServerInfoIpAddrType, sysLogServerInfoIpAddr }
        ::= { sysLogServerInfoTable 1 }

        SysLogServerInfoEntry ::=
			SEQUENCE {
				sysLogServerInfoIpAddrType	InetAddressType,
				sysLogServerInfoIpAddr		InetAddress,
				sysLogServerInfoLogLevel	INTEGER,
				sysLogServerInfoRowStatus	RowStatus
			}
       
        sysLogServerInfoIpAddrType OBJECT-TYPE
        SYNTAX  InetAddressType { ipv4(1), ipv6(2) }
        MAX-ACCESS  not-accessible
        STATUS  current
        DESCRIPTION
                      	""
        ::= { sysLogServerInfoEntry 1 }
        
        sysLogServerInfoIpAddr OBJECT-TYPE
        SYNTAX  InetAddress
        MAX-ACCESS  not-accessible
        STATUS  current
        DESCRIPTION
                      	""
        ::= { sysLogServerInfoEntry 2 }

        sysLogServerInfoLogLevel OBJECT-TYPE
        SYNTAX  INTEGER {
        	level0(0),
        	level0_1(1),
        	level0_2(2),
        	level0_3(3),
        	level0_4(4),
        	level0_5(5),
        	level0_6(6),
        	level0_7(7)
        }
        MAX-ACCESS  read-write
        STATUS  current
        DESCRIPTION
                      	""
        ::= { sysLogServerInfoEntry 3 }

        sysLogServerInfoRowStatus OBJECT-TYPE
        SYNTAX  RowStatus
        MAX-ACCESS  read-create
        STATUS  current
        DESCRIPTION
                      	""
        ::= { sysLogServerInfoEntry 4 }
                                             
-- diffservSetup
	diffservSetup     	OBJECT IDENTIFIER ::= { ves1724-56fanless 34 }

        diffservState OBJECT-TYPE
        SYNTAX  EnabledStatus
        MAX-ACCESS  read-write
        STATUS  current
        DESCRIPTION
                      ""
        ::= { diffservSetup 1 }
        
-- diffservMapTable
        diffservMapTable OBJECT-TYPE
        SYNTAX	SEQUENCE OF DiffservMapEntry
        MAX-ACCESS  not-accessible
        STATUS  current
        DESCRIPTION
                 	""
        ::= { diffservSetup 2 }
        
	diffservMapEntry OBJECT-TYPE
        SYNTAX	DiffservMapEntry
        MAX-ACCESS	not-accessible
        STATUS	current
        DESCRIPTION    	"An entry in diffservMapTable."
        INDEX          	{ diffservMapDscp }
        ::= { diffservMapTable 1 }

        DiffservMapEntry ::=
           SEQUENCE {
        	diffservMapDscp		INTEGER,
        	diffservMapPriority	INTEGER
           }

        diffservMapDscp OBJECT-TYPE
        SYNTAX  INTEGER
        MAX-ACCESS  read-only
        STATUS  current
        DESCRIPTION
                      	"0-63"
        ::= { diffservMapEntry 1 }

        diffservMapPriority OBJECT-TYPE
        SYNTAX  INTEGER
        MAX-ACCESS  read-write
        STATUS  current
        DESCRIPTION
                      	"0-7"
        ::= { diffservMapEntry 2 }

-- diffservPortTable
        diffservPortTable OBJECT-TYPE
        SYNTAX	SEQUENCE OF DiffservPortEntry
        MAX-ACCESS  not-accessible
        STATUS  current
        DESCRIPTION
                 	""
        ::= { diffservSetup 3 }
        
	diffservPortEntry OBJECT-TYPE
        SYNTAX	DiffservPortEntry
        MAX-ACCESS	not-accessible
        STATUS	current
        DESCRIPTION    	"An entry in diffservPortTable."
        INDEX          	{ dot1dBasePort }
        ::= { diffservPortTable 1 }

        DiffservPortEntry ::=
           SEQUENCE {
        	diffservPortState	EnabledStatus
           }

        diffservPortState OBJECT-TYPE
        SYNTAX  EnabledStatus
        MAX-ACCESS  read-write
        STATUS  current
        DESCRIPTION
                      	""
        ::= { diffservPortEntry 1 }




-- vturSwitchSetup
	vturSwitchSetup     	OBJECT IDENTIFIER ::= { ves1724-56fanless 35 }

-- vturLayer2Setup
		vturLayer2Setup     	OBJECT IDENTIFIER ::= { vturSwitchSetup 1 }

	layer2Table OBJECT-TYPE
       	SYNTAX	SEQUENCE OF Layer2Entry
       	MAX-ACCESS  not-accessible
       	STATUS  current
       	DESCRIPTION
      	      	""
       	::= { vturLayer2Setup 1 }

	layer2Entry OBJECT-TYPE
       	SYNTAX	Layer2Entry
       	MAX-ACCESS	not-accessible
       	STATUS	current
       	DESCRIPTION    	"An entry in layer2Table."
       	INDEX          	{ dot1dBasePort}
       	::= { layer2Table 1 }

        Layer2Entry ::=
       	SEQUENCE {
       	vturIgmpSnoopingStateSetup	INTEGER
        }

        vturIgmpSnoopingStateSetup OBJECT-TYPE
        SYNTAX  INTEGER {
         		enabled(1),
         		disabled(2)
        }
        MAX-ACCESS  read-write
        STATUS  current
        DESCRIPTION
                      ""
        ::= { layer2Entry 2 }

       
       
-- vturPortSetup
		vturPortSetup     	OBJECT IDENTIFIER ::= { vturSwitchSetup 2 }

-- PortTable
    portTable OBJECT-TYPE
       	SYNTAX	SEQUENCE OF PortEntry
       	MAX-ACCESS  not-accessible
       	STATUS  current
       	DESCRIPTION
      	      	""
       	::= { vturPortSetup 1 }

	portEntry OBJECT-TYPE
       	SYNTAX	PortEntry
       	MAX-ACCESS	not-accessible
       	STATUS	current
       	DESCRIPTION    	"An entry in portTable."
       	INDEX          	{ dot1dBasePort, portNumber }
       	::= { portTable 1 }

    PortEntry ::=
       	SEQUENCE {
       	portNumber	INTEGER,
       	portAdminStatus INTEGER,
        portOperStatus	INTEGER,
        portSpeedDuplex	INTEGER,
        portOperSpeed	INTEGER  
        }

    portNumber OBJECT-TYPE
       	SYNTAX  INTEGER
     	MAX-ACCESS  read-only
       	STATUS  current
       	DESCRIPTION
                    	"Display all ports we got in CPE side"
        ::= { portEntry 1 }

    portAdminStatus OBJECT-TYPE
       	SYNTAX  INTEGER {
       	enable(1),
       	disable(2)
       	}
     	MAX-ACCESS  read-write
       	STATUS  current
       	DESCRIPTION
                    	"Specify CPE port's admin status."
        ::= { portEntry 2 }

    portOperStatus OBJECT-TYPE
       	SYNTAX  INTEGER {
       	enable(1),
       	disable(2)
       	}
     	MAX-ACCESS  read-only
       	STATUS  current
       	DESCRIPTION
                    	"CPE port's current status."
        ::= { portEntry 3 }

    portSpeedDuplex OBJECT-TYPE
       	SYNTAX  INTEGER {
       	autoneg(1),
       	half_10M(2),
       	full_10M(3),
       	half_100M(4),
       	full_100M(5)
       	}
       	MAX-ACCESS  read-write
       	STATUS  current
       	DESCRIPTION
                     	"Specify each port's speed and duplex in CPE side."
        ::= { portEntry 4 }


    portOperSpeed OBJECT-TYPE
       	SYNTAX  INTEGER {
       	linkdown(0),
       	autoneg(1),
       	half_10M(2),
       	full_10M(3),
       	half_100M(4),
       	full_100M(5)
       	}
       	MAX-ACCESS  read-only
       	STATUS  current
       	DESCRIPTION
                     	"CPE port's current speed."
        ::= { portEntry 8 }




-- vturWanSetup
		vturWanSetup     	OBJECT IDENTIFIER ::= { vturSwitchSetup 4 }


-- vturWanTable
vturWan OBJECT IDENTIFIER ::= { vturWanSetup 1 }
   vturWanTable OBJECT-TYPE
       	SYNTAX	SEQUENCE OF VturWanEntry
       	MAX-ACCESS  not-accessible
       	STATUS  current
       	DESCRIPTION
      	      	""
       	::= { vturWan 1 }

     vturWanEntry OBJECT-TYPE
       	SYNTAX	VturWanEntry
       	MAX-ACCESS	not-accessible
       	STATUS	current
       	DESCRIPTION    	"An entry in vturWanTable."
       	INDEX          	{ dot1dBasePort, vturWanIndex }
       	::= { vturWanTable 1 }

     VturWanEntry ::=
       	SEQUENCE {
        vturWanIndex	INTEGER,
	vturVlanTagging	INTEGER,
	vturVlanID	INTEGER,
	vtur8021p	INTEGER,
	vturPPPUsername	OCTET STRING,
	vturPPPPassword	OCTET STRING,
	vturWanProtocol INTEGER,
	vturWanProtocolSetting BITS,
	vturWanIP IpAddress,
	vturWanSubnetMask IpAddress,
	vturWanService	EnabledStatus,
        vturWanRowStatus  RowStatus,
        vturWanDefaultGateway	EnabledStatus,
        vturWanDefaultDNS	EnabledStatus
        }

     vturWanIndex OBJECT-TYPE
       	SYNTAX  INTEGER
       	MAX-ACCESS  read-only
       	STATUS  current
       	DESCRIPTION
                   	"Display the wan index range from 1 to 4 we got in CPE side"
       	::= { vturWanEntry 1 }

     vturVlanTagging OBJECT-TYPE
       	SYNTAX  INTEGER
       	{
       	disable(1),
       	vlan_mux(2),
       	auto_vlan(3)
       	}
       	MAX-ACCESS  read-write
       	STATUS  current
       	DESCRIPTION
                   	"Display the vlan tagging we got in CPE side"
       	::= { vturWanEntry 2 }

     vturVlanID OBJECT-TYPE
       	SYNTAX  INTEGER
       	MAX-ACCESS  read-write
       	STATUS  current
       	DESCRIPTION
                   	"Display the vlan id range from 1 to 4094 we got in CPE side"
       	::= { vturWanEntry 3 }       	

     vtur8021p OBJECT-TYPE
       	SYNTAX  INTEGER
       	MAX-ACCESS  read-write
       	STATUS  current
       	DESCRIPTION
                   	"Display the 802.1p value range from 0 to 7 we got in CPE side"
       	::= { vturWanEntry 4 }

     vturPPPUsername OBJECT-TYPE
       	SYNTAX  OCTET STRING
       	MAX-ACCESS  read-write
       	STATUS  current
       	DESCRIPTION
                   	"Display the PPP username we got in CPE side"
       	::= { vturWanEntry 5 }
       	
     vturPPPPassword OBJECT-TYPE
       	SYNTAX  OCTET STRING
       	MAX-ACCESS  read-write
       	STATUS  current
       	DESCRIPTION
                   	"Display the PPP password we got in CPE side"
       	::= { vturWanEntry 6 }
       	
     vturWanProtocol OBJECT-TYPE
       	SYNTAX  INTEGER
       	{
       	pppoe(1),
       	mer(2),
       	bridge(3)
       	}
       	MAX-ACCESS  read-write
       	STATUS  current
       	DESCRIPTION
                   	"Display the wan protocol info we got in CPE side"
       	::= { vturWanEntry 7 }

     vturWanProtocolSetting OBJECT-TYPE
       	SYNTAX  BITS
       	{
		dhcp_client_(0),
		nat(1),
		firewall(2),
		igmp(3)
	}       	
       	MAX-ACCESS  read-write
       	STATUS  current
       	DESCRIPTION
                   	"Display the wan service enable/disable status we got in CPE side"
       	::= { vturWanEntry 8 }       	       	       	       	      
          
      vturWanIP OBJECT-TYPE
        SYNTAX  IpAddress
        MAX-ACCESS  read-create
        STATUS  current
        DESCRIPTION
                      	"Display the wan IP setting we got in CPE side"
        ::= { vturWanEntry 9 }

      vturWanSubnetMask OBJECT-TYPE
        SYNTAX  IpAddress
        MAX-ACCESS  read-create
        STATUS  current
        DESCRIPTION
                      	"Display the wan subnet mask we got in CPE side"
        ::= { vturWanEntry 10 }

     vturWanService OBJECT-TYPE
       	SYNTAX  EnabledStatus
       	MAX-ACCESS  read-write
       	STATUS  current
       	DESCRIPTION
                   	"Display the wan service enable/disable status we got in CPE side"
       	::= { vturWanEntry 11 }       	       	       	       	      

      vturWanRowStatus OBJECT-TYPE
        SYNTAX  RowStatus
        MAX-ACCESS  read-create
        STATUS  current
        DESCRIPTION
                      	""
        ::= { vturWanEntry 12 }        

      vturWanDefaultGateway OBJECT-TYPE
       	SYNTAX  EnabledStatus
       	MAX-ACCESS  read-write
       	STATUS  current
       	DESCRIPTION
                   	"Display the wan default gateway enable/disable status we got in CPE side"
       	::= { vturWanEntry 13 }        

      vturWanDefaultDNS OBJECT-TYPE
       	SYNTAX  EnabledStatus
       	MAX-ACCESS  read-write
       	STATUS  current
       	DESCRIPTION
                   	"Display the wan default DNS enable/disable status we got in CPE side"
       	::= { vturWanEntry 14 }        

	vturWanCommon OBJECT IDENTIFIER ::= { vturWanSetup 2 }

        vturWanCommonTable  OBJECT-TYPE
        SYNTAX	SEQUENCE OF VturWanCommonEntry
       	MAX-ACCESS  not-accessible
       	STATUS  current
       	DESCRIPTION
      	      	""
        ::= { vturWanCommon 1 }

	vturWanCommonEntry OBJECT-TYPE
       	SYNTAX	VturWanCommonEntry
       	MAX-ACCESS	not-accessible
       	STATUS	current
       	DESCRIPTION    	"An entry in vturWanCommonTable."
       	INDEX          	{ dot1dBasePort}
       	::= { vturWanCommonTable 1 }

        VturWanCommonEntry ::=
       	SEQUENCE {
       	vturWanQoS			EnabledStatus,
       	vturEnableAutoDefaultGateway	EnabledStatus,
        vturDefaultGatewayIP		IpAddress,
        vturVitualPortEnable		EnabledStatus,
        vturAutoDNS		EnabledStatus,
        vturPrimaryDNS						IpAddress,
        vturSecodnaryDNS						IpAddress
        }


        vturWanQoS OBJECT-TYPE
        SYNTAX  EnabledStatus
        MAX-ACCESS  read-write
        STATUS  current
        DESCRIPTION
                      ""
        ::= { vturWanCommonEntry 1 }

        vturEnableAutoDefaultGateway OBJECT-TYPE
        SYNTAX  EnabledStatus 
        MAX-ACCESS  read-write
        STATUS  current
        DESCRIPTION
                      "Display the enable auto default gateay setting we get from CPE side"
        ::= { vturWanCommonEntry 2 }

        vturDefaultGatewayIP OBJECT-TYPE
       	SYNTAX  IpAddress 
     	MAX-ACCESS  read-write
       	STATUS  current
       	DESCRIPTION
       		"Display the default gateway setting we get from CPE side"
        ::= { vturWanCommonEntry 3 }

        vturVitualPortEnable OBJECT-TYPE
        SYNTAX  EnabledStatus
        MAX-ACCESS  read-write
        STATUS  current
        DESCRIPTION
                      "Display Enable/Disable virtual port on eth1 setting we get on CPE side"
        ::= { vturWanCommonEntry 4 }

       vturAutoDNS OBJECT-TYPE
        SYNTAX  EnabledStatus
        MAX-ACCESS  read-write
        STATUS  current
        DESCRIPTION
                      "Display Enable/Disable Auto DNS on eth1 setting we get on CPE side"
        ::= { vturWanCommonEntry 5 }

        vturPrimaryDNS OBJECT-TYPE
       	SYNTAX  IpAddress 
     	MAX-ACCESS  read-write
       	STATUS  current
       	DESCRIPTION
       		"Display the primary DNS address we get from CPE side"
        ::= { vturWanCommonEntry 6 }
        
        vturSecodnaryDNS OBJECT-TYPE
       	SYNTAX  IpAddress 
     	MAX-ACCESS  read-write
       	STATUS  current
       	DESCRIPTION
       		"Display the secondary DNS address we get from CPE side"
        ::= { vturWanCommonEntry 7 }        

-- vturClassificationSetup
		vturClassificationSetup     	OBJECT IDENTIFIER ::= { vturSwitchSetup 5 }


-- vturClassificationTable
    vturClassificationTable OBJECT-TYPE
       	SYNTAX	SEQUENCE OF VturClassificationEntry
       	MAX-ACCESS  not-accessible
       	STATUS  current
       	DESCRIPTION
      	      	""
       	::= { vturClassificationSetup 1 }

     vturClassificationEntry OBJECT-TYPE
       	SYNTAX	VturClassificationEntry
       	MAX-ACCESS	not-accessible
       	STATUS	current
       	DESCRIPTION    	"An entry in vturClassificationTable."
       	INDEX          	{ dot1dBasePort, vturClassificationIndex }
       	::= { vturClassificationTable 1 }

     VturClassificationEntry ::=
       	SEQUENCE {
        vturClassificationIndex	INTEGER,
	vturClassificationRuleEnable	EnabledStatus,
	vturWanInterface		INTEGER,
	vturClassificationQueue		INTEGER,
	vturClassification8021p		INTEGER,
	vturClassificationVid		INTEGER,
	vturFilterPhysicalPort		INTEGER,
	vturFilterProtocol		INTEGER,
	vturFilterSourceIP		IpAddress,
	vturFilterSourceSubnetMask	IpAddress,
	vturFilterDestinationIP		IpAddress,
	vturFilterDestinationSubnetMask	IpAddress,
	vturFilterSourcePortStart	INTEGER,
	vturFilterSourcePortEnd		INTEGER,
	vturFilterDestinationPortStart	INTEGER,
	vturFilterDestinationPortEnd	INTEGER,
	vturFilterSourceMACAddr		OCTET STRING,
	vturFilterSourceMACMask		OCTET STRING,
	vturFilterDestinationMACAddr	OCTET STRING,
	vturFilterDestinationMACMask	OCTET STRING,
	vturFilter8021p			INTEGER,
	vturFilterProtocolType		INTEGER,
	vturPolicyGatewayIP		IpAddress,
        vturClassificationRowStatus  RowStatus,
        vturClassificationBandwidth		INTEGER
        }

     vturClassificationIndex OBJECT-TYPE
       	SYNTAX  INTEGER
       	MAX-ACCESS  read-only
       	STATUS  current
       	DESCRIPTION
                   	"Display the classification index range from 1 to 8 we got in CPE side"
       	::= { vturClassificationEntry 1 }

     vturClassificationRuleEnable OBJECT-TYPE
       	SYNTAX  EnabledStatus
       	MAX-ACCESS  read-write
       	STATUS  current
       	DESCRIPTION
                   	"Display the classification enable/disable status we got in CPE side"
       	::= { vturClassificationEntry 2 }

     vturWanInterface OBJECT-TYPE
       	SYNTAX  INTEGER
       	MAX-ACCESS  read-write
       	STATUS  current
       	DESCRIPTION
                   	"Display the wan interface index range from 1 to 4 we got in CPE side"
       	::= { vturClassificationEntry 3 }       	

     vturClassificationQueue OBJECT-TYPE
       	SYNTAX  INTEGER
       	MAX-ACCESS  read-write
       	STATUS  current
       	DESCRIPTION
                   	"Display the assigned queue (1-4)802.1p value we got in CPE side"
       	::= { vturClassificationEntry 4 }
      
     vturClassification8021p OBJECT-TYPE
       	SYNTAX  INTEGER
       	MAX-ACCESS  read-write
       	STATUS  current
       	DESCRIPTION
                   	"Mark 802.1p if 802.1q is enabled [0-7]"
       	::= { vturClassificationEntry 5 }

     vturClassificationVid OBJECT-TYPE
       	SYNTAX  INTEGER
       	MAX-ACCESS  read-write
       	STATUS  current
       	DESCRIPTION
                   	"Display the 802.1Q VLAN ID: [1-4094]"
       	::= { vturClassificationEntry 6 }
       	
     vturFilterPhysicalPort OBJECT-TYPE
       	SYNTAX  INTEGER
       	MAX-ACCESS  read-write
       	STATUS  current
       	DESCRIPTION
                   	" Physical LAN Port number"
       	::= { vturClassificationEntry 7 }

     vturFilterProtocol OBJECT-TYPE
                SYNTAX  INTEGER{
		tcp_udp(1),
       	tcp(2),
       	udp(3),
       	icmp(4)
       	}
       	MAX-ACCESS  read-write
       	STATUS  current
       	DESCRIPTION
                   	"Protocol: [TCP/UDP, TCP, UDP, ICMP]  1-4"
       	::= { vturClassificationEntry 8 }       	       	       	       	      

     vturFilterSourceIP OBJECT-TYPE
       	SYNTAX  IpAddress
       	MAX-ACCESS  read-only
       	STATUS  current
       	DESCRIPTION
                   	"Display the filtering source IP we got in CPE side"
       	::= { vturClassificationEntry 9 }

     vturFilterSourceSubnetMask OBJECT-TYPE
       	SYNTAX  IpAddress
       	MAX-ACCESS  read-write
       	STATUS  current
       	DESCRIPTION
                   	"Display the filtering source subnet mask we got in CPE side"
       	::= { vturClassificationEntry 10 }

     vturFilterDestinationIP OBJECT-TYPE
       	SYNTAX  IpAddress
       	MAX-ACCESS  read-write
       	STATUS  current
       	DESCRIPTION
                   	"Display the filtering destination IP we got in CPE side"
       	::= { vturClassificationEntry 11 }       	

     vturFilterDestinationSubnetMask OBJECT-TYPE
       	SYNTAX  IpAddress
       	MAX-ACCESS  read-write
       	STATUS  current
       	DESCRIPTION
                   	"Display the filtering destination subnet mask we got in CPE side"
       	::= { vturClassificationEntry 12 }
       	
     vturFilterSourcePortStart OBJECT-TYPE
       	SYNTAX  INTEGER
       	MAX-ACCESS  read-write
       	STATUS  current
       	DESCRIPTION
                   	"Display the filtering source port start we got in CPE side"
       	::= { vturClassificationEntry 13 }
       	
     vturFilterSourcePortEnd OBJECT-TYPE
       	SYNTAX  INTEGER
       	MAX-ACCESS  read-write
       	STATUS  current
       	DESCRIPTION
                   	"Display the filtering source port end we got in CPE side"
       	::= { vturClassificationEntry 14 }

     vturFilterDestinationPortStart OBJECT-TYPE
       	SYNTAX  INTEGER
       	MAX-ACCESS  read-write
       	STATUS  current
       	DESCRIPTION
                   	"Display the filtering destination port start we got in CPE side"
       	::= { vturClassificationEntry 15 }
       	
     vturFilterDestinationPortEnd OBJECT-TYPE
       	SYNTAX  INTEGER
       	MAX-ACCESS  read-write
       	STATUS  current
       	DESCRIPTION
                   	"Display the filtering destination end port we got in CPE side"
       	::= { vturClassificationEntry 16 }       	

     vturFilterSourceMACAddr OBJECT-TYPE
       	SYNTAX  OCTET STRING
       	MAX-ACCESS  read-write
       	STATUS  current
       	DESCRIPTION
                   	"Display the filtering source MAC addr we got in CPE side"
       	::= { vturClassificationEntry 17 }
       	
     vturFilterSourceMACMask OBJECT-TYPE
       	SYNTAX  OCTET STRING
       	MAX-ACCESS  read-write
       	STATUS  current
       	DESCRIPTION
                   	"Display the filtering source MAC mask we got in CPE side"
       	::= { vturClassificationEntry 18 }      

     vturFilterDestinationMACAddr OBJECT-TYPE
       	SYNTAX  OCTET STRING
       	MAX-ACCESS  read-write
       	STATUS  current
       	DESCRIPTION
                   	"Display the filtering destination MAC addr we got in CPE side"
       	::= { vturClassificationEntry 19 }
       	
     vturFilterDestinationMACMask OBJECT-TYPE
       	SYNTAX  OCTET STRING
       	MAX-ACCESS  read-write
       	STATUS  current
       	DESCRIPTION
                   	"Display the filtering destination MAC mask we got in CPE side"
       	::= { vturClassificationEntry 20 }  

     vturFilter8021p OBJECT-TYPE
       	SYNTAX  INTEGER
       	MAX-ACCESS  read-write
       	STATUS  current
       	DESCRIPTION
                   	"Display the filtering 802.1p value we got in CPE side"
       	::= { vturClassificationEntry 21 }
       	
     vturFilterProtocolType OBJECT-TYPE
       	SYNTAX  INTEGER
       	MAX-ACCESS  read-write
       	STATUS  current
       	DESCRIPTION
                   	"Display the filtering protocol type we got in CPE side"
       	::= { vturClassificationEntry 22 } 

     vturPolicyGatewayIP OBJECT-TYPE
       	SYNTAX  IpAddress
       	MAX-ACCESS  read-write
       	STATUS  current
       	DESCRIPTION
                   	"Display the filtering protocol type we got in CPE side"
       	::= { vturClassificationEntry 23 } 

      vturClassificationRowStatus OBJECT-TYPE
        SYNTAX  RowStatus
        MAX-ACCESS  read-create
        STATUS  current
        DESCRIPTION
                      	""
        ::= { vturClassificationEntry 24 }
           
      vturClassificationBandwidth OBJECT-TYPE
       	SYNTAX  INTEGER
       	MAX-ACCESS  read-write
       	STATUS  current
       	DESCRIPTION
                   	"Display limited bandwidth control(1-255 0:disable) we got in CPE side"
       	::= { vturClassificationEntry 25 }
           


-- vturMiscSetup
		vturMiscSetup     	OBJECT IDENTIFIER ::= { vturSwitchSetup 6 }


-- vturMntTable
    vturMntTable OBJECT-TYPE
       	SYNTAX	SEQUENCE OF VturMntEntry
       	MAX-ACCESS  not-accessible
       	STATUS  current
       	DESCRIPTION
      	      	""
       	::= { vturMiscSetup 1 }

	vturMntEntry OBJECT-TYPE
       	SYNTAX	VturMntEntry
       	MAX-ACCESS	not-accessible
       	STATUS	current
       	DESCRIPTION    	"An entry in VTUR Misc Table."
       	INDEX          	{ dot1dBasePort }
       	::= { vturMntTable 1 }

    VturMntEntry ::=
       	SEQUENCE {
        mntOperation	INTEGER,    
        mntCommit		INTEGER,
        mntStatus		INTEGER,
        mntRefetchCPEInfo	INTEGER
        }

    mntOperation OBJECT-TYPE
       	SYNTAX  INTEGER {
       	layer2Setup(1),
       	portSetup(2),
       	priorityQueueSetup(3),
       	dot1qVlanSetup(4),
       	portBasedVlanSetup(5),
       	loadFactoryDefault(6),
       	resetSW(7),
        apBasicSetup(8),
        apSecuritySetup(9),
        apRadiusSetup(10),
        apMacFilterSetup(11),
        apMacFilterAddrSetup(12),
        reinit(13),
        consoleSetup(14),
        remoteFunctionSetup(15),         
        regetstatue(16),         
        protocolBasedVlanSetup(17),
        vturWanSetup(18),
        vturClassificationSetup(19),
        vturLanSetup(20),
        vturResetCounter(21),
        loadDefaultWithoutIP(22)
       	}
       	MAX-ACCESS  read-write
       	STATUS  current
       	DESCRIPTION
                   	"Specify the operation of VTUR"
       	::= { vturMntEntry 1 }
    
    mntCommit OBJECT-TYPE
       	SYNTAX  INTEGER {
       	idle(0),
       	commit(1)
       	}
       	MAX-ACCESS  read-write
       	STATUS  current
       	DESCRIPTION
                    	"Apply maintenance setting to vtur"
        ::= { vturMntEntry 2 }
    
    mntStatus OBJECT-TYPE
       	SYNTAX  INTEGER {
       	in_progress(0),
       	success(1),
       	fail(2)
       	}
       	MAX-ACCESS  read-only
       	STATUS  current
       	DESCRIPTION
                    	"Display the current status regarding to the operation."
        ::= { vturMntEntry 3 }

    mntRefetchCPEInfo OBJECT-TYPE
    	SYNTAX	INTEGER	{
    	none(0),
    	refetching(1)
    	}
    	MAX-ACCESS	read-write
    	STATUS	current
    	DESCRIPTION
    					"Refetch current CPE information."
    	::= { vturMntEntry 4 }

-- vturAPSetup
	vturAPSetup     	OBJECT IDENTIFIER ::= { vturSwitchSetup 7 }
	
-- vturAPGeneral
        vturAPGeneral OBJECT IDENTIFIER ::= { vturAPSetup 1 }

-- vturAPGeneralStatisticsTable

        vturAPGeneralStatisticsTable  OBJECT-TYPE
        SYNTAX	SEQUENCE OF VturAPGeneralStatisticsEntry
        MAX-ACCESS  not-accessible
        STATUS  current
        DESCRIPTION
                 	""
        ::= { vturAPGeneral 1 }

		vturAPGeneralStatisticsEntry OBJECT-TYPE
       		SYNTAX	VturAPGeneralStatisticsEntry
       		MAX-ACCESS	not-accessible
       		STATUS	current
	       	DESCRIPTION    	"An entry in VTUR AP General Statistics Table."
	       	INDEX          	{ dot1dBasePort }
	       	::= { vturAPGeneralStatisticsTable 1 }

		VturAPGeneralStatisticsEntry ::=
	       	SEQUENCE {
	        lanRxBytes	Counter32,
	        lanRxPkts	Counter32,
	        lanTxBytes	Counter32,
	        lanTxPkts	Counter32,
	        vdslRxBytes	Counter32,
	        vdslRxPkts	Counter32,
	        vdslTxBytes	Counter32,
	        vdslTxPkts	Counter32,
	        wlanRxBytes	Counter32,
	        wlanRxPkts	Counter32,
	        wlanRxErrs	Counter32,
	        wlanRxDrops	Counter32,
	        wlanTxBytes	Counter32,
	        wlanTxPkts	Counter32,
	        wlanTxErrs	Counter32,
	        wlanTxDrops	Counter32
	        }


		        lanRxBytes OBJECT-TYPE
        		SYNTAX  Counter32
        		MAX-ACCESS  read-only
        		STATUS  current
        		DESCRIPTION
                      		"Received bytes on LAN"
        		::= { vturAPGeneralStatisticsEntry 1 }

		        lanRxPkts OBJECT-TYPE
        		SYNTAX  Counter32
        		MAX-ACCESS  read-only
        		STATUS  current
        		DESCRIPTION
                      		"Received frames on LAN"
        		::= { vturAPGeneralStatisticsEntry 2 }


		        lanTxBytes OBJECT-TYPE
        		SYNTAX  Counter32
        		MAX-ACCESS  read-only
        		STATUS  current
        		DESCRIPTION
                      		"Transmitted bytes on LAN"
        		::= { vturAPGeneralStatisticsEntry 3 }

		        lanTxPkts OBJECT-TYPE
        		SYNTAX  Counter32
        		MAX-ACCESS  read-only
        		STATUS  current
        		DESCRIPTION
                      		"Transmitted frames on LAN"
        		::= { vturAPGeneralStatisticsEntry 4 }

		        vdslRxBytes OBJECT-TYPE
        		SYNTAX  Counter32
        		MAX-ACCESS  read-only
        		STATUS  current
        		DESCRIPTION
                      		"Received bytes on VDSL"
        		::= { vturAPGeneralStatisticsEntry 5 }

		        vdslRxPkts OBJECT-TYPE
        		SYNTAX  Counter32
        		MAX-ACCESS  read-only
        		STATUS  current
        		DESCRIPTION
                      		"Received frames on VDSL"
        		::= { vturAPGeneralStatisticsEntry 6 }

		        vdslTxBytes OBJECT-TYPE
        		SYNTAX  Counter32
        		MAX-ACCESS  read-only
        		STATUS  current
        		DESCRIPTION
                      		"Transmitted bytes on VDSL"
        		::= { vturAPGeneralStatisticsEntry 7 }

		        vdslTxPkts OBJECT-TYPE
        		SYNTAX  Counter32
        		MAX-ACCESS  read-only
        		STATUS  current
        		DESCRIPTION
                      		"Transmitted frames on VDSL"
        		::= { vturAPGeneralStatisticsEntry 8 }

		        wlanRxBytes OBJECT-TYPE
        		SYNTAX  Counter32
        		MAX-ACCESS  read-only
        		STATUS  current
        		DESCRIPTION
                      		"Received bytes on WLAN"
        		::= { vturAPGeneralStatisticsEntry 9 }

		        wlanRxPkts OBJECT-TYPE
        		SYNTAX  Counter32
        		MAX-ACCESS  read-only
        		STATUS  current
        		DESCRIPTION
                      		"Received frames on WLAN "
        		::= { vturAPGeneralStatisticsEntry 10 }

		        wlanRxErrs OBJECT-TYPE
        		SYNTAX  Counter32
        		MAX-ACCESS  read-only
        		STATUS  current
        		DESCRIPTION
                      		"Received error frames on WLAN "
        		::= { vturAPGeneralStatisticsEntry 11 }

		        wlanRxDrops OBJECT-TYPE
        		SYNTAX  Counter32
        		MAX-ACCESS  read-only
        		STATUS  current
        		DESCRIPTION
                      		"Received drop frames on WLAN "
        		::= { vturAPGeneralStatisticsEntry 12 }

		        wlanTxBytes OBJECT-TYPE
        		SYNTAX  Counter32
        		MAX-ACCESS  read-only
        		STATUS  current
        		DESCRIPTION
                      		"Transmitted bytes on WLAN "
        		::= { vturAPGeneralStatisticsEntry 13 }

		        wlanTxPkts OBJECT-TYPE
        		SYNTAX  Counter32
        		MAX-ACCESS  read-only
        		STATUS  current
        		DESCRIPTION
                      		"Transmitted frames on WLAN "
        		::= { vturAPGeneralStatisticsEntry 14 }

		        wlanTxErrs OBJECT-TYPE
        		SYNTAX  Counter32
        		MAX-ACCESS  read-only
        		STATUS  current
        		DESCRIPTION
                      		"Transmitted error frames on WLAN "
        		::= { vturAPGeneralStatisticsEntry 15 }

		        wlanTxDrops OBJECT-TYPE
        		SYNTAX  Counter32
        		MAX-ACCESS  read-only
        		STATUS  current
        		DESCRIPTION
                      		"Transmitted drop frames on WLAN "
        		::= { vturAPGeneralStatisticsEntry 16 }

        vturAPWlan OBJECT IDENTIFIER ::= { vturAPSetup 2 }

-- vturAPWlanBasicTable

        vturAPWlanBasicTable  OBJECT-TYPE
        SYNTAX	SEQUENCE OF VturAPWlanBasicEntry
        MAX-ACCESS  not-accessible
        STATUS  current
        DESCRIPTION
                 	""
        ::= { vturAPWlan 1 }

		vturAPWlanBasicEntry OBJECT-TYPE
       		SYNTAX	VturAPWlanBasicEntry
       		MAX-ACCESS	not-accessible
       		STATUS	current
	       	DESCRIPTION    	"An entry in VTUR AP Wlan Basic Table."
	       	INDEX          	{ dot1dBasePort }
	       	::= { vturAPWlanBasicTable 1 }

		VturAPWlanBasicEntry ::=
	       	SEQUENCE {
	        enable	INTEGER,
	        ssid	DisplayString,
	        bssid	MacAddress,
	        hidden	INTEGER,
	        channel	INTEGER,
	        mode	INTEGER,
	        txPower	INTEGER,
	        multicastRate	INTEGER
	        }


		        enable OBJECT-TYPE
        		SYNTAX  INTEGER
        		MAX-ACCESS  read-write
        		STATUS  current
        		DESCRIPTION
                      		"0: disable wlan
                      		 1: enable wlan"
        		::= { vturAPWlanBasicEntry 1 }

		        ssid OBJECT-TYPE
        		SYNTAX  DisplayString
        		MAX-ACCESS  read-write
        		STATUS  current
        		DESCRIPTION
                      		"SSID of the AP"
        		::= { vturAPWlanBasicEntry 2 }

		        bssid OBJECT-TYPE
        		SYNTAX  MacAddress
        		MAX-ACCESS  read-only
        		STATUS  current
        		DESCRIPTION
                      		"Mac address of AP"
        		::= { vturAPWlanBasicEntry 3 }

		        hidden OBJECT-TYPE
        		SYNTAX  INTEGER
        		MAX-ACCESS  read-write
        		STATUS  current
        		DESCRIPTION
                      		"0: not hide AP's SSID
                      		 1: hide AP's SSID"
        		::= { vturAPWlanBasicEntry 4 }

		        channel OBJECT-TYPE
        		SYNTAX  INTEGER
        		MAX-ACCESS  read-write
        		STATUS  current
        		DESCRIPTION
                      		"Channel number of the AP"
        		::= { vturAPWlanBasicEntry 5 }

		        mode OBJECT-TYPE
        		SYNTAX  INTEGER
        		MAX-ACCESS  read-write
        		STATUS  current
        		DESCRIPTION
                      		"1: B or G mix mode
                      		 2: Pure G mode
                      		 3: Pure B mode"
        		::= { vturAPWlanBasicEntry 6 }

		        txPower OBJECT-TYPE
        		SYNTAX  INTEGER
        		MAX-ACCESS  read-write
        		STATUS  current
        		DESCRIPTION
                      		"Transmit power
                      		 1: 30 mW
                      		 2: 15 mW"
        		::= { vturAPWlanBasicEntry 7 }

		        multicastRate OBJECT-TYPE
        		SYNTAX  INTEGER
        		MAX-ACCESS  read-write
        		STATUS  current
        		DESCRIPTION
                      		"Transmit rate of multicast packets. If the value not zero, transmit rate is value * 500kbps
                      		 0: auto
                      		 2, 4, 11, 22: Transmit rate = 1, 2, 5.5, 11 Mbps when mode = pure B mode
                      		 12, 18, 24, 36, 48, 96, 108: Transmit rate = 6, 9, 12, 18, 24, 36, 48, 54 Mbps when mode = pure G mode2, 4, 11, 12, 18, 22, 24, 36, 48, 96, 108: Transmit rate = 1, 2, 5.5, 6, 9, 11, 12, 18, 24, 36, 48, 54 Mbps when mode = B or G mix mode"
        		::= { vturAPWlanBasicEntry 8 }

-- vturAPWlanSecurityTable

        vturAPWlanSecurityTable  OBJECT-TYPE
        SYNTAX	SEQUENCE OF VturAPWlanSecurityEntry
        MAX-ACCESS  not-accessible
        STATUS  current
        DESCRIPTION
                 	""
        ::= { vturAPWlan 2 }

		vturAPWlanSecurityEntry OBJECT-TYPE
       		SYNTAX	VturAPWlanSecurityEntry
       		MAX-ACCESS	not-accessible
       		STATUS	current
	       	DESCRIPTION    	"An entry in VTUR AP Wlan Security Table."
	       	INDEX          	{ dot1dBasePort }
	       	::= { vturAPWlanSecurityTable 1 }

		VturAPWlanSecurityEntry ::=
	       	SEQUENCE {
	        securityMode	INTEGER,
	        wepEncryp	INTEGER,
	        keyId		INTEGER,
	        key1		DisplayString,
	        key2		DisplayString,
	        key3		DisplayString,
	        key4		DisplayString,
	        psk		DisplayString,
	        wpaMix		INTEGER,
	        reAuthTime	INTEGER,
	        idleTime	INTEGER,
	        gtkTime		INTEGER
	        }

		        securityMode OBJECT-TYPE
        		SYNTAX  INTEGER
        		MAX-ACCESS  read-write
        		STATUS  current
        		DESCRIPTION
                      		"1: No security
                      		 2: Static WEP
                      		 3: WPA-PSK
                      		 4: WPA
                      		 5: WPA2
                      		 6: WPA2-PSK"
        		::= { vturAPWlanSecurityEntry 1 }

		        wepEncryp OBJECT-TYPE
        		SYNTAX  INTEGER
        		MAX-ACCESS  read-write
        		STATUS  current
        		DESCRIPTION
                      		"This field is for SecurityMode = static WEP.
                      		 1: 64-Bit
                      		 2: 128-Bit"
        		::= { vturAPWlanSecurityEntry 2 }

		        keyId OBJECT-TYPE
        		SYNTAX  INTEGER
        		MAX-ACCESS  read-write
        		STATUS  current
        		DESCRIPTION
                      		"This field is for SecurityMode = static WEP. It indicate which key will be used for encryption. 
                      		 If KeyId is equal to 1, AP will use Key1 to encrypt frame."
        		::= { vturAPWlanSecurityEntry 3 }

		        key1 OBJECT-TYPE
        		SYNTAX  DisplayString
        		MAX-ACCESS  read-write
        		STATUS  current
        		DESCRIPTION
                      		"This field is for SecurityMode = static WEP.
                      		 If WEPEncryp is 64-Bit, key1 will be 10 heximal digits.
                      		 If WEPEncryp is 128-Bit, key1 will be 26 heximal digits."
        		::= { vturAPWlanSecurityEntry 4 }

		        key2 OBJECT-TYPE
        		SYNTAX  DisplayString
        		MAX-ACCESS  read-write
        		STATUS  current
        		DESCRIPTION
                      		"This field is for SecurityMode = static WEP.
                      		 If WEPEncryp is 64-Bit, key2 will be 10 heximal digits.
                      		 If WEPEncryp is 128-Bit, key2 will be 26 heximal digits."
        		::= { vturAPWlanSecurityEntry 5 }

		        key3 OBJECT-TYPE
        		SYNTAX  DisplayString
        		MAX-ACCESS  read-write
        		STATUS  current
        		DESCRIPTION
                      		"This field is for SecurityMode = static WEP.
                      		 If WEPEncryp is 64-Bit, key3 will be 10 heximal digits.
                      		 If WEPEncryp is 128-Bit, key3 will be 26 heximal digits."
        		::= { vturAPWlanSecurityEntry 6 }

		        key4 OBJECT-TYPE
        		SYNTAX  DisplayString
        		MAX-ACCESS  read-write
        		STATUS  current
        		DESCRIPTION
                      		"This field is for SecurityMode = static WEP.
                      		 If WEPEncryp is 64-Bit, key4 will be 10 heximal digits.
                      		 If WEPEncryp is 128-Bit, key4 will be 26 heximal digits."
        		::= { vturAPWlanSecurityEntry 7 }

		        psk OBJECT-TYPE
        		SYNTAX  DisplayString
        		MAX-ACCESS  read-write
        		STATUS  current
        		DESCRIPTION
                      		"This field is for SecurityMode = WPA-PSK or WPA2-PSK. It means Pre-Shared Key"
        		::= { vturAPWlanSecurityEntry 8 }

		        wpaMix OBJECT-TYPE
        		SYNTAX  INTEGER
        		MAX-ACCESS  read-write
        		STATUS  current
        		DESCRIPTION
                      		"This field is for SecurityMode = WPA2 or WPA2-PSK. 
                      		 When WPAMix is enable on WPA2, stations with WPA2-AES or WPA-TKIP could connect to AP.
                      		 When WPAMix is enable on WPA2-PSK, stations with WPA2-PSK-AES or WPA-PSK-TKIP could connect to AP.
                      		 0: disable
                      		 1: enable"
        		::= { vturAPWlanSecurityEntry 9 }

		        reAuthTime OBJECT-TYPE
        		SYNTAX  INTEGER
        		MAX-ACCESS  read-write
        		STATUS  current
        		DESCRIPTION
                      		"This field is for SecurityMode = WPA-PSK, WPA2-PSK, WPA or WPA2. 
                      		 AP will trigger re-authentication with station every [ReAuthTime] seconds."
        		::= { vturAPWlanSecurityEntry 10 }

		        idleTime OBJECT-TYPE
        		SYNTAX  INTEGER
        		MAX-ACCESS  read-write
        		STATUS  current
        		DESCRIPTION
                      		"This field is for SecurityMode = WPA-PSK, WPA2-PSK, WPA or WPA2. 
                      		 AP will flush station¡¦s information if there are no packets from station for [idleTime] seconds."
        		::= { vturAPWlanSecurityEntry 11 }

		        gtkTime OBJECT-TYPE
        		SYNTAX  INTEGER
        		MAX-ACCESS  read-write
        		STATUS  current
        		DESCRIPTION
                      		"This field is for SecurityMode = WPA-PSK, WPA2-PSK, WPA or WPA2. 
                      		 AP will trigger the update of group key with station every [GTKTime] seconds."
        		::= { vturAPWlanSecurityEntry 12 }

-- vturAPWlanRadiusTable

        vturAPWlanRadiusTable  OBJECT-TYPE
        SYNTAX	SEQUENCE OF VturAPWlanRadiusEntry
        MAX-ACCESS  not-accessible
        STATUS  current
        DESCRIPTION
                 	""
        ::= { vturAPWlan 3 }

		vturAPWlanRadiusEntry OBJECT-TYPE
       		SYNTAX	VturAPWlanRadiusEntry
       		MAX-ACCESS	not-accessible
       		STATUS	current
	       	DESCRIPTION    	"An entry in VTUR AP Wlan Security Table."
	       	INDEX          	{ dot1dBasePort }
	       	::= { vturAPWlanRadiusTable 1 }

		VturAPWlanRadiusEntry ::=
	       	SEQUENCE {
	        authServIP	InetAddress,
	        authServPort	INTEGER,
	        authServSecret	DisplayString,
	        accServActive	INTEGER,
	        accServIP	InetAddress,
	        accServPort	INTEGER,
	        accServSecret	DisplayString
	        }


		        authServIP OBJECT-TYPE
			SYNTAX      InetAddress
        		MAX-ACCESS  read-write
        		STATUS  current
        		DESCRIPTION
                      		"This field is the IP address of authentication server."
        		::= { vturAPWlanRadiusEntry 1 }

		        authServPort OBJECT-TYPE
        		SYNTAX  INTEGER
        		MAX-ACCESS  read-write
        		STATUS  current
        		DESCRIPTION
                      		"This field is the port number of authentication server."
        		::= { vturAPWlanRadiusEntry 2 }

		        authServSecret OBJECT-TYPE
        		SYNTAX  DisplayString
        		MAX-ACCESS  read-write
        		STATUS  current
        		DESCRIPTION
                      		"This field is the shared secret of authentication server."
        		::= { vturAPWlanRadiusEntry 3 }

		        accServActive OBJECT-TYPE
        		SYNTAX  INTEGER
        		MAX-ACCESS  read-write
        		STATUS  current
        		DESCRIPTION
                      		"This field is for activating or inactivating accounting server.
                      		 0: inactivate accounting server.
                      		 1: activate accounting server"
        		::= { vturAPWlanRadiusEntry 4 }


		        accServIP OBJECT-TYPE
        		SYNTAX      InetAddress
        		MAX-ACCESS  read-write
        		STATUS  current
        		DESCRIPTION
                      		"This field is the IP address of accounting server."
        		::= { vturAPWlanRadiusEntry 5 }

		        accServPort OBJECT-TYPE
        		SYNTAX  INTEGER
        		MAX-ACCESS  read-write
        		STATUS  current
        		DESCRIPTION
                      		"This field is the port number of accounting server."
        		::= { vturAPWlanRadiusEntry 6 }

		        accServSecret OBJECT-TYPE
        		SYNTAX  DisplayString
        		MAX-ACCESS  read-write
        		STATUS  current
        		DESCRIPTION
                      		"This field is the shared secret of accounting server."
        		::= { vturAPWlanRadiusEntry 7 }



       	vturAPWlanMacFilter OBJECT IDENTIFIER ::= { vturAPWlan 4 }
-- vturAPWlanMacFilterTable

        vturAPWlanMacFilterTable  OBJECT-TYPE
        SYNTAX	SEQUENCE OF VturAPWlanMacFilterEntry
        MAX-ACCESS  not-accessible
        STATUS  current
        DESCRIPTION
                 	""
        ::= { vturAPWlanMacFilter 1 }

		vturAPWlanMacFilterEntry OBJECT-TYPE
       		SYNTAX	VturAPWlanMacFilterEntry
       		MAX-ACCESS	not-accessible
       		STATUS	current
	       	DESCRIPTION    	"An entry in VTUR AP Wlan Mac Filter Table."
	       	INDEX          	{ dot1dBasePort }
	       	::= { vturAPWlanMacFilterTable 1 }

		VturAPWlanMacFilterEntry ::=
	       	SEQUENCE {
	        macFltActive	INTEGER,
	        macFltAction	INTEGER
	        }

		        macFltActive OBJECT-TYPE
        		SYNTAX  INTEGER
        		MAX-ACCESS  read-write
        		STATUS  current
        		DESCRIPTION
                      		"Activate or inactivate wlan MAC filter.
                      		 0: Inactive
                      		 1: Active"
        		::= { vturAPWlanMacFilterEntry 1 }

		        macFltAction OBJECT-TYPE
        		SYNTAX  INTEGER
        		MAX-ACCESS  read-write
        		STATUS  current
        		DESCRIPTION
                      		"0: allow association for station which matches the address which is defined in MacFltAddr1~MacFltAddr8.
                      		 1: deny association for station which matches the address which is defined in MacFltAddr1~MacFltAddr8."
        		::= { vturAPWlanMacFilterEntry 2 }


-- vturAPWlanMacFltAddrTable

        vturAPWlanMacFltAddrTable  OBJECT-TYPE
        SYNTAX	SEQUENCE OF VturAPWlanMacFltAddrEntry
        MAX-ACCESS  not-accessible
        STATUS  current
        DESCRIPTION
                 	""
        ::= { vturAPWlanMacFilter 2 }

		vturAPWlanMacFltAddrEntry OBJECT-TYPE
       		SYNTAX	VturAPWlanMacFltAddrEntry
       		MAX-ACCESS	not-accessible
       		STATUS	current
	       	DESCRIPTION    	"An entry in VTUR AP Wlan Security Table."
	       	INDEX          	{ dot1dBasePort, fltStaIndex }
	       	::= { vturAPWlanMacFltAddrTable 1 }
	       	
		VturAPWlanMacFltAddrEntry ::=
	       	SEQUENCE {
	        fltStaIndex	INTEGER,
	        macFltAddr	MacAddress
	        }

		        fltStaIndex  OBJECT-TYPE
        		SYNTAX  INTEGER
        		MAX-ACCESS  read-only
        		STATUS  current
        		DESCRIPTION
                      		"The index for Mac filter"
        		::= { vturAPWlanMacFltAddrEntry 1 }

		        macFltAddr  OBJECT-TYPE
        		SYNTAX  MacAddress
        		MAX-ACCESS  read-write
        		STATUS  current
        		DESCRIPTION
                      		"The address for Mac filter"
        		::= { vturAPWlanMacFltAddrEntry 2 }


-- vturAPWlanStatisticsTable

	
	vturAPWlanStatisticsTable  OBJECT-TYPE
        SYNTAX	SEQUENCE OF VturAPWlanStatisticsEntry
        MAX-ACCESS  not-accessible
        STATUS  current
        DESCRIPTION
                 	""
        ::= { vturAPWlan 5 }

		vturAPWlanStatisticsEntry OBJECT-TYPE
       		SYNTAX	VturAPWlanStatisticsEntry
       		MAX-ACCESS	not-accessible
       		STATUS	current
	       	DESCRIPTION    	"An entry in VTUR AP Wlan Security Table."
	       	INDEX          	{ dot1dBasePort }
	       	::= { vturAPWlanStatisticsTable 1 }

		VturAPWlanStatisticsEntry ::=
	       	SEQUENCE {
	        inPkts		INTEGER,
	        inOctets	INTEGER,
	        inUCasts	INTEGER,
	        inMCasts	INTEGER,
	        rxFCSErrors	INTEGER,
	        outPkts		INTEGER,
	        outOctets	INTEGER,
	        outUCasts	INTEGER,
	        outMCasts	INTEGER
	        }

		        inPkts  OBJECT-TYPE
        		SYNTAX  INTEGER
        		MAX-ACCESS  read-only
        		STATUS  current
        		DESCRIPTION
                      		"Same as WLANRxPkts in vturAPGeneral.vturAPGeneralStatistics MIB "
        		::= { vturAPWlanStatisticsEntry 1 }

		        inOctets  OBJECT-TYPE
        		SYNTAX  INTEGER
        		MAX-ACCESS  read-only
        		STATUS  current
        		DESCRIPTION
                      		"Same as WLANRxBytes in vturAPGeneral.vturAPGeneralStatistics MIB "
        		::= { vturAPWlanStatisticsEntry 2 }

		        inUCasts  OBJECT-TYPE
        		SYNTAX  INTEGER
        		MAX-ACCESS  read-only
        		STATUS  current
        		DESCRIPTION
                      		"Received unicast frames"
        		::= { vturAPWlanStatisticsEntry 3 }

		        inMCasts  OBJECT-TYPE
        		SYNTAX  INTEGER
        		MAX-ACCESS  read-only
        		STATUS  current
        		DESCRIPTION
                      		"Received multicast frames"
        		::= { vturAPWlanStatisticsEntry 4 }

		        rxFCSErrors  OBJECT-TYPE
        		SYNTAX  INTEGER
        		MAX-ACCESS  read-only
        		STATUS  current
        		DESCRIPTION
                      		"Same as WLANRxErrs in vturAPGeneral.vturAPGeneralStatistics MIB"
        		::= { vturAPWlanStatisticsEntry 5 }

		        outPkts  OBJECT-TYPE
        		SYNTAX  INTEGER
        		MAX-ACCESS  read-only
        		STATUS  current
        		DESCRIPTION
                      		"Same as WLANTxPkts in vturAPGeneral.vturAPGeneralStatistics MIB"
        		::= { vturAPWlanStatisticsEntry 6 }

		        outOctets  OBJECT-TYPE
        		SYNTAX  INTEGER
        		MAX-ACCESS  read-only
        		STATUS  current
        		DESCRIPTION
                      		"Same as WLANTxBytes in vturAPGeneral.vturAPGeneralStatistics MIB"
        		::= { vturAPWlanStatisticsEntry 7 }

		        outUCasts  OBJECT-TYPE
        		SYNTAX  INTEGER
        		MAX-ACCESS  read-only
        		STATUS  current
        		DESCRIPTION
                      		"Transmitted unicast frames"
        		::= { vturAPWlanStatisticsEntry 8 }

		        outMCasts  OBJECT-TYPE
        		SYNTAX  INTEGER
        		MAX-ACCESS  read-only
        		STATUS  current
        		DESCRIPTION
                      		"Transmitted multicast frames"
        		::= { vturAPWlanStatisticsEntry 9 }


-- vturAPWlanStaListTable


	vturAPWlanStaListTable  OBJECT-TYPE
        SYNTAX	SEQUENCE OF VturAPWlanStaListEntry
        MAX-ACCESS  not-accessible
        STATUS  current
        DESCRIPTION
                 	""
        ::= { vturAPWlan 6 }

		vturAPWlanStaListEntry OBJECT-TYPE
       		SYNTAX	VturAPWlanStaListEntry
       		MAX-ACCESS	not-accessible
       		STATUS	current
	       	DESCRIPTION    	"An entry in VTUR AP Wlan Security Table."
	       	INDEX          	{ dot1dBasePort, staIndex }
	       	::= { vturAPWlanStaListTable 1 }

		VturAPWlanStaListEntry ::=
	       	SEQUENCE {
	        staIndex	INTEGER,
	        staMacAddr	MacAddress
	        }

		        staIndex  OBJECT-TYPE
        		SYNTAX  INTEGER
        		MAX-ACCESS  read-only
        		STATUS  current
        		DESCRIPTION
                      		"The index of associated WLAN STA. Max = 32, Min = 1"
        		::= { vturAPWlanStaListEntry 1 }
        	
		        staMacAddr  OBJECT-TYPE
        		SYNTAX  MacAddress
        		MAX-ACCESS  read-only
        		STATUS  current
        		DESCRIPTION
                      		"The address of associated WLAN STA "
        		::= { vturAPWlanStaListEntry 2 }




-- vturConsoleSetup
		vturConsoleSetup     	OBJECT IDENTIFIER ::= { vturSwitchSetup 8 }

		vturConsoleTable OBJECT-TYPE
       	SYNTAX	SEQUENCE OF VturConsoleEntry
       	MAX-ACCESS  not-accessible
       	STATUS  current
       	DESCRIPTION
      	      	""
       	::= { vturConsoleSetup 1 }

	vturConsoleEntry OBJECT-TYPE
       	SYNTAX	VturConsoleEntry
       	MAX-ACCESS	not-accessible
       	STATUS	current
       	DESCRIPTION    	"An entry in vturConsoleTable."
       	INDEX          	{ dot1dBasePort}
       	::= { vturConsoleTable 1 }

        VturConsoleEntry ::=
       	SEQUENCE {
       	vturConsoleSet			INTEGER,
       	vturConsoleAdminPassword	OCTET STRING,
       	vturConsoleUserPassword		OCTET STRING
        }


        vturConsoleSet OBJECT-TYPE
        SYNTAX  INTEGER {
         		enable(1),
         		disable(2)
        }
        MAX-ACCESS  read-write
        STATUS  current
        DESCRIPTION
                      ""
        ::= { vturConsoleEntry 1 }

	vturConsoleAdminPassword OBJECT-TYPE
		SYNTAX  OCTET STRING
		MAX-ACCESS  read-write
		STATUS  current
		DESCRIPTION
			"The operation for vtur device admin password"
		::= { vturConsoleEntry 2 }
		
	vturConsoleUserPassword OBJECT-TYPE
		SYNTAX  OCTET STRING
		MAX-ACCESS  read-write
		STATUS  current
		DESCRIPTION
			"The operation for vtur device user password"
		::= { vturConsoleEntry 3 }		

-- vturRemoteFunctionSetup
	vturRemoteFunctionSetup     	OBJECT IDENTIFIER ::= { vturSwitchSetup 9 }

	remoteFunctionTable OBJECT-TYPE
       	SYNTAX	SEQUENCE OF RemoteFunctionEntry
       	MAX-ACCESS  not-accessible
       	STATUS  current
       	DESCRIPTION
      	      	""
       	::= { vturRemoteFunctionSetup 1 }

	remoteFunctionEntry OBJECT-TYPE
       	SYNTAX	RemoteFunctionEntry
       	MAX-ACCESS	not-accessible
       	STATUS	current
       	DESCRIPTION    	"An entry in RemoteFunctionTable."
       	INDEX          	{ dot1dBasePort}
       	::= { remoteFunctionTable 1 }

        RemoteFunctionEntry ::=
       	SEQUENCE {
       	telnet  INTEGER,
       	tftp    INTEGER,
       	web     INTEGER,
       	snmp    INTEGER,
       	ssh     INTEGER,
       	wireless INTEGER
        }


        telnet OBJECT-TYPE
        SYNTAX  INTEGER {
         		enable_all(1),
         		disable_all(2),
         		enable_lan_only(3),
         		enable_wan_only(4)
        }
        MAX-ACCESS  read-write
        STATUS  current
        DESCRIPTION
                      ""
        ::= { remoteFunctionEntry 3 }

        tftp OBJECT-TYPE
        SYNTAX  INTEGER {
         		enable_all(1),
         		disable_all(2),
         		enable_lan_only(3),
         		enable_wan_only(4)
        }
        MAX-ACCESS  read-write
        STATUS  current
        DESCRIPTION
                      ""
        ::= { remoteFunctionEntry 4 }

        web OBJECT-TYPE
        SYNTAX  INTEGER {
         		enable_all(1),
         		disable_all(2),
         		enable_lan_only(3),
         		enable_wan_only(4)
        }
        MAX-ACCESS  read-write
        STATUS  current
        DESCRIPTION
                      ""
        ::= { remoteFunctionEntry 5 }

        snmp OBJECT-TYPE
        SYNTAX  INTEGER {
         		enable_all(1),
         		disable_all(2),
         		enable_lan_only(3),
         		enable_wan_only(4)
        }
        MAX-ACCESS  read-write
        STATUS  current
        DESCRIPTION
                      ""
        ::= { remoteFunctionEntry 6 }

        ssh OBJECT-TYPE
        SYNTAX  INTEGER {
           		enable_all(1),
         		disable_all(2),
         		enable_lan_only(3),
         		enable_wan_only(4)
        }
        MAX-ACCESS  read-write
        STATUS  current
        DESCRIPTION
                      ""
        ::= { remoteFunctionEntry 7 }

        wireless OBJECT-TYPE
        SYNTAX  INTEGER {
           		disable(1),
         		enable(2)
        }
        MAX-ACCESS  read-write
        STATUS  current
        DESCRIPTION
                      ""
        ::= { remoteFunctionEntry 8 }
---------------------------------------------------------------------------
---------------------------------------------------------------------------
-- vturMacTableSetup
	vturMacTableSetup     	OBJECT IDENTIFIER ::= { vturSwitchSetup 10 }

	vturMacTable OBJECT-TYPE
       	SYNTAX	SEQUENCE OF VturMacTableEntry
       	MAX-ACCESS  not-accessible
       	STATUS  current
       	DESCRIPTION
      	      	""
       	::= { vturMacTableSetup 1 }

	vturMacTableEntry OBJECT-TYPE
       	SYNTAX	VturMacTableEntry
       	MAX-ACCESS	not-accessible
       	STATUS	current
       	DESCRIPTION    	"An entry in vturMacTable."
       	INDEX          	{ dot1dBasePort, staIndex}
       	::= { vturMacTable 1 }


	VturMacTableEntry ::=
       	SEQUENCE {
        vturMacIndex	INTEGER,
        vturMacAddr	MacAddress
        }

	        vturMacIndex  OBJECT-TYPE
       		SYNTAX  INTEGER
       		MAX-ACCESS  read-only
       		STATUS  current
       		DESCRIPTION
			"The index of associated vtur STA. Max = 32, Min = 1"
        		::= { vturMacTableEntry 1 }
        	
	        vturMacAddr  OBJECT-TYPE
       		SYNTAX  MacAddress
       		MAX-ACCESS  read-only
       		STATUS  current
       		DESCRIPTION
			"The address of associated vtur STA "
        		::= { vturMacTableEntry 2 }


-- vturLanSetup
	vturLanSetup     	OBJECT IDENTIFIER ::= { vturSwitchSetup 11 }

	vturLanTable OBJECT-TYPE
       	SYNTAX	SEQUENCE OF VturLanEntry
       	MAX-ACCESS  not-accessible
       	STATUS  current
       	DESCRIPTION
      	      	""
       	::= { vturLanSetup 1 }

	vturLanEntry OBJECT-TYPE
       	SYNTAX	VturLanEntry
       	MAX-ACCESS	not-accessible
       	STATUS	current
       	DESCRIPTION    	"An entry in vturLanTable."
       	INDEX          	{ dot1dBasePort }
       	::= { vturLanTable 1 }

        VturLanEntry ::=
       	SEQUENCE {
       	vturLanIP  IpAddress,
       	vturLanSubnetmask    IpAddress,
       	vturDHCPOption     INTEGER,
       	vturDHCPServerStartIPAddr    IpAddress,
       	vturDHCPServerEndIPAddr     IpAddress,
       	vturDHCPServerSubnetmask    IpAddress,
       	vturDHCPServerIPAddr    IpAddress
        }


        vturLanIP OBJECT-TYPE
        SYNTAX  IpAddress
        MAX-ACCESS  read-write
        STATUS  current
        DESCRIPTION
                      ""
        ::= { vturLanEntry 1 }

        vturLanSubnetmask OBJECT-TYPE
        SYNTAX  IpAddress
        MAX-ACCESS  read-write
        STATUS  current
        DESCRIPTION
                      ""
        ::= { vturLanEntry 2 }

        vturDHCPOption OBJECT-TYPE
        SYNTAX  INTEGER{
			disable_dhcp_server(1),
         	enable_dhcp_server(2),
         	dhcp_server_relay(3)
         	}
        MAX-ACCESS  read-write
        STATUS  current
        DESCRIPTION
                      ""
        ::= { vturLanEntry 3 }

        vturDHCPServerStartIPAddr OBJECT-TYPE
        SYNTAX  IpAddress 
        MAX-ACCESS  read-write
        STATUS  current
        DESCRIPTION
                      ""
        ::= { vturLanEntry 4 }

        vturDHCPServerEndIPAddr OBJECT-TYPE
        SYNTAX  IpAddress 
        MAX-ACCESS  read-write
        STATUS  current
        DESCRIPTION
                      ""
        ::= { vturLanEntry 5 }
        
        vturDHCPServerSubnetmask OBJECT-TYPE
        SYNTAX  IpAddress 
        MAX-ACCESS  read-write
        STATUS  current
        DESCRIPTION
                      ""
        ::= { vturLanEntry 6 }

        vturDHCPServerIPAddr OBJECT-TYPE
        SYNTAX  IpAddress 
        MAX-ACCESS  read-write
        STATUS  current
        DESCRIPTION
                      ""
        ::= { vturLanEntry 7 }        
-----------------------------------------------------------------------------------------------
-- vturCFMSetup
	vturCFMSetup     	OBJECT IDENTIFIER ::= { vturSwitchSetup 12 }

	vturCFMTable OBJECT-TYPE
       	SYNTAX	SEQUENCE OF VturCFMEntry
       	MAX-ACCESS  not-accessible
       	STATUS  current
       	DESCRIPTION
      	      	""
       	::= { vturCFMSetup 1 }

	vturCFMEntry OBJECT-TYPE
       	SYNTAX	VturCFMEntry
       	MAX-ACCESS	not-accessible
       	STATUS	current
       	DESCRIPTION    	"An entry in vturCFMTable."
       	INDEX          	{ dot1dBasePort }
       	::= { vturCFMTable 1 }

        VturCFMEntry ::=
       	SEQUENCE {
       	vturCFMCommit	INTEGER,
       	vturCFMMdName  OCTET STRING,
       	vturCFMMaName    OCTET STRING,
       	vturCFMVid     INTEGER,
       	vturCFMMepId    Dot1agCfmMepId,
       	vturCFMMdLevel     INTEGER,
       	vturCFMAction    INTEGER,
       	vturCFMDestMAC    OCTET STRING,
       	vturCFMLBMCount   INTEGER,
       	vturCFMResultSentLBM     INTEGER,
       	vturCFMResultInorderLBM     INTEGER,
	vturCFMResultOutorderLBM     INTEGER,
	vturMACAddr		OCTET STRING,
       	vturCFMReadStatus	INTEGER	
        }

        vturCFMCommit OBJECT-TYPE
        SYNTAX  INTEGER
        {
		commit(1)
        }
        MAX-ACCESS  read-write
        STATUS  current
        DESCRIPTION
                      "Set 1 to commit CFM operation and read value always return 0"
        ::= { vturCFMEntry 1 }

        vturCFMMdName OBJECT-TYPE
        SYNTAX  OCTET STRING
        MAX-ACCESS  read-write
        STATUS  current
        DESCRIPTION
                      ""
        ::= { vturCFMEntry 2 }

        vturCFMMaName OBJECT-TYPE
        SYNTAX  OCTET STRING
        MAX-ACCESS  read-write
        STATUS  current
        DESCRIPTION
                      ""
        ::= { vturCFMEntry 3 }

        vturCFMVid OBJECT-TYPE
        SYNTAX  INTEGER
        MAX-ACCESS  read-write
        STATUS  current
        DESCRIPTION
                      ""
        ::= { vturCFMEntry 4 }

        vturCFMMepId OBJECT-TYPE
        SYNTAX  Dot1agCfmMepId 
        MAX-ACCESS  read-write
        STATUS  current
        DESCRIPTION
                      ""
        ::= { vturCFMEntry 5 }

        vturCFMMdLevel OBJECT-TYPE
        SYNTAX  INTEGER 
        MAX-ACCESS  read-write
        STATUS  current
        DESCRIPTION
                      ""
        ::= { vturCFMEntry 6 }
        
        vturCFMAction OBJECT-TYPE
        SYNTAX  INTEGER
    	{
	 	save(0),    	
        enable_cfm(1),
        disable_cfm(2),
        send_loopback_message(3),
        send_linktrace_message(4),
         reset_configuration(5)
        }        
        MAX-ACCESS  read-write
        STATUS  current
        DESCRIPTION
                      "Currently only support 0:save ,3:send loopback message and 5:load cpe cfm default"
        ::= { vturCFMEntry 7 }

        vturCFMDestMAC OBJECT-TYPE
        SYNTAX  OCTET STRING 
        MAX-ACCESS  read-write
        STATUS  current
        DESCRIPTION
                      ""
        ::= { vturCFMEntry 8 }    

        vturCFMLBMCount OBJECT-TYPE
        SYNTAX  INTEGER 
        MAX-ACCESS  read-write
        STATUS  current
        DESCRIPTION
                      ""
        ::= { vturCFMEntry 9 }            

        vturCFMResultSentLBM OBJECT-TYPE
        SYNTAX  INTEGER 
        MAX-ACCESS  read-only
        STATUS  current
        DESCRIPTION
                      ""
        ::= { vturCFMEntry 10 }            

        vturCFMResultInorderLBM OBJECT-TYPE
        SYNTAX  INTEGER 
        MAX-ACCESS  read-only
        STATUS  current
        DESCRIPTION
                      ""
        ::= { vturCFMEntry 11 }            

        vturCFMResultOutorderLBM OBJECT-TYPE
        SYNTAX  INTEGER 
        MAX-ACCESS  read-only
        STATUS  current
        DESCRIPTION
                      ""
        ::= { vturCFMEntry 12 }  
        
        vturMACAddr OBJECT-TYPE
        SYNTAX  OCTET STRING 
        MAX-ACCESS  read-only
        STATUS  current
        DESCRIPTION
                      "CPE MAC address"
        ::= { vturCFMEntry 13 }             
        
        vturCFMReadStatus OBJECT-TYPE
        SYNTAX  INTEGER
        {
       	commit(1)
        }
        MAX-ACCESS  read-write
        STATUS  current
        DESCRIPTION
                      "Set 1 to commit CFM Read operation and read value always return 0"
        ::= { vturCFMEntry 14 }               
------------------------------------------------------------------------------------------------

-- vturInfo
		vturInfo     	OBJECT IDENTIFIER ::= { ves1724-56fanless 37 }

-- vturInfoTable
    vturInfoTable OBJECT-TYPE
       	SYNTAX	SEQUENCE OF VturInfoEntry
       	MAX-ACCESS  not-accessible
       	STATUS  current
       	DESCRIPTION
      	      	""
       	::= { vturInfo 1 }

	vturInfoEntry OBJECT-TYPE
       	SYNTAX	VturInfoEntry
       	MAX-ACCESS	not-accessible
       	STATUS	current
       	DESCRIPTION    	"An entry in vturInfoTable."
       	INDEX          	{ dot1dBasePort }
       	::= { vturInfoTable 1 }

    VturInfoEntry ::=
       	SEQUENCE {
        vturName	DisplayString,
        vturSysVersion	DisplayString,
        vturModemCodeVersion	DisplayString
        }

    vturName OBJECT-TYPE
        SYNTAX  DisplayString
        MAX-ACCESS  read-only
        STATUS  current
        DESCRIPTION
                   	"Display remote device name"
       	::= { vturInfoEntry 1 }

    vturSysVersion OBJECT-TYPE
        SYNTAX  DisplayString
        MAX-ACCESS  read-only
        STATUS  current
        DESCRIPTION
                    	"Display remote device system version info"
        ::= { vturInfoEntry 2 }

    vturModemCodeVersion OBJECT-TYPE
        SYNTAX  DisplayString
        MAX-ACCESS  read-only
        STATUS  current
        DESCRIPTION
                    	"Display remote device VDSL modem code version info"
        ::= { vturInfoEntry 3 }    

  --  protocol-based VLAN
	protoBasedVlanSetup     	OBJECT IDENTIFIER ::= { ves1724-56fanless 38 }
	
	    protoBasedVlanTable  OBJECT-TYPE
	    SYNTAX	SEQUENCE OF ProtoBasedVlanEntry 
	    MAX-ACCESS  not-accessible
	    STATUS  current
	    DESCRIPTION
	             	""
	    ::= { protoBasedVlanSetup 1 }	

	protoBasedVlanEntry  OBJECT-TYPE
        SYNTAX	ProtoBasedVlanEntry 
        MAX-ACCESS	not-accessible
        STATUS	current
        DESCRIPTION    	"An entry in protoBasedVlanTable."
        INDEX          	{ protoBasedVlanPort, protoBasedVlanPacketType, protoBasedVlanEtherType }
        ::= { protoBasedVlanTable 1 }

        ProtoBasedVlanEntry ::=
           SEQUENCE {
            protoBasedVlanPort			INTEGER,
        	protoBasedVlanPacketType	INTEGER,
        	protoBasedVlanEtherType		INTEGER,
        	protoBasedVlanName			DisplayString,
        	protoBasedVlanVid			INTEGER,
        	protoBasedVlanPriority		INTEGER,
        	protoBasedVlanState			RowStatus
           }

        protoBasedVlanPort OBJECT-TYPE
        SYNTAX  INTEGER
        MAX-ACCESS  read-only
        STATUS  current
        DESCRIPTION
                      	""
        ::= { protoBasedVlanEntry 1 }

        protoBasedVlanPacketType OBJECT-TYPE
        SYNTAX  INTEGER {
        	etherII(1),
        	snap(2),
        	llc(3)
        }
        MAX-ACCESS  read-only
        STATUS  current
        DESCRIPTION
                      	""
        ::= { protoBasedVlanEntry 2 }

        protoBasedVlanEtherType OBJECT-TYPE
        SYNTAX  INTEGER
        MAX-ACCESS  read-only
        STATUS  current
        DESCRIPTION
                      	""
        ::= { protoBasedVlanEntry 3 }

        protoBasedVlanName OBJECT-TYPE
        SYNTAX  DisplayString (SIZE (0..32))
        MAX-ACCESS  read-write
        STATUS  current
        DESCRIPTION
                      	""
        ::= { protoBasedVlanEntry 4 }

        protoBasedVlanVid OBJECT-TYPE
        SYNTAX  INTEGER (1..4094)
        MAX-ACCESS  read-write
        STATUS  current
        DESCRIPTION
                      	""
        ::= { protoBasedVlanEntry 5 }

        protoBasedVlanPriority OBJECT-TYPE
        SYNTAX  INTEGER (0..7)
        MAX-ACCESS  read-write
        STATUS  current
        DESCRIPTION
                      	""
        ::= { protoBasedVlanEntry 6 }

        protoBasedVlanState OBJECT-TYPE
        SYNTAX  RowStatus
        MAX-ACCESS  read-create
        STATUS  current
        DESCRIPTION
                      	""
        ::= { protoBasedVlanEntry 7 } 
                                             
      
--  classifierSetup
	classifierSetup     	OBJECT IDENTIFIER ::= { ves1724-56fanless 39 }

        classifierRuleTable	OBJECT-TYPE
        SYNTAX	SEQUENCE OF ClassifierRuleEntry
        MAX-ACCESS  not-accessible
        STATUS  current
        DESCRIPTION
                 	""
        ::= { classifierSetup 1 }

		classifierRuleEntry OBJECT-TYPE
        SYNTAX	ClassifierRuleEntry
        MAX-ACCESS	not-accessible
        STATUS	current
        DESCRIPTION    	"An entry in classifierRuleTable."
        INDEX          	{classifierName }
        ::= { classifierRuleTable 1 }

      	ClassifierRuleEntry ::=
		SEQUENCE {
        	classifierName		DisplayString,      
        	classifierEnable	INTEGER, 
        	classifierPacketFormat INTEGER,
        	classifierVlanId 	INTEGER,
        	classifier8021pPriority INTEGER,
        	classifierEtherType INTEGER,
        	classifierSrcMAC 	MacAddress,
        	classifierIncomingPort INTEGER,
        	classifierDstMAC 	MacAddress,
        	classifierDSCP		INTEGER,
        	classifierIpProtocol INTEGER,
        	classifierEstablishOnly INTEGER,
        	classifierSrcIp	    IpAddress,
        	classifierSrcIpMask	INTEGER,
        	classifierSrcSocket INTEGER,
        	classifierDstIp		IpAddress,  
        	classifierDstIpMask	INTEGER,  
        	classifierDstSocket INTEGER,
        	classifierRowstatus RowStatus,
        	classifierSrcIpv6	    Ipv6Address,
        	classifierSrcIpv6Mask	INTEGER, 
        	classifierDstIpv6		Ipv6Address,
        	classifierDstIpv6Mask	INTEGER,
       	   	classifierIncomingPortList PortList       	
           }                                             
                        
        classifierName OBJECT-TYPE
        SYNTAX  DisplayString
        MAX-ACCESS  read-only
        STATUS  current
        DESCRIPTION
                      	"Name of classifier rule."
        ::= { classifierRuleEntry 1 }                        
                        
        classifierEnable OBJECT-TYPE
        SYNTAX  EnabledStatus
        MAX-ACCESS  read-write
        STATUS  current
        DESCRIPTION
        	"Classifier rule enabled/disabled."
        ::= { classifierRuleEntry 2 }

        classifierPacketFormat OBJECT-TYPE
        SYNTAX  INTEGER   
        {
      		all(1),
 		ethernetII_untagged(2),
		ethernetII_tagged(3),
     		ethernet802_3_untagged(4),
      		ethernet802_3_tagged(5)
        }
        MAX-ACCESS  read-write
        STATUS  current
        DESCRIPTION
        	"Packet format for classifier rule. All(1), 802.3 untagged(2), 802.3 tagged(3), EthernetII untagged(4), EthernetII tagged(5)."
        ::= { classifierRuleEntry 3 }
                                             
   		classifierVlanId OBJECT-TYPE
        SYNTAX  INTEGER
        MAX-ACCESS  read-write
        STATUS  current
        DESCRIPTION
                      	"Vlan id for classifer rule, 1~4094."
        ::= { classifierRuleEntry 4 }

   		classifier8021pPriority OBJECT-TYPE
        SYNTAX  INTEGER
        MAX-ACCESS  read-write
        STATUS  current
        DESCRIPTION
                      	"802.1p priority for classifier rule, 0~7."
        ::= { classifierRuleEntry 5 }      
        
   		classifierEtherType OBJECT-TYPE
        SYNTAX  INTEGER 
        MAX-ACCESS  read-write
        STATUS  current
        DESCRIPTION
                      	"Ether type for classifier rule, in decimal expression."
        ::= { classifierRuleEntry 6 }
         
        classifierSrcMAC OBJECT-TYPE
        SYNTAX  MacAddress
        MAX-ACCESS  read-write
        STATUS  current
        DESCRIPTION
                      	"Source mac address for classifier rule"
        ::= { classifierRuleEntry 7 }
     	
        classifierIncomingPort OBJECT-TYPE
        SYNTAX  INTEGER
        MAX-ACCESS  read-write
        STATUS  current
        DESCRIPTION
                      	"Incoming Port for classifier rule"                      	
        ::= { classifierRuleEntry 8 }

        classifierDstMAC OBJECT-TYPE
        SYNTAX  MacAddress
        MAX-ACCESS  read-write
        STATUS  current
        DESCRIPTION
                      	"Destination mac address for classifier rule"
        ::= { classifierRuleEntry 9 }
         
        classifierDSCP OBJECT-TYPE
        SYNTAX  INTEGER
        MAX-ACCESS  read-write
        STATUS  current
        DESCRIPTION
                      	"DSCP for classifier rule"                      	
        ::= { classifierRuleEntry 10 }                              
        
        classifierIpProtocol OBJECT-TYPE
        SYNTAX  INTEGER
        MAX-ACCESS  read-write
        STATUS  current
        DESCRIPTION
                      	"IP Protocol for classifier rule"                      	
        ::= { classifierRuleEntry 11 }       
           
        classifierEstablishOnly OBJECT-TYPE
        SYNTAX  EnabledStatus
        MAX-ACCESS  read-write
        STATUS  current
        DESCRIPTION
                      	"IP Protocol for EstablishOnly for classifier rule"                      	
        ::= { classifierRuleEntry 12 }  
           
    	classifierSrcIp OBJECT-TYPE
        SYNTAX  IpAddress
        MAX-ACCESS  read-write
        STATUS  current
        DESCRIPTION
                      	"Source IP address for classifier rule"
        ::= { classifierRuleEntry 13 }
        
        classifierSrcIpMask OBJECT-TYPE
        SYNTAX  INTEGER
        MAX-ACCESS  read-write
        STATUS  current
        DESCRIPTION
                      	"Source IP Mask for classifier rule"
        ::= { classifierRuleEntry 14 }
 
        classifierSrcSocket OBJECT-TYPE
        SYNTAX  INTEGER
        MAX-ACCESS  read-write
        STATUS  current
        DESCRIPTION
                      	"Source Socket Number for classifier rule"                      	
        ::= { classifierRuleEntry 15 }
        
        classifierDstIp OBJECT-TYPE
        SYNTAX  IpAddress
        MAX-ACCESS  read-write
        STATUS  current
        DESCRIPTION
                      	"Destination IP address for classifier rule"
        ::= { classifierRuleEntry 16 }
        
        classifierDstIpMask OBJECT-TYPE
        SYNTAX  INTEGER
        MAX-ACCESS  read-write
        STATUS  current
        DESCRIPTION
                      	"Destination IP Mask for classifier rule"
        ::= { classifierRuleEntry 17 }
 
        classifierDstSocket OBJECT-TYPE
        SYNTAX  INTEGER
        MAX-ACCESS  read-write
        STATUS  current
        DESCRIPTION
                      	"Destination Socket Number for classifier rule"                      	
        ::= { classifierRuleEntry 18 }
        
        classifierRowstatus OBJECT-TYPE
        SYNTAX  RowStatus
        MAX-ACCESS  read-create
        STATUS  current
        DESCRIPTION
                      	"Row Status for classifier rule"
        ::= { classifierRuleEntry 19 } 
      
        classifierSrcIpv6 OBJECT-TYPE
        SYNTAX  Ipv6Address
        MAX-ACCESS  read-write
        STATUS  current
        DESCRIPTION
                      	"Source IPv6 address for classifier rule"
        ::= { classifierRuleEntry 20 }  
        
        classifierSrcIpv6Mask OBJECT-TYPE
        SYNTAX  INTEGER
        MAX-ACCESS  read-write
        STATUS  current
        DESCRIPTION
                      	"Source IPv6 Mask for classifier rule"
        ::= { classifierRuleEntry 21 }
        
        classifierDstIpv6 OBJECT-TYPE
        SYNTAX  Ipv6Address
        MAX-ACCESS  read-write
        STATUS  current
        DESCRIPTION
                      	"Destination IPv6 address for classifier rule"
        ::= { classifierRuleEntry 22 }  
        
        classifierDstIpv6Mask OBJECT-TYPE
        SYNTAX  INTEGER
        MAX-ACCESS  read-write
        STATUS  current
        DESCRIPTION
                      	"Destination IPv6 Mask for classifier rule"
        ::= { classifierRuleEntry 23 }
      
	classifierIncomingPortList OBJECT-TYPE
        SYNTAX  PortList
        MAX-ACCESS  read-only
        STATUS  current
        DESCRIPTION
                      	"Incoming PortList for classifier rule"                      	
        ::= { classifierRuleEntry 24 }
        
      
      classifierRuleSet OBJECT-TYPE
        SYNTAX  DisplayString
        MAX-ACCESS  read-write
        STATUS  current
        DESCRIPTION
                      	"classifier Rule Set."
        ::= { classifierSetup 2 }

--  policySetup
	policySetup     	OBJECT IDENTIFIER ::= { ves1724-56fanless 40 }

        policyTable	OBJECT-TYPE
        SYNTAX	SEQUENCE OF PolicyEntry
        MAX-ACCESS  not-accessible
        STATUS  current
        DESCRIPTION
                 	""
        ::= { policySetup 1 }  
        
 		policyEntry OBJECT-TYPE
        SYNTAX	PolicyEntry
        MAX-ACCESS	not-accessible
        STATUS	current
        DESCRIPTION    	"An entry in policyTable."
        INDEX          	{policyName }
        ::= { policyTable 1 }
       
      	PolicyEntry ::=
		SEQUENCE {
        	policyName			DisplayString,      
        	policyEnable		INTEGER,  
        	policyClassifier  	DisplayString, 
        	policyVlanId		INTEGER,
        	policyEgressPort 	INTEGER,
        	policyOutPktFormat  INTEGER,
        	policy8021pPriority INTEGER,
        	policyDSCP          INTEGER,
        	policyTOS           INTEGER,
        	policyBandwidth     INTEGER,
        	policyOutOfProfileDSCP   INTEGER,
        	policyForwardingAction   INTEGER,
        	policyPriorityAction     INTEGER,
        	policyDiffServAction 	 INTEGER,
        	policyOutgoingAction	 BITS,
        	policyMeteringEnable     INTEGER,
            policyOutOfProfileAction BITS,
            policyRowstatus 		 RowStatus,
            policyEgressPortList 		 PortList                        
        }  
 
        policyName OBJECT-TYPE
        SYNTAX  DisplayString
        MAX-ACCESS  read-only
        STATUS  current
        DESCRIPTION
                      	"Name of policy rule."
        ::= { policyEntry 1 }   
         
        policyEnable OBJECT-TYPE
        SYNTAX  EnabledStatus
        MAX-ACCESS  read-write
        STATUS  current
        DESCRIPTION
        	"Policy rule enabled/disabled."
        ::= { policyEntry 2 }  
           
        policyClassifier OBJECT-TYPE
        SYNTAX  DisplayString
        MAX-ACCESS  read-only
        STATUS  current
        DESCRIPTION
                      	"Classifier of policy rule."
        ::= { policyEntry 3 }      
                                           
        policyVlanId OBJECT-TYPE
        SYNTAX  INTEGER
        MAX-ACCESS  read-write
        STATUS  current
        DESCRIPTION
                      	"Vlan id for policy rule, 1~4094."
        ::= { policyEntry 4 } 
        
        policyEgressPort OBJECT-TYPE
        SYNTAX  INTEGER
        MAX-ACCESS  read-write
        STATUS  current
        DESCRIPTION
                      	"Egress Port for policy rule"
        ::= { policyEntry 5 }  
         
        policyOutPktFormat OBJECT-TYPE
        SYNTAX  INTEGER
        {   
        	tag(1),
        	untag(2)
        }
        MAX-ACCESS  read-write
        STATUS  current
        DESCRIPTION
                      	"Outgoing packet format for Egress port for policy rule"
        ::= { policyEntry 6 } 
        
        policy8021pPriority OBJECT-TYPE
        SYNTAX  INTEGER
        MAX-ACCESS  read-write
        STATUS  current
        DESCRIPTION
                      	"802.1p priority for policy rule, 0~7."
        ::= { policyEntry 7 }    
        
        policyDSCP OBJECT-TYPE
        SYNTAX  INTEGER
        MAX-ACCESS  read-write
        STATUS  current
        DESCRIPTION
                      	"DSCP for policy rule."
        ::= { policyEntry 8 }   
        
        policyTOS OBJECT-TYPE
        SYNTAX  INTEGER
        MAX-ACCESS  read-write
        STATUS  current
        DESCRIPTION
                      	"TOS for policy rule, 0~7"
        ::= { policyEntry 9 }  
        
        policyBandwidth OBJECT-TYPE
        SYNTAX  INTEGER
        MAX-ACCESS  read-write
        STATUS  current
        DESCRIPTION
                      	"Bandwidth for policy rule"
        ::= { policyEntry 10 }  
          
        policyOutOfProfileDSCP OBJECT-TYPE
        SYNTAX  INTEGER
        MAX-ACCESS  read-write
        STATUS  current
        DESCRIPTION
                      	"Out Of Profile DSCP for policy rule."
        ::= { policyEntry 11 } 
        
        policyForwardingAction OBJECT-TYPE
        SYNTAX  INTEGER
        {   
        	no_change(1),
        	discard_the_packet(2),
        	do_not_drop_the_matching_frame_previously_marked_for_dopping(3)
        }
        MAX-ACCESS  read-write
        STATUS  current
        DESCRIPTION
                      	"Forwarding Action for policy rule"
        ::= { policyEntry 12 } 
   
        policyPriorityAction OBJECT-TYPE
        SYNTAX  INTEGER
        {   
        	no_change(1),
        	set_the_packets_802_1_priority(2),
        	send_the_packet_to_priority_queue(3),
        	replace_the_802_1_priority_field_with_the_IP_TOS_value(4) 
        }
        MAX-ACCESS  read-write
        STATUS  current
        DESCRIPTION
                      	"Priority Action for policy rule"
        ::= { policyEntry 13}    

        policyDiffServAction OBJECT-TYPE
        SYNTAX  INTEGER
        {   
        	no_change(1),
        	set_the_packets_TOS_field(2),
        	replace_the_IP_TOS_field_with_the_802_1_priority_value(3),
        	set_the_Diffserv_Codepoint_field_in_the_frame(4) 
        }
        MAX-ACCESS  read-write
        STATUS  current
        DESCRIPTION
                      	"DiffServ Action for policy rule"
        ::= { policyEntry 14}     
        
        policyOutgoingAction OBJECT-TYPE
		SYNTAX	BITS {
			send_the_packet_to_the_mirror_port(1),
			send_the_packet_to_the_egress_port(2),
			send_the_matching_frames_to_the_egress_port(3),
			set_the_packets_VLAN_ID(4) 
		}
		MAX-ACCESS  read-create
		STATUS      current
		DESCRIPTION
	        "Outgoing Action for policy rule"
		::= { policyEntry 15 }

        policyMeteringEnable OBJECT-TYPE
        SYNTAX  INTEGER
        MAX-ACCESS  read-write
        STATUS  current
        DESCRIPTION
        	"Metering for Policy rule enabled/disabled."
        ::= { policyEntry 16 }  
        
        policyOutOfProfileAction OBJECT-TYPE
		SYNTAX	BITS {
			drop_the_packet(1),
			change_the_DSCP_value(2),
			set_Out_Drop_Precedence(3),
			do_not_drop_the_matching_frame_previously_marked_for_dropping(4)
		}
		MAX-ACCESS  read-create
		STATUS      current
		DESCRIPTION
	        "Out Of Profile Action for policy rule"
		::= { policyEntry 17 }
 
        policyRowstatus OBJECT-TYPE
        SYNTAX  RowStatus
        MAX-ACCESS  read-create
        STATUS  current
        DESCRIPTION
                      	"Row Status for policy rule"
        ::= { policyEntry 18 }      

	policyEgressPortList OBJECT-TYPE
        SYNTAX  PortList
        MAX-ACCESS  read-only
        STATUS  current
        DESCRIPTION
            "Egress PortList for policy rule"
        ::= { policyEntry 19 }  

        policyRuleSet OBJECT-TYPE
        SYNTAX  DisplayString
        MAX-ACCESS  read-write
        STATUS  current
        DESCRIPTION
                      	"policy Rule Set."
        ::= { policySetup 2 }


--  switchCounterStatus
	switchCounterStatus     	OBJECT IDENTIFIER ::= { ves1724-56fanless 42 }

vlanCounterTable OBJECT-TYPE
        SYNTAX SEQUENCE OF VlanCounterEntry
        MAX-ACCESS  not-accessible
        STATUS  current
        DESCRIPTION
                  ""
        ::= { switchCounterStatus 1 }
 
 vlanCounterEntry OBJECT-TYPE
        SYNTAX VlanCounterEntry
        MAX-ACCESS not-accessible
        STATUS current
        DESCRIPTION     "An entry in vlanCounterTable."
        INDEX           { ifIndex, dot1qVlanIndex }
        ::= { vlanCounterTable 1 }
 
        VlanCounterEntry ::=
             SEQUENCE {
                 vlanCounterTxPkts  				Counter64,
                 vlanCounterRxPkts  				Counter64,
                 vlanCounterTxMulticastPkts 		Counter64,
                 vlanCounterRxMulticastPkts 		Counter64,
                 vlanCounterTxBroadcastPkts 		Counter64,
                 vlanCounterRxBroadcastPkts 		Counter64,
                 vlanCounterTxTotalBytes            Counter64,
                 vlanCounterRxTotalBytes            Counter64,
                 vlanCounterTxPktsRate  			Counter64,
                 vlanCounterRxPktsRate  			Counter64,
                 vlanCounterTxPkts64Octets 			Counter64,
                 vlanCounterRxPkts64Octets 			Counter64,
                 vlanCounterTxPkts65to127Octets 	Counter64,
                 vlanCounterRxPkts65to127Octets 	Counter64,
                 vlanCounterTxPkts128to255Octets 	Counter64,
                 vlanCounterRxPkts128to255Octets 	Counter64,
                 vlanCounterTxPkts256to511Octets  	Counter64,
                 vlanCounterRxPkts256to511Octets  	Counter64,
                 vlanCounterTxPkts512to1023Octets  	Counter64,
                 vlanCounterRxPkts512to1023Octets  	Counter64,
                 vlanCounterTxPkts1024to1518Octets  Counter64,
                 vlanCounterRxPkts1024to1518Octets  Counter64,
                 vlanCounterTxPktsGiant 			Counter64,
                 vlanCounterRxPktsGiant 			Counter64       
           }
        
        vlanCounterTxPkts  OBJECT-TYPE
        SYNTAX  Counter64
        UNITS	"Packets"
        MAX-ACCESS  read-only
        STATUS  current
        DESCRIPTION
        "The total number of packets (including bad packets,
 		 broadcast packets, and multicast packets) received."
        ::= { vlanCounterEntry 1 }
 
        vlanCounterRxPkts  OBJECT-TYPE
        SYNTAX  Counter64
        UNITS	"Packets"
        MAX-ACCESS  read-only
        STATUS  current
        DESCRIPTION
        "The total number of packets (including bad packets,
 		 broadcast packets, and multicast packets) received."
        ::= { vlanCounterEntry 2 }

        vlanCounterTxMulticastPkts  OBJECT-TYPE
        SYNTAX  Counter64
        UNITS	"Packets"
        MAX-ACCESS  read-only
        STATUS  current
        DESCRIPTION
        "The total number of good packets received that were
 		 directed to a multicast address. Note that this number
 		 does not include packets directed to the broadcast address."
        ::= { vlanCounterEntry 3 }
        
        vlanCounterRxMulticastPkts  OBJECT-TYPE
        SYNTAX  Counter64
        UNITS	"Packets"
        MAX-ACCESS  read-only
        STATUS  current
        DESCRIPTION
        "The total number of good packets received that were
 		 directed to a multicast address.  Note that this number
 		 does not include packets directed to the broadcast address."
        ::= { vlanCounterEntry 4 }
 
        vlanCounterTxBroadcastPkts  OBJECT-TYPE
        SYNTAX  Counter64
        UNITS	"Packets"
        MAX-ACCESS  read-only
        STATUS  current
        DESCRIPTION
        "The total number of good packets received that were
 		 directed to the broadcast address.  Note that this
 		 does not include multicast packets."
        ::= { vlanCounterEntry 5 }
                
        vlanCounterRxBroadcastPkts  OBJECT-TYPE
        SYNTAX  Counter64
        UNITS	"Packets"
        MAX-ACCESS  read-only
        STATUS  current
        DESCRIPTION
        "The total number of good packets received that were
 		 directed to the broadcast address.  Note that this
 		 does not include multicast packets."
        ::= { vlanCounterEntry 6 }
        
        vlanCounterTxTotalBytes  OBJECT-TYPE
        SYNTAX  Counter64
        UNITS "Bytes"
        MAX-ACCESS  read-only
        STATUS  current    
        DESCRIPTION
        "The total number of packets size received."
        ::= { vlanCounterEntry 7 }
 
        vlanCounterRxTotalBytes  OBJECT-TYPE
        SYNTAX  Counter64
        UNITS "Bytes"
        MAX-ACCESS  read-only
        STATUS  current
        DESCRIPTION
        "The total number of packets size received."
        ::= { vlanCounterEntry 8 }
        
        vlanCounterTxPktsRate  OBJECT-TYPE
        SYNTAX  Counter64
        UNITS "Bs/s"
        MAX-ACCESS  read-only
        STATUS  current    
        DESCRIPTION
        "The number of packets seen from the source host to 
         the destination host during this sampling interval, 
 		 counted using the rules for counting the Packets object."
        ::= { vlanCounterEntry 9 }
 
        vlanCounterRxPktsRate  OBJECT-TYPE
        SYNTAX  Counter64
        UNITS "Bs/s"
        MAX-ACCESS  read-only
        STATUS  current
        DESCRIPTION
        "The number of packets seen from the source host to 
         the destination host during this sampling interval, 
 		 counted using the rules for counting the Packets object."
        ::= { vlanCounterEntry 10 }
                
        vlanCounterTxPkts64Octets  OBJECT-TYPE
        SYNTAX  Counter64
        UNITS	"Packets"
        MAX-ACCESS  read-only
        STATUS  current
        DESCRIPTION
        "The total number of packets received 
         that were 64 octets in length."
        ::= { vlanCounterEntry 11 }
        
        vlanCounterRxPkts64Octets  OBJECT-TYPE
        SYNTAX  Counter64
        UNITS	"Packets"
        MAX-ACCESS  read-only
        STATUS  current
        DESCRIPTION
        "The total number of packets received 
         that were 64 octets in length."
        ::= { vlanCounterEntry 12 }
 
        vlanCounterTxPkts65to127Octets  OBJECT-TYPE
        SYNTAX  Counter64
        UNITS	"Packets"
        MAX-ACCESS  read-only
        STATUS  current
        DESCRIPTION
        "The total number of packets received that were 
         between 65 and 127 octets in length."
        ::= { vlanCounterEntry 13 }
                
        vlanCounterRxPkts65to127Octets  OBJECT-TYPE
        SYNTAX  Counter64
        UNITS	"Packets"
        MAX-ACCESS  read-only
        STATUS  current
        DESCRIPTION
        "The total number of packets received that were 
         between 65 and 127 octets in length."
        ::= { vlanCounterEntry 14 }
        
        vlanCounterTxPkts128to255Octets  OBJECT-TYPE
        SYNTAX  Counter64
        UNITS	"Packets"
        MAX-ACCESS  read-only
        STATUS  current
        DESCRIPTION
        "The total number of packets received that were 
         between 128 and 255 octets in length."
        ::= { vlanCounterEntry 15 }
        
        vlanCounterRxPkts128to255Octets  OBJECT-TYPE
        SYNTAX  Counter64
        UNITS	"Packets"
        MAX-ACCESS  read-only
        STATUS  current
        DESCRIPTION
        "The total number of packets received that were 
         between 128 and 255 octets in length."
        ::= { vlanCounterEntry 16 }
 
        vlanCounterTxPkts256to511Octets  OBJECT-TYPE
        SYNTAX  Counter64
        UNITS	"Packets"
        MAX-ACCESS  read-only
        STATUS  current
        DESCRIPTION
        "The total number of packets received that were 
         between 256 and 511 octets in length."
        ::= { vlanCounterEntry 17 }
                
        vlanCounterRxPkts256to511Octets  OBJECT-TYPE
        SYNTAX  Counter64
        UNITS	"Packets"
        MAX-ACCESS  read-only
        STATUS  current
        DESCRIPTION
        "The total number of packets received that were 
         between 256 and 511 octets in length."
        ::= { vlanCounterEntry 18 }
        
        vlanCounterTxPkts512to1023Octets  OBJECT-TYPE
        SYNTAX  Counter64
        UNITS	"Packets"
        MAX-ACCESS  read-only
        STATUS  current
        DESCRIPTION
        "The total number of packets received that were 
         between 512 and 1023 octets in length."
        ::= { vlanCounterEntry 19 }
        
        vlanCounterRxPkts512to1023Octets  OBJECT-TYPE
        SYNTAX  Counter64
        UNITS	"Packets"
        MAX-ACCESS  read-only
        STATUS  current
        DESCRIPTION
        "The total number of packets received that were 
         between 512 and 1023 octets in length."
        ::= { vlanCounterEntry 20 }
 
        vlanCounterTxPkts1024to1518Octets  OBJECT-TYPE
        SYNTAX  Counter64
        UNITS	"Packets"
        MAX-ACCESS  read-only
        STATUS  current
        DESCRIPTION
        "The total number of packets received that were 
         between 1024 and 1518 octets in length."
        ::= { vlanCounterEntry 21 }
                
        vlanCounterRxPkts1024to1518Octets  OBJECT-TYPE
        SYNTAX  Counter64
        UNITS	"Packets"
        MAX-ACCESS  read-only
        STATUS  current
        DESCRIPTION
        "The total number of packets received that were 
         between 1024 and 1518 octets in length."
        ::= { vlanCounterEntry 22 }
        
        vlanCounterTxPktsGiant  OBJECT-TYPE
        SYNTAX  Counter64
        UNITS	"Packets"
        MAX-ACCESS  read-only
        STATUS  current
        DESCRIPTION
        "The total number of packets received that were 
         greater than 1518 octets in length."
        ::= { vlanCounterEntry 23 }
                
        vlanCounterRxPktsGiant  OBJECT-TYPE
        SYNTAX  Counter64
        UNITS	"Packets"
        MAX-ACCESS  read-only
        STATUS  current
        DESCRIPTION
        "The total number of packets received that were 
         greater than 1518 octets in length."
        ::= { vlanCounterEntry 24 }



-- switchCounterTable

        switchCounterTable OBJECT-TYPE
        SYNTAX	SEQUENCE OF SwitchCounterEntry
        MAX-ACCESS  not-accessible
        STATUS  current
        DESCRIPTION
                 	""
        ::= { switchCounterStatus 2 }

	switchCounterEntry OBJECT-TYPE
        SYNTAX	SwitchCounterEntry
        MAX-ACCESS	not-accessible
        STATUS	current
        DESCRIPTION    	"An entry in switchCounterTable."
        INDEX          	{ dot1dBasePort }
        ::= { switchCounterTable 1 }

        SwitchCounterEntry ::=
           SEQUENCE {
        	switchUnknownUnicastCounter	Counter32,
        	switchtxratelimitdropcounter	Counter32,
        	switchrxratelimitdropcounter	Counter64,
        	switchrxmeterdropcounter	Counter64
           }

        switchUnknownUnicastCounter OBJECT-TYPE
        SYNTAX  Counter32
        MAX-ACCESS  read-only
        STATUS  current
        DESCRIPTION
        "Unknown unicast counter for the port."
        ::= { switchCounterEntry 1 }

        switchtxratelimitdropcounter OBJECT-TYPE
        SYNTAX  Counter32
        MAX-ACCESS  read-only
        STATUS  current
        DESCRIPTION
        "Rx Ratelimit drop counter."
        ::= { switchCounterEntry 2 }

        switchrxratelimitdropcounter OBJECT-TYPE
        SYNTAX  Counter64
        MAX-ACCESS  read-only
        STATUS  current
        DESCRIPTION
        "Tx Ratelimit drop counter."
        ::= { switchCounterEntry 3 }

        switchrxmeterdropcounter OBJECT-TYPE
        SYNTAX  Counter64
        MAX-ACCESS  read-only
        STATUS  current
        DESCRIPTION
        "Rx Metering drop counter."
        ::= { switchCounterEntry 4 }


-- vlanCounterResetTable

	vlanCounterResetTable OBJECT-TYPE
        SYNTAX SEQUENCE OF VlanCounterResetEntry
        MAX-ACCESS  not-accessible
        STATUS  current
        DESCRIPTION
                  ""
        ::= { switchCounterStatus 3 }
        
       vlanCounterResetEntry OBJECT-TYPE
        SYNTAX VlanCounterResetEntry
        MAX-ACCESS not-accessible
        STATUS current
        DESCRIPTION     "An entry in vlanCounterTable."
        INDEX           { dot1qVlanIndex }
        ::= { vlanCounterResetTable 1 }
 
        VlanCounterResetEntry ::=
             SEQUENCE {
                 vlanCounterReset  INTEGER
           }
           
        vlanCounterReset OBJECT-TYPE
        SYNTAX  INTEGER {
        	enable(1),
        	disable(2)
        }
        MAX-ACCESS  read-write
        STATUS  current
        DESCRIPTION
               "Clear VLAN counters."
        ::= { vlanCounterResetEntry 1 }


-- vlanCounterSwitchSetup

	vlanCounterSwitchSetup     	OBJECT IDENTIFIER ::= { switchCounterStatus 4 }

        vlanCounterSwitch OBJECT-TYPE
        SYNTAX  INTEGER {
        	enable(1),
        	disable(2)
        }
        MAX-ACCESS  read-write
        STATUS  current
        DESCRIPTION
               "Switch VLAN counters on/off."
        ::= { vlanCounterSwitchSetup 1 }

        vlanCounterVlan OBJECT-TYPE
        SYNTAX  INTEGER
        MAX-ACCESS  read-write
        STATUS  current
        DESCRIPTION
               "VLAN counter per vlan."
        ::= { vlanCounterSwitchSetup 2 }
           
        vlanCounterPort OBJECT-TYPE
        SYNTAX  INTEGER
        MAX-ACCESS  read-write
        STATUS  current
        DESCRIPTION
               "VLAN counters per port."
        ::= { vlanCounterSwitchSetup 3 }
           
        vlanCounterDirection OBJECT-TYPE
        SYNTAX  INTEGER {
        	tx(1),
        	rx(2)
        }
        MAX-ACCESS  read-write
        STATUS  current
        DESCRIPTION
               "VLAN counters per direction."
        ::= { vlanCounterSwitchSetup 4 }

--  rateLimitProfilePortSetup
	rateLimitProfilePortSetup     	OBJECT IDENTIFIER ::= { ves1724-56fanless 43 }

        rateLimitProfilePortTable	OBJECT-TYPE
        SYNTAX	SEQUENCE OF RateLimitProfilePortEntry
        MAX-ACCESS  not-accessible
        STATUS  current
        DESCRIPTION
                 	""
        ::= { rateLimitProfilePortSetup 1 }

	rateLimitProfilePortEntry OBJECT-TYPE 
        SYNTAX	RateLimitProfilePortEntry
        MAX-ACCESS	not-accessible
        STATUS	current
        DESCRIPTION    	"An entry in rateLimitProfilePortTable."
        INDEX          	{ dot1dBasePort }
        ::= { rateLimitProfilePortTable 1 }

        RateLimitProfilePortEntry ::=
	SEQUENCE {
        	rateLimitPortProfile	DisplayString
        }

        rateLimitPortProfile OBJECT-TYPE
        SYNTAX  DisplayString
        MAX-ACCESS  read-write
        STATUS  current
        DESCRIPTION
                      	""
        ::= { rateLimitProfilePortEntry 1 }

  perQueueProfilePortTable	OBJECT-TYPE
        SYNTAX	SEQUENCE OF PerQueueProfilePortEntry
        MAX-ACCESS  not-accessible
        STATUS  current
        DESCRIPTION
                 	""
        ::= { rateLimitProfilePortSetup 2 }
        
	perQueueProfilePortEntry OBJECT-TYPE
        SYNTAX	PerQueueProfilePortEntry
        MAX-ACCESS	not-accessible
        STATUS	current
        DESCRIPTION    	"An entry in perQueueProfilePortTable."
        INDEX          	{ dot1dBasePort }
        ::= { perQueueProfilePortTable 1 }

        PerQueueProfilePortEntry ::=
	SEQUENCE {
        	perQueuePortProfile	DisplayString
        }

        perQueuePortProfile OBJECT-TYPE
        SYNTAX  DisplayString
        MAX-ACCESS  read-write
        STATUS  current
        DESCRIPTION
                      	""
        ::= { perQueueProfilePortEntry 1 }        

----------------------------------------------------
--  rateLimitProfileSetup
	rateLimitProfileSetup     	OBJECT IDENTIFIER ::= { ves1724-56fanless 44 }

	rateLimitMaxNumberOfProfile OBJECT-TYPE
        SYNTAX  INTEGER
        MAX-ACCESS  read-only
        STATUS  current
        DESCRIPTION
                      	""
        ::= { rateLimitProfileSetup 1 }

        rateLimitProfileTable	OBJECT-TYPE
        SYNTAX	SEQUENCE OF RateLimitProfileEntry
        MAX-ACCESS  not-accessible
        STATUS  current
        DESCRIPTION
                 	""
        ::= { rateLimitProfileSetup 2 }

	rateLimitProfileEntry OBJECT-TYPE
        SYNTAX	RateLimitProfileEntry
        MAX-ACCESS	not-accessible
        STATUS	current
        DESCRIPTION    	"An entry in rateLimitMaxNumberOfProfile."
        INDEX          	{ rateLimitProfileName }
        ::= { rateLimitProfileTable 1 }

        RateLimitProfileEntry ::=
	SEQUENCE {
        	rateLimitProfileName		DisplayString,
		rateLimitProfilePeakRate	INTEGER,
		rateLimitProfileEgrRate	INTEGER,
	        rateLimitProfileCommitRate	INTEGER,
			rateLimitProfilePeakState	EnabledStatus,
			rateLimitProfileEgrState	EnabledStatus,
			rateLimitProfileCommitState EnabledStatus,
        	rateLimitProfileRowStatus	RowStatus
        }

        rateLimitProfileName OBJECT-TYPE
        SYNTAX  DisplayString
        MAX-ACCESS  read-only
        STATUS  current
        DESCRIPTION
                      	""
        ::= { rateLimitProfileEntry 1 }

        rateLimitProfilePeakRate OBJECT-TYPE
        SYNTAX  INTEGER
        MAX-ACCESS  read-write
        STATUS  current
        DESCRIPTION
                      	"Peak rate in Kbit/s.  The range of FE port is between 1 and 100,000. For GE port, the range is between 1 and 1000,000."
        ::= { rateLimitProfileEntry 2 }

        rateLimitProfileEgrRate OBJECT-TYPE
        SYNTAX  INTEGER
        MAX-ACCESS  read-write
        STATUS  current
        DESCRIPTION
                      	"Egress rate in Kbit/s.  The range of FE port is between 1 and 100,000. For GE port, the range is between 1 and 1000,000."
        ::= { rateLimitProfileEntry 3 }

        rateLimitProfileCommitRate OBJECT-TYPE
        SYNTAX  INTEGER
        MAX-ACCESS  read-write
        STATUS  current
        DESCRIPTION
                      	"Commit rate in Kbit/s.  The range of FE port is between 0 and 100,000. For GE port, the range is between 0 and 1000,000."
        ::= { rateLimitProfileEntry 4 }

        
        rateLimitProfilePeakState OBJECT-TYPE
        SYNTAX  EnabledStatus
        MAX-ACCESS  read-write
        STATUS  current
        DESCRIPTION
                      	"Ingress peak rate limiting enabled/disabled on the port."
        ::= { rateLimitProfileEntry 5 }                                              
        
        rateLimitProfileEgrState OBJECT-TYPE
        SYNTAX  EnabledStatus
        MAX-ACCESS  read-write
        STATUS  current
        DESCRIPTION
                      	"Egress rate limiting enabled/disabled on the port."
        ::= { rateLimitProfileEntry 6 }        
        
        rateLimitProfileCommitState OBJECT-TYPE
        SYNTAX  EnabledStatus
        MAX-ACCESS  read-write
        STATUS  current
        DESCRIPTION
                      	"Ingress commit rate limiting enabled/disabled on the port."
        ::= { rateLimitProfileEntry 7 }
        

        rateLimitProfileRowStatus OBJECT-TYPE
        SYNTAX  RowStatus
        MAX-ACCESS  read-create
        STATUS  current
        DESCRIPTION
                      	""
        ::= { rateLimitProfileEntry 8 }

	perQueueMaxNumberOfProfile OBJECT-TYPE
        SYNTAX  INTEGER
        MAX-ACCESS  read-only
        STATUS  current
        DESCRIPTION
                      	""
        ::= { rateLimitProfileSetup 3 }

        perQueueProfileTable	OBJECT-TYPE
        SYNTAX	SEQUENCE OF PerQueueProfileEntry
        MAX-ACCESS  not-accessible
        STATUS  current
        DESCRIPTION
                 	""
        ::= { rateLimitProfileSetup 4 }

	perQueueProfileEntry OBJECT-TYPE
        SYNTAX	PerQueueProfileEntry
        MAX-ACCESS	not-accessible
        STATUS	current
        DESCRIPTION    	"An entry in perQueueMaxNumberOfProfile."
        INDEX          	{ perQueueProfileName }
        ::= { perQueueProfileTable 1 }

        PerQueueProfileEntry ::=
	SEQUENCE {
        	perQueueProfileName		DisplayString,
		perQueueProfileQ0CIR	INTEGER,
		perQueueProfileQ0PIR	INTEGER,
		perQueueProfileQ1CIR	INTEGER,
		perQueueProfileQ1PIR	INTEGER,
		perQueueProfileQ2CIR	INTEGER,
		perQueueProfileQ2PIR	INTEGER,
		perQueueProfileQ3CIR	INTEGER,
		perQueueProfileQ3PIR	INTEGER,
		perQueueProfileQ4CIR	INTEGER,
		perQueueProfileQ4PIR	INTEGER,
		perQueueProfileQ5CIR	INTEGER,
		perQueueProfileQ5PIR	INTEGER,
		perQueueProfileQ6CIR	INTEGER,
		perQueueProfileQ6PIR	INTEGER,
		perQueueProfileQ7CIR	INTEGER,
		perQueueProfileQ7PIR	INTEGER,
        	perQueueProfileRowStatus	RowStatus
        }

        perQueueProfileName OBJECT-TYPE
        SYNTAX  DisplayString
        MAX-ACCESS  read-only
        STATUS  current
        DESCRIPTION
                      	""
        ::= { perQueueProfileEntry 1 }

        perQueueProfileQ0CIR OBJECT-TYPE
        SYNTAX  INTEGER
        MAX-ACCESS  read-write
        STATUS  current
        DESCRIPTION
                      	"Commit rate of Queue0 in Kbit/s.  The range is between 0 and 1000,000."
        ::= { perQueueProfileEntry 2 }

        perQueueProfileQ0PIR OBJECT-TYPE
        SYNTAX  INTEGER
        MAX-ACCESS  read-write
        STATUS  current
        DESCRIPTION
                      	"Peak rate of Queue0 in Kbit/s.  The range is between 0 and 1000,000."
        ::= { perQueueProfileEntry 3 }
        
        perQueueProfileQ1CIR OBJECT-TYPE
        SYNTAX  INTEGER
        MAX-ACCESS  read-write
        STATUS  current
        DESCRIPTION
                      	"Commit rate of Queue1 in Kbit/s.  The range is between 0 and 1000,000."
        ::= { perQueueProfileEntry 4 }

        perQueueProfileQ1PIR OBJECT-TYPE
        SYNTAX  INTEGER
        MAX-ACCESS  read-write
        STATUS  current
        DESCRIPTION
                      	"Peak rate of Queue1 in Kbit/s.  The range is between 0 and 1000,000."
        ::= { perQueueProfileEntry 5 }
        
        perQueueProfileQ2CIR OBJECT-TYPE
        SYNTAX  INTEGER
        MAX-ACCESS  read-write
        STATUS  current
        DESCRIPTION
                      	"Commit rate of Queue2 in Kbit/s.  The range is between 0 and 1000,000."
        ::= { perQueueProfileEntry 6 }

        perQueueProfileQ2PIR OBJECT-TYPE
        SYNTAX  INTEGER
        MAX-ACCESS  read-write
        STATUS  current
        DESCRIPTION
                      	"Peak rate of Queue2 in Kbit/s.  The range is between 0 and 1000,000."
        ::= { perQueueProfileEntry 7 }
        
        perQueueProfileQ3CIR OBJECT-TYPE
        SYNTAX  INTEGER
        MAX-ACCESS  read-write
        STATUS  current
        DESCRIPTION
                      	"Commit rate of Queue3 in Kbit/s.  The range is between 0 and 1000,000."
        ::= { perQueueProfileEntry 8 }

        perQueueProfileQ3PIR OBJECT-TYPE
        SYNTAX  INTEGER
        MAX-ACCESS  read-write
        STATUS  current
        DESCRIPTION
                      	"Peak rate of Queue3 in Kbit/s.  The range is between 0 and 1000,000."
        ::= { perQueueProfileEntry 9 }
        
        perQueueProfileQ4CIR OBJECT-TYPE
        SYNTAX  INTEGER
        MAX-ACCESS  read-write
        STATUS  current
        DESCRIPTION
                      	"Commit rate of Queue4 in Kbit/s.  The range is between 0 and 1000,000."
        ::= { perQueueProfileEntry 10 }

        perQueueProfileQ4PIR OBJECT-TYPE
        SYNTAX  INTEGER
        MAX-ACCESS  read-write
        STATUS  current
        DESCRIPTION
                      	"Peak rate of Queue4 in Kbit/s.  The range is between 0 and 1000,000."
        ::= { perQueueProfileEntry 11 }
        
        perQueueProfileQ5CIR OBJECT-TYPE
        SYNTAX  INTEGER
        MAX-ACCESS  read-write
        STATUS  current
        DESCRIPTION
                      	"Commit rate of Queue5 in Kbit/s.  The range is between 0 and 1000,000."
        ::= { perQueueProfileEntry 12 }

        perQueueProfileQ5PIR OBJECT-TYPE
        SYNTAX  INTEGER
        MAX-ACCESS  read-write
        STATUS  current
        DESCRIPTION
                      	"Peak rate of Queue5 in Kbit/s.  The range is between 0 and 1000,000."
        ::= { perQueueProfileEntry 13 }
        
        perQueueProfileQ6CIR OBJECT-TYPE
        SYNTAX  INTEGER
        MAX-ACCESS  read-write
        STATUS  current
        DESCRIPTION
                      	"Commit rate of Queue6 in Kbit/s.  The range is between 0 and 1000,000."
        ::= { perQueueProfileEntry 14 }

        perQueueProfileQ6PIR OBJECT-TYPE
        SYNTAX  INTEGER
        MAX-ACCESS  read-write
        STATUS  current
        DESCRIPTION
                      	"Peak rate of Queue6 in Kbit/s.  The range is between 0 and 1000,000."
        ::= { perQueueProfileEntry 15 }
        
        perQueueProfileQ7CIR OBJECT-TYPE
        SYNTAX  INTEGER
        MAX-ACCESS  read-write
        STATUS  current
        DESCRIPTION
                      	"Commit rate of Queue7 in Kbit/s.  The range is between 0 and 1000,000."
        ::= { perQueueProfileEntry 16 }

        perQueueProfileQ7PIR OBJECT-TYPE
        SYNTAX  INTEGER
        MAX-ACCESS  read-write
        STATUS  current
        DESCRIPTION
                      	"Peak rate of Queue7 in Kbit/s.  The range is between 0 and 1000,000."
        ::= { perQueueProfileEntry 17 }
 
        perQueueProfileRowStatus OBJECT-TYPE
        SYNTAX  RowStatus
        MAX-ACCESS  read-create
        STATUS  current
        DESCRIPTION
                      	""
        ::= { perQueueProfileEntry 18 }

------------------------
-- vlanSecuritySetup
	vlanSecuritySetup OBJECT IDENTIFIER ::= { ves1724-56fanless 45 }

        vlanSecurityTable OBJECT-TYPE
        SYNTAX	SEQUENCE OF VlanSecurityEntry
        MAX-ACCESS  not-accessible
        STATUS  current
        DESCRIPTION
                 	""
        ::= { vlanSecuritySetup 1 }

	vlanSecurityEntry OBJECT-TYPE
        SYNTAX	VlanSecurityEntry
        MAX-ACCESS	not-accessible
        STATUS	current
        DESCRIPTION    	"An entry in vlanSecurityTable."
        INDEX          	{ dot1qVlanIndex  }
        ::= { vlanSecurityTable 1 }

        VlanSecurityEntry ::=
           SEQUENCE {
		vlanSecurityCount		INTEGER
           }

        vlanSecurityCount OBJECT-TYPE
        SYNTAX  INTEGER
        MAX-ACCESS  read-write
        STATUS  current
        DESCRIPTION
                      	"Number of (dynamic) MAC addresses that may be learned on the VID."
        ::= { vlanSecurityEntry 1}

----------------------------
-- cfmSetup
	cfmSetup OBJECT IDENTIFIER ::= { ves1724-56fanless 46 }

-- cfmLoopbackPortTable

        cfmLoopbackPortTable OBJECT-TYPE
        SYNTAX	SEQUENCE OF CfmLoopbackPortEntry
        MAX-ACCESS  not-accessible
        STATUS  current
        DESCRIPTION
                 	""
        ::= { cfmSetup 1 }

	cfmLoopbackPortEntry OBJECT-TYPE
        SYNTAX	CfmLoopbackPortEntry
        MAX-ACCESS	not-accessible
        STATUS	current
        DESCRIPTION    	"An entry in cfmLoopbackPortTable."
        INDEX          	{ dot1dBasePort }
        ::= { cfmLoopbackPortTable 1 }

        CfmLoopbackPortEntry ::=
           SEQUENCE {
        	cfmLoopbackPortState	EnabledStatus
           }

        cfmLoopbackPortState OBJECT-TYPE
        SYNTAX  EnabledStatus
        MAX-ACCESS  read-write
        STATUS  current
        DESCRIPTION
                      	"CFM loopback enabled/disabled on the port."
        ::= { cfmLoopbackPortEntry 1 }
        
        cfmMIPTable	OBJECT-TYPE
        SYNTAX	SEQUENCE OF CfmMIPEntry
        MAX-ACCESS  not-accessible
        STATUS  current
        DESCRIPTION
                 	""
        ::= { cfmSetup 2 }

	cfmMIPEntry OBJECT-TYPE
        SYNTAX	CfmMIPEntry
        MAX-ACCESS	not-accessible
        STATUS	current
        DESCRIPTION    	"An entry in cfmMIPTable."
        INDEX          	{ cfmLevel, cfmVlanID, cfmPort }
        ::= { cfmMIPTable 1 }

        CfmMIPEntry ::=
	SEQUENCE {
        	cfmPort		INTEGER,
        	cfmVlanID	INTEGER,
        	cfmLevel	INTEGER,
        	cfmMIPRowStatus		RowStatus
        }

        cfmPort OBJECT-TYPE
        SYNTAX  INTEGER
        MAX-ACCESS  read-only
        STATUS  current
        DESCRIPTION
                      	""
        ::= { cfmMIPEntry 1 }

        cfmVlanID OBJECT-TYPE
        SYNTAX  INTEGER
        MAX-ACCESS  read-only
        STATUS  current
        DESCRIPTION
                      	""
        ::= { cfmMIPEntry 2 }

        cfmLevel OBJECT-TYPE
        SYNTAX  INTEGER
        MAX-ACCESS  read-only
        STATUS  current
        DESCRIPTION
                      	""
        ::= { cfmMIPEntry 3 }

        cfmMIPRowStatus OBJECT-TYPE
        SYNTAX  RowStatus
        MAX-ACCESS  read-create
        STATUS  current
        DESCRIPTION
                      	""
        ::= { cfmMIPEntry 4 }        
                               
	cfmActionEnableStatus OBJECT-TYPE
        SYNTAX  EnabledStatus
        MAX-ACCESS  read-write
        STATUS  current
        DESCRIPTION
                      	"CFM Action enable status for the CO device"
        ::= { cfmSetup 3 }
                    
--  MRSTP
	mrstp     	OBJECT IDENTIFIER ::= { ves1724-56fanless 48 }
    
    mrstpSetup  OBJECT IDENTIFIER ::= { mrstp 1 }
	                 
	mrstpBridgeTable  OBJECT-TYPE
	SYNTAX	SEQUENCE OF MrstpBridgeEntry 
	MAX-ACCESS  not-accessible
	STATUS  current
	DESCRIPTION
		    	""
	    ::= { mrstpSetup 1 }	

	mrstpBridgeEntry  OBJECT-TYPE
        SYNTAX	MrstpBridgeEntry 
        MAX-ACCESS	not-accessible
        STATUS	current
        DESCRIPTION    	"An entry in mrstpBridgeTable."
        INDEX          	{ mrstpBridgeIndex }
        ::= { mrstpBridgeTable 1 }

        MrstpBridgeEntry ::=
           SEQUENCE {
           	mrstpBridgeIndex				INTEGER,
           	mrstpState				INTEGER,  
 			mrstpProtocolSpecification		INTEGER,      	
           	mrstpPriority				INTEGER,
        	mrstpTimeSinceTopologyChange		TimeTicks,
        	mrstpTopChanges				Counter32,
        	mrstpDesignatedRoot			BridgeId,
        	mrstpRootCost				INTEGER,
        	mrstpRootPort				INTEGER,
        	mrstpMaxAge				Timeout,
        	mrstpHelloTime				Timeout,
        	mrstpHoldTime				INTEGER,
        	mrstpForwardDelay			Timeout,
        	mrstpBridgeMaxAge			Timeout,
        	mrstpBridgeHelloTime			Timeout,
        	mrstpBridgeForwardDelay			Timeout
           }

          -- the dot1dStp group

          -- Implementation of the dot1dStp group is optional.  It is
          -- implemented by those bridges that support the Spanning Tree
          -- Protocol.
          
          mrstpBridgeIndex OBJECT-TYPE
              SYNTAX  INTEGER
              MAX-ACCESS  read-only
              STATUS  current
              DESCRIPTION
                      "The tree index of the MRSTP."
              ::= { mrstpBridgeEntry 1 }
			
		  mrstpState OBJECT-TYPE
        	SYNTAX  EnabledStatus
        	MAX-ACCESS  read-write
        	STATUS  current
        	DESCRIPTION
                      "Enabled/disabled on the mrstp bridge."
        ::= { mrstpBridgeEntry 2 }
        
          mrstpProtocolSpecification OBJECT-TYPE
              SYNTAX  INTEGER {
                          unknown(1),
                          decLb100(2),
                          ieee8021d(3)
                      }
              MAX-ACCESS  read-only
              STATUS  current
              DESCRIPTION
                      "An indication of what version of the Spanning
                      Tree Protocol is being run.  The value
                      'decLb100(2)' indicates the DEC LANbridge 100
                      Spanning Tree protocol.  IEEE 802.1d
                      implementations will return 'ieee8021d(3)'.  If
                      future versions of the IEEE Spanning Tree Protocol
                      are released that are incompatible with the
                      current version a new value will be defined."
              ::= { mrstpBridgeEntry 3 }
        
          mrstpPriority OBJECT-TYPE
              SYNTAX  INTEGER (0..65535)
              MAX-ACCESS  read-write
              STATUS  current
              DESCRIPTION
                      "The value of the write-able portion of the Bridge
                      ID, i.e., the first two octets of the (8 octet
                      long) Bridge ID.  The other (last) 6 octets of the
                      Bridge ID are given by the value of
                      dot1dBaseBridgeAddress."
              REFERENCE
                      "IEEE 802.1D-1990: Section 4.5.3.7"
              ::= { mrstpBridgeEntry 4 }

          mrstpTimeSinceTopologyChange OBJECT-TYPE
              SYNTAX  TimeTicks
              MAX-ACCESS  read-only
              STATUS  current
              DESCRIPTION
                      "The time (in hundredths of a second) since the
                      last time a topology change was detected by the
                      bridge entity."
              REFERENCE
                      "IEEE 802.1D-1990: Section 6.8.1.1.3"
              ::= { mrstpBridgeEntry 5 }

          mrstpTopChanges OBJECT-TYPE
              SYNTAX  Counter32
              MAX-ACCESS  read-only
              STATUS  current
              DESCRIPTION
                      "The total number of topology changes detected by
                      this bridge since the management entity was last
                      reset or initialized."
              REFERENCE
                      "IEEE 802.1D-1990: Section 6.8.1.1.3"
              ::= { mrstpBridgeEntry 6 }

          mrstpDesignatedRoot OBJECT-TYPE
              SYNTAX  BridgeId
              MAX-ACCESS  read-only
              STATUS  current
              DESCRIPTION
                      "The bridge identifier of the root of the spanning
                      tree as determined by the Spanning Tree Protocol
                      as executed by this node.  This value is used as
                      the Root Identifier parameter in all Configuration
                      Bridge PDUs originated by this node."
              REFERENCE
                      "IEEE 802.1D-1990: Section 4.5.3.1"
              ::= { mrstpBridgeEntry 7 }

          mrstpRootCost OBJECT-TYPE
              SYNTAX  INTEGER
              MAX-ACCESS  read-only
              STATUS  current
              DESCRIPTION
                      "The cost of the path to the root as seen from
                      this bridge."
              REFERENCE
                      "IEEE 802.1D-1990: Section 4.5.3.2"
              ::= { mrstpBridgeEntry 8 }

          mrstpRootPort OBJECT-TYPE
              SYNTAX  INTEGER
              MAX-ACCESS  read-only
              STATUS  current
              DESCRIPTION
                      "The port number of the port which offers the
                      lowest cost path from this bridge to the root
                      bridge."
              REFERENCE
                      "IEEE 802.1D-1990: Section 4.5.3.3"
              ::= { mrstpBridgeEntry 9 }

          mrstpMaxAge OBJECT-TYPE
              SYNTAX  Timeout
              MAX-ACCESS  read-only
              STATUS  current
              DESCRIPTION
                      "The maximum age of Spanning Tree Protocol
                      information learned from the network on any port
                      before it is discarded, in units of hundredths of
                      a second.  This is the actual value that this
                      bridge is currently using."
              REFERENCE
                      "IEEE 802.1D-1990: Section 4.5.3.4"
              ::= { mrstpBridgeEntry 10 }

          mrstpHelloTime OBJECT-TYPE
              SYNTAX  Timeout
              MAX-ACCESS  read-only
              STATUS  current
              DESCRIPTION
                      "The amount of time between the transmission of
                      Configuration bridge PDUs by this node on any port
                      when it is the root of the spanning tree or trying
                      to become so, in units of hundredths of a second.
                      This is the actual value that this bridge is
                      currently using."
              REFERENCE
                      "IEEE 802.1D-1990: Section 4.5.3.5"
              ::= { mrstpBridgeEntry 11 }

          mrstpHoldTime OBJECT-TYPE
              SYNTAX  INTEGER
              MAX-ACCESS  read-only
              STATUS  current
              DESCRIPTION
                      "This time value determines the interval length
                      during which no more than two Configuration bridge
                      PDUs shall be transmitted by this node, in units
                      of hundredths of a second."
              REFERENCE
                      "IEEE 802.1D-1990: Section 4.5.3.14"
              ::= { mrstpBridgeEntry 12 }

          mrstpForwardDelay OBJECT-TYPE
              SYNTAX  Timeout
              MAX-ACCESS  read-only
              STATUS  current
              DESCRIPTION
                      "This time value, measured in units of hundredths
                      of a second, controls how fast a port changes its
                      spanning state when moving towards the Forwarding
                      state.  The value determines how long the port
                      stays in each of the Listening and Learning
                      states, which precede the Forwarding state.  This
                      value is also used, when a topology change has
                      been detected and is underway, to age all dynamic
                      entries in the Forwarding Database.  [Note that
                      this value is the one that this bridge is
                      currently using, in contrast to
                      mrstpBridgeForwardDelay which is the value that
                      this bridge and all others would start using
                      if/when this bridge were to become the root.]"
              REFERENCE
                      "IEEE 802.1D-1990: Section 4.5.3.6"
              ::= { mrstpBridgeEntry 13 }

          mrstpBridgeMaxAge OBJECT-TYPE
              SYNTAX  Timeout (600..4000)
              MAX-ACCESS  read-write
              STATUS  current
              DESCRIPTION
                      "The value that all bridges use for MaxAge when
                      this bridge is acting as the root.  Note that
                      802.1D-1990 specifies that the range for this
                      parameter is related to the value of
                      mrstpBridgeHelloTime. The granularity of this
                      timer is specified by 802.1D-1990 to be 1 second.
                      An agent may return a badValue error if a set is
                      attempted to a value which is not a whole number
                      of seconds."
              REFERENCE
                      "IEEE 802.1D-1990: Section 4.5.3.8"
              ::= { mrstpBridgeEntry 14 }

          mrstpBridgeHelloTime OBJECT-TYPE
              SYNTAX  Timeout (100..1000)
              MAX-ACCESS  read-write
              STATUS  current
              DESCRIPTION
                      "The value that all bridges use for HelloTime when
                      this bridge is acting as the root.  The
                      granularity of this timer is specified by 802.1D-
                      1990 to be 1 second.  An agent may return a
                      badValue error if a set is attempted to a value
                      which is not a whole number of seconds."
              REFERENCE
                      "IEEE 802.1D-1990: Section 4.5.3.9"
              ::= { mrstpBridgeEntry 15 }

          mrstpBridgeForwardDelay OBJECT-TYPE
              SYNTAX  Timeout (400..3000)
              MAX-ACCESS  read-write
              STATUS  current
              DESCRIPTION
                      "The value that all bridges use for ForwardDelay
                      when this bridge is acting as the root.  Note that
                      802.1D-1990 specifies that the range for this
                      parameter is related to the value of
                      mrstpBridgeMaxAge.  The granularity of this
                      timer is specified by 802.1D-1990 to be 1 second.
                      An agent may return a badValue error if a set is
                      attempted to a value which is not a whole number
                      of seconds."
              REFERENCE
                      "IEEE 802.1D-1990: Section 4.5.3.10"
              ::= { mrstpBridgeEntry 16 }

          -- The Spanning Tree Port Table

          mrstpPortTable OBJECT-TYPE
              SYNTAX  SEQUENCE OF MrstpPortEntry
              MAX-ACCESS  not-accessible
              STATUS  current
              DESCRIPTION
                      "A table that contains port-specific information
                      for the Spanning Tree Protocol."
              ::= { mrstpSetup 2 }

          mrstpPortEntry OBJECT-TYPE
              SYNTAX  MrstpPortEntry
              MAX-ACCESS  not-accessible
              STATUS  current
              DESCRIPTION
                      "A list of information maintained by every port
                      about the Spanning Tree Protocol state for that
                      port."
              INDEX   { mrstpPort }
              ::= { mrstpPortTable 1 }

          MrstpPortEntry ::=
              SEQUENCE {
                  mrstpPort
                      INTEGER,
                  mrstpPortPriority
                      INTEGER,
                  mrstpPortState
                      INTEGER,
                  mrstpPortEnable
                      INTEGER,
                  mrstpPortPathCost
                      INTEGER,
                  mrstpPortDesignatedRoot
                      BridgeId,
                  mrstpPortDesignatedCost
                      INTEGER,
                  mrstpPortDesignatedBridge
                      BridgeId,
                  mrstpPortDesignatedPort
                      OCTET STRING,
                  mrstpPortForwardTransitions
                      Counter32,
                  mrstpPortOnBridgeIndex
                      INTEGER
              }

          mrstpPort OBJECT-TYPE
              SYNTAX  INTEGER (1..65535)
              MAX-ACCESS  read-only
              STATUS  current
              DESCRIPTION
                      "The port number of the port for which this entry
                      contains Spanning Tree Protocol management
                      information."
              REFERENCE
                      "IEEE 802.1D-1990: Section 6.8.2.1.2"
              ::= { mrstpPortEntry 1 }

          mrstpPortPriority OBJECT-TYPE
              SYNTAX  INTEGER (0..255)
              MAX-ACCESS  read-write
              STATUS  current
              DESCRIPTION
                      "The value of the priority field which is
                      contained in the first (in network byte order)
                      octet of the (2 octet long) Port ID.  The other
                      octet of the Port ID is given by the value of
                      mrstpPort."
              REFERENCE
                      "IEEE 802.1D-1990: Section 4.5.5.1"
              ::= { mrstpPortEntry 2 }

          mrstpPortState OBJECT-TYPE
              SYNTAX  INTEGER {
                          disabled(1),
                          blocking(2),
                          listening(3),
                          learning(4),
                          forwarding(5),
                          broken(6)
                      }
              MAX-ACCESS  read-only
              STATUS  current
              DESCRIPTION
                      "The port's current state as defined by
                      application of the Spanning Tree Protocol.  This
                      state controls what action a port takes on
                      reception of a frame.  If the bridge has detected
                      a port that is malfunctioning it will place that
                      port into the broken(6) state.  For ports which
                      are disabled (see mrstpPortEnable), this object
                      will have a value of disabled(1)."
              REFERENCE
                      "IEEE 802.1D-1990: Section 4.5.5.2"
              ::= { mrstpPortEntry 3 }

          mrstpPortEnable OBJECT-TYPE
              SYNTAX  INTEGER {
                          enabled(1),
                          disabled(2)
                      }
              MAX-ACCESS  read-write
              STATUS  current
              DESCRIPTION
                      "The enabled/disabled status of the port."
              REFERENCE
                      "IEEE 802.1D-1990: Section 4.5.5.2"
              ::= { mrstpPortEntry 4 }

          mrstpPortPathCost OBJECT-TYPE
              SYNTAX  INTEGER (1..65535)
              MAX-ACCESS  read-write
              STATUS  current
              DESCRIPTION
                      "The contribution of this port to the path cost of
                      paths towards the spanning tree root which include
                      this port.  802.1D-1990 recommends that the
                      default value of this parameter be in inverse
                      proportion to the speed of the attached LAN."
              REFERENCE
                      "IEEE 802.1D-1990: Section 4.5.5.3"
              ::= { mrstpPortEntry 5 }

          mrstpPortDesignatedRoot OBJECT-TYPE
              SYNTAX  BridgeId
              MAX-ACCESS  read-only
              STATUS  current
              DESCRIPTION
                      "The unique Bridge Identifier of the Bridge
                      recorded as the Root in the Configuration BPDUs
                      transmitted by the Designated Bridge for the
                      segment to which the port is attached."
              REFERENCE
                      "IEEE 802.1D-1990: Section 4.5.5.4"
              ::= { mrstpPortEntry 6 }

          mrstpPortDesignatedCost OBJECT-TYPE
              SYNTAX  INTEGER
              MAX-ACCESS  read-only
              STATUS  current
              DESCRIPTION
                      "The path cost of the Designated Port of the
                      segment connected to this port.  This value is
                      compared to the Root Path Cost field in received
                      bridge PDUs."
              REFERENCE
                      "IEEE 802.1D-1990: Section 4.5.5.5"
              ::= { mrstpPortEntry 7 }

          mrstpPortDesignatedBridge OBJECT-TYPE
              SYNTAX  BridgeId
              MAX-ACCESS  read-only
              STATUS  current
              DESCRIPTION
                      "The Bridge Identifier of the bridge which this
                      port considers to be the Designated Bridge for
                      this port's segment."
              REFERENCE
                      "IEEE 802.1D-1990: Section 4.5.5.6"
              ::= { mrstpPortEntry 8 }

          mrstpPortDesignatedPort OBJECT-TYPE
              SYNTAX  OCTET STRING (SIZE (2))
              MAX-ACCESS  read-only
              STATUS  current
              DESCRIPTION
                      "The Port Identifier of the port on the Designated
                      Bridge for this port's segment."
              REFERENCE
                      "IEEE 802.1D-1990: Section 4.5.5.7"
              ::= { mrstpPortEntry 9 }

          mrstpPortForwardTransitions OBJECT-TYPE
              SYNTAX  Counter32
              MAX-ACCESS  read-only
              STATUS  current
              DESCRIPTION
                      "The number of times this port has transitioned
                      from the Learning state to the Forwarding state."
              ::= { mrstpPortEntry 10 }

          mrstpPortOnBridgeIndex OBJECT-TYPE
              SYNTAX  INTEGER
              MAX-ACCESS  read-write
              STATUS  current
              DESCRIPTION
                      "Indetify the bridge index that this port joined to in MRSTP."
              ::= { mrstpPortEntry 11 }
              
--  MRSTP Trap
	mrstpNotifications     	OBJECT IDENTIFIER ::= { mrstp 2 }              
	
	 newRoot NOTIFICATION-TYPE
      OBJECTS {
        mrstpBridgeIndex
      }
      STATUS  current
      DESCRIPTION
          ""
      ::= { mrstpNotifications 1 }
                                             
    topologyChange NOTIFICATION-TYPE
      OBJECTS {
        mrstpBridgeIndex
      }
      STATUS  current
      DESCRIPTION
          ""
      ::= { mrstpNotifications 2 }                                                              
---------------------------------------------------
--
--  dhcp snooping
--
---------------------------------------------------

	dhcpSnp     	OBJECT IDENTIFIER ::= { ves1724-56fanless 49 }
	

--
--  dhcp snooping vlan table
--
	
        dhcpSnpVlanTable	OBJECT-TYPE
        SYNTAX	SEQUENCE OF DhcpSnpVlanEntry
        MAX-ACCESS  not-accessible
        STATUS  current
        DESCRIPTION
                 	""
        ::= { dhcpSnp 1 }

	dhcpSnpVlanEntry OBJECT-TYPE
        SYNTAX	DhcpSnpVlanEntry
        MAX-ACCESS	not-accessible
        STATUS	current
        DESCRIPTION    	""
        INDEX          	{ dhcpSnpVlanEntryVid }
        ::= { dhcpSnpVlanTable 1 }

        DhcpSnpVlanEntry ::=
	SEQUENCE {
        	dhcpSnpVlanEntryVid		INTEGER,
        	dhcpSnpVlanEntryEnable		EnabledStatus,
        	dhcpSnpVlanEntryOption82Enable	EnabledStatus,
        	dhcpSnpVlanEntryInfo		EnabledStatus,
        	dhcpSnpVlanEntryRemoteID	EnabledStatus,
					dhcpSnpVlanEntrySPV			INTEGER,
					dhcpSnpVlanEntryDELIM		INTEGER
        }

        dhcpSnpVlanEntryVid OBJECT-TYPE
        SYNTAX  INTEGER (1..4094)
        MAX-ACCESS  read-only
        STATUS  current
        DESCRIPTION
                      	""
        ::= { dhcpSnpVlanEntry 1 }

        dhcpSnpVlanEntryEnable OBJECT-TYPE
        SYNTAX  EnabledStatus
        MAX-ACCESS  read-write
        STATUS  current
        DESCRIPTION
                      	""
        ::= { dhcpSnpVlanEntry 2 }
        
        dhcpSnpVlanEntryOption82Enable OBJECT-TYPE
        SYNTAX  EnabledStatus
        MAX-ACCESS  read-write
        STATUS  current
        DESCRIPTION
                      	""
        ::= { dhcpSnpVlanEntry 3 }
        
        dhcpSnpVlanEntryInfo OBJECT-TYPE
        SYNTAX  EnabledStatus
        MAX-ACCESS  read-write
        STATUS  current
        DESCRIPTION
                      	""
        ::= { dhcpSnpVlanEntry 4 }

        dhcpSnpVlanEntryRemoteID OBJECT-TYPE
        SYNTAX  EnabledStatus
        MAX-ACCESS  read-write
        STATUS  current
        DESCRIPTION
                      	""
        ::= { dhcpSnpVlanEntry 5 }


		dhcpSnpVlanEntrySPV OBJECT-TYPE
        SYNTAX  INTEGER	
        {
      		private(0),
 			sp(1),
			sv(2),
     		pv(3),
     		spv(4)
        }
        MAX-ACCESS  read-write
        STATUS  current
        DESCRIPTION
        	"Tag option setting for DHCP snooping. private(0), SP(1), SV(2), PV(3), SPV(4)."
        ::= { dhcpSnpVlanEntry 6 }        

        dhcpSnpVlanEntryDELIM OBJECT-TYPE
        SYNTAX  INTEGER	
        {
        	none(0),
      		pound(1),
 			semicolon(2),
			dot(3),
     		comma(4),
     		slash(5),
     		space(6)
        }
        MAX-ACCESS  read-write
        STATUS  current
        DESCRIPTION
        	"Delimiter setting for DHCP snooping. none(0), pound[#](1), semicolon[;](2), dot[.](3), comma[,](4), slash[/](5), space[ ](6)."
        ::= { dhcpSnpVlanEntry 7 }
--	end ab4daa       

--
--  dhcp snooping interface table
--

        dhcpSnpPortTable	OBJECT-TYPE
        SYNTAX	SEQUENCE OF DhcpSnpPortEntry
        MAX-ACCESS  not-accessible
        STATUS  current
        DESCRIPTION
                 	""
        ::= { dhcpSnp 2 }

	dhcpSnpPortEntry OBJECT-TYPE
        SYNTAX	DhcpSnpPortEntry
        MAX-ACCESS	not-accessible
        STATUS	current
        DESCRIPTION    	""
        INDEX          	{ dhcpSnpPortEntryPort }
        ::= { dhcpSnpPortTable 1 }

        DhcpSnpPortEntry ::=
	SEQUENCE {
        	dhcpSnpPortEntryPort		INTEGER,
        	dhcpSnpPortEntryTrust		EnabledStatus,
        	dhcpSnpPortEntryRate		INTEGER
        }

        dhcpSnpPortEntryPort OBJECT-TYPE
        SYNTAX  INTEGER
        MAX-ACCESS  read-only
        STATUS  current
        DESCRIPTION
                      	""
        ::= { dhcpSnpPortEntry 1 }

        dhcpSnpPortEntryTrust OBJECT-TYPE
        SYNTAX  EnabledStatus
        MAX-ACCESS  read-write
        STATUS  current
        DESCRIPTION
                      	""
        ::= { dhcpSnpPortEntry 2 }

        dhcpSnpPortEntryRate OBJECT-TYPE
        SYNTAX  INTEGER (0..2048)
        MAX-ACCESS  read-write
        STATUS  current
        DESCRIPTION
                      	"0 means unlimited"
        ::= { dhcpSnpPortEntry 3 }
--
--  dhcp snooping binding table
--

        dhcpSnpBindTable	OBJECT-TYPE
        SYNTAX	SEQUENCE OF DhcpSnpBindEntry
        MAX-ACCESS  not-accessible
        STATUS  current
        DESCRIPTION
                 	""
        ::= { dhcpSnp 3 }

	dhcpSnpBindEntry OBJECT-TYPE
        SYNTAX	DhcpSnpBindEntry
        MAX-ACCESS	not-accessible
        STATUS	current
        DESCRIPTION    	""
        INDEX          	{ dhcpSnpBindEntryMac, dhcpSnpBindEntryVid }
        ::= { dhcpSnpBindTable 1 }

        DhcpSnpBindEntry ::=
	SEQUENCE {
        	dhcpSnpBindEntryMac		MacAddress,
        	dhcpSnpBindEntryVid		INTEGER,
        	dhcpSnpBindEntryIP		IpAddress,
        	dhcpSnpBindEntryLease		INTEGER,
        	dhcpSnpBindEntryType		INTEGER,
        	dhcpSnpBindEntryPort		INTEGER
        }

        dhcpSnpBindEntryMac OBJECT-TYPE
        SYNTAX  MacAddress
        MAX-ACCESS  read-only
        STATUS  current
        DESCRIPTION
                      	""
        ::= { dhcpSnpBindEntry 1 }

        dhcpSnpBindEntryVid OBJECT-TYPE
        SYNTAX  INTEGER
        MAX-ACCESS  read-only
        STATUS  current
        DESCRIPTION
                      	""
        ::= { dhcpSnpBindEntry 2 }
        
        dhcpSnpBindEntryIP OBJECT-TYPE
        SYNTAX  IpAddress
        MAX-ACCESS  read-only
        STATUS  current
        DESCRIPTION
                      	""
        ::= { dhcpSnpBindEntry 3 }

        dhcpSnpBindEntryLease OBJECT-TYPE
        SYNTAX  INTEGER
        MAX-ACCESS  read-only
        STATUS  current
        DESCRIPTION
                      	""
        ::= { dhcpSnpBindEntry 4 }

        dhcpSnpBindEntryType OBJECT-TYPE
        SYNTAX  INTEGER { dynamic(2) }
        MAX-ACCESS  read-only
        STATUS  current
        DESCRIPTION
                      	""
        ::= { dhcpSnpBindEntry 5 }

        dhcpSnpBindEntryPort OBJECT-TYPE
        SYNTAX  INTEGER
        MAX-ACCESS  read-only
        STATUS  current
        DESCRIPTION
                      	""
        ::= { dhcpSnpBindEntry 6 }

--
--  dhcp snooping
--

	dhcpSnpEnable OBJECT-TYPE
	SYNTAX  EnabledStatus
	MAX-ACCESS  read-write
	STATUS  current
	DESCRIPTION
	              ""
	::= { dhcpSnp 4 }                                      

--
--  dhcp snooping database
--

	
	dhcpSnpDb     	OBJECT IDENTIFIER ::= { dhcpSnp 5 }
	
	dhcpSnpDbAbort OBJECT-TYPE
	SYNTAX  INTEGER (1..65535)
	MAX-ACCESS  read-write
	STATUS  current
	DESCRIPTION
	              ""
	::= { dhcpSnpDb 1 }                                      	

	dhcpSnpDbWriteDelay OBJECT-TYPE
	SYNTAX  INTEGER (1..65535)
	MAX-ACCESS  read-write
	STATUS  current
	DESCRIPTION
	              ""
	::= { dhcpSnpDb 2 }                                      
	
	dhcpSnpDbUrl OBJECT-TYPE
	SYNTAX  DisplayString (SIZE (0..255))
	MAX-ACCESS  read-write
	STATUS  current
	DESCRIPTION
	              ""
	::= { dhcpSnpDb 3 }

	dhcpSnpDbUrlRenew OBJECT-TYPE
	SYNTAX  DisplayString (SIZE (0..255))
	MAX-ACCESS  read-write
	STATUS  current
	DESCRIPTION
	              ""
	::= { dhcpSnpDb 4 }

	dhcpSnpDbStat     	OBJECT IDENTIFIER ::= { dhcpSnpDb 5 }

	dhcpSnpDbStatClear OBJECT-TYPE
	SYNTAX  EnabledStatus
	MAX-ACCESS  read-write
	STATUS  current
	DESCRIPTION
	              ""
	::= { dhcpSnpDbStat 1 }  
		
	dhcpSnpDbStatAgentRunning OBJECT-TYPE
	SYNTAX  INTEGER { none(0), read(1), write(2) }
	MAX-ACCESS  read-only
	STATUS  current
	DESCRIPTION
	              ""
	::= { dhcpSnpDbStat 2 }                                      	

	dhcpSnpDbStatDelayExpiry OBJECT-TYPE
	SYNTAX  INTEGER 
	MAX-ACCESS  read-only
	STATUS  current
	DESCRIPTION
	              ""
	::= { dhcpSnpDbStat 3 }	

	dhcpSnpDbStatAbortExpiry OBJECT-TYPE
	SYNTAX  INTEGER
	MAX-ACCESS  read-only
	STATUS  current
	DESCRIPTION
	              ""
	::= { dhcpSnpDbStat 4 }

	dhcpSnpDbStatLastSuccTime OBJECT-TYPE
	SYNTAX  DisplayString
	MAX-ACCESS  read-only
	STATUS  current
	DESCRIPTION
	              ""
	::= { dhcpSnpDbStat 5 }
	
	dhcpSnpDbStatLastFailTime OBJECT-TYPE
	SYNTAX  DisplayString
	MAX-ACCESS  read-only
	STATUS  current
	DESCRIPTION
	              ""
	::= { dhcpSnpDbStat 6 }
	
	dhcpSnpDbStatLastFailReason OBJECT-TYPE
	SYNTAX  DisplayString
	MAX-ACCESS  read-only
	STATUS  current
	DESCRIPTION
	              ""
	::= { dhcpSnpDbStat 7 }

	dhcpSnpDbStatTotalAttempt OBJECT-TYPE
	SYNTAX  INTEGER
	MAX-ACCESS  read-only
	STATUS  current
	DESCRIPTION
	              ""
	::= { dhcpSnpDbStat 8 }
	
	dhcpSnpDbStatStartupFail OBJECT-TYPE
	SYNTAX  INTEGER
	MAX-ACCESS  read-only
	STATUS  current
	DESCRIPTION
	              ""
	::= { dhcpSnpDbStat 9 }

	dhcpSnpDbStatSuccTrans OBJECT-TYPE
	SYNTAX  INTEGER
	MAX-ACCESS  read-only
	STATUS  current
	DESCRIPTION
	              ""
	::= { dhcpSnpDbStat 10 }
	
	dhcpSnpDbStatFailTrans OBJECT-TYPE
	SYNTAX  INTEGER
	MAX-ACCESS  read-only
	STATUS  current
	DESCRIPTION
	              ""
	::= { dhcpSnpDbStat 11 }

	dhcpSnpDbStatSuccRead OBJECT-TYPE
	SYNTAX  INTEGER
	MAX-ACCESS  read-only
	STATUS  current
	DESCRIPTION
	              ""
	::= { dhcpSnpDbStat 12 }

	dhcpSnpDbStatFailRead OBJECT-TYPE
	SYNTAX  INTEGER
	MAX-ACCESS  read-only
	STATUS  current
	DESCRIPTION
	              ""
	::= { dhcpSnpDbStat 13 }

	dhcpSnpDbStatSuccWrite OBJECT-TYPE
	SYNTAX  INTEGER
	MAX-ACCESS  read-only
	STATUS  current
	DESCRIPTION
	              ""
	::= { dhcpSnpDbStat 14 }

	dhcpSnpDbStatFailWrite OBJECT-TYPE
	SYNTAX  INTEGER
	MAX-ACCESS  read-only
	STATUS  current
	DESCRIPTION
	              ""
	::= { dhcpSnpDbStat 15 }

	dhcpSnpDbStatFirstSuccAccess OBJECT-TYPE
	SYNTAX  INTEGER { none(0), read(1), write(2) }
	MAX-ACCESS  read-only
	STATUS  current
	DESCRIPTION
	              ""
	::= { dhcpSnpDbStat 16 }

	dhcpSnpDbStatLastIgnoreBindCol OBJECT-TYPE
	SYNTAX  INTEGER
	MAX-ACCESS  read-only
	STATUS  current
	DESCRIPTION
	              "Last ignored: binding collision"
	::= { dhcpSnpDbStat 17 }

	dhcpSnpDbStatLastIgnoreExpireLease OBJECT-TYPE
	SYNTAX  INTEGER
	MAX-ACCESS  read-only
	STATUS  current
	DESCRIPTION
	              "Last ignored: expired leases"
	::= { dhcpSnpDbStat 18 }

	dhcpSnpDbStatLastIgnoreInvalidIntf OBJECT-TYPE
	SYNTAX  INTEGER
	MAX-ACCESS  read-only
	STATUS  current
	DESCRIPTION
	              "Last ignored: invalid interface"
	::= { dhcpSnpDbStat 19 }

	dhcpSnpDbStatLastIgnoreUnsuppVlan OBJECT-TYPE
	SYNTAX  INTEGER
	MAX-ACCESS  read-only
	STATUS  current
	DESCRIPTION
	              "Last ignored: unsupported vlans"
	::= { dhcpSnpDbStat 20 }

	dhcpSnpDbStatLastIgnoreParse OBJECT-TYPE
	SYNTAX  INTEGER
	MAX-ACCESS  read-only
	STATUS  current
	DESCRIPTION
	              "Last ignored: parsing error"
	::= { dhcpSnpDbStat 21 }

	dhcpSnpDbStatTotalIgnoreBindCol OBJECT-TYPE
	SYNTAX  INTEGER
	MAX-ACCESS  read-only
	STATUS  current
	DESCRIPTION
	              "Total ignored: binding collision"
	::= { dhcpSnpDbStat 22 }

	dhcpSnpDbStatTotalIgnoreExpireLease OBJECT-TYPE
	SYNTAX  INTEGER
	MAX-ACCESS  read-only
	STATUS  current
	DESCRIPTION
	              "Total ignored: expired leases"
	::= { dhcpSnpDbStat 23 }

	dhcpSnpDbStatTotalIgnoreInvalidIntf OBJECT-TYPE
	SYNTAX  INTEGER
	MAX-ACCESS  read-only
	STATUS  current
	DESCRIPTION
	              "Total ignored: invalid interface"
	::= { dhcpSnpDbStat 24 }

	dhcpSnpDbStatTotalIgnoreUnsuppVlan OBJECT-TYPE
	SYNTAX  INTEGER
	MAX-ACCESS  read-only
	STATUS  current
	DESCRIPTION
	              "Total ignored: unsupported vlans"
	::= { dhcpSnpDbStat 25 }

	dhcpSnpDbStatTotalIgnoreParse OBJECT-TYPE
	SYNTAX  INTEGER
	MAX-ACCESS  read-only
	STATUS  current
	DESCRIPTION
	              "Total ignored: parsing error"
	::= { dhcpSnpDbStat 26 }


	dhcpSnpDbStatFirstSuccessAccess OBJECT-TYPE
	SYNTAX INTEGER{
        		none(0),
        		read(1),
        		write(2)
        }
	MAX-ACCESS  read-only
	STATUS  current
	DESCRIPTION
	              "First Success Access"
	::= { dhcpSnpDbStat 27 }

--
--  dhcp snooping dhcp vlan
--

	dhcpSnpDhcpVlan     	OBJECT IDENTIFIER ::= { dhcpSnp 6 }

	dhcpSnpDhcpVlanVid OBJECT-TYPE
	SYNTAX  INTEGER (0..4094)
	MAX-ACCESS  read-write
	STATUS  current
	DESCRIPTION
	              "0: disable DHCP VLAN."
	::= { dhcpSnpDhcpVlan 1 }
	
-- --------------------------------------------------------------
--
-- ip source guard
--
-- --------------------------------------------------------------

	ipsg OBJECT IDENTIFIER ::= { ves1724-56fanless 50 }
	
	    ipsgTable  OBJECT-TYPE
	    SYNTAX	SEQUENCE OF IpsgEntry 
	    MAX-ACCESS  not-accessible
	    STATUS  current
	    DESCRIPTION
	             	""
	    ::= { ipsg 1 }	

	ipsgEntry  OBJECT-TYPE
        SYNTAX	IpsgEntry 
        MAX-ACCESS	not-accessible
        STATUS	current
        DESCRIPTION    	""
        INDEX          	{ ipsgEntryMac, ipsgEntryVid }
        ::= { ipsgTable 1 }

        IpsgEntry ::=
           SEQUENCE {
            ipsgEntryMac		MacAddress,
        	ipsgEntryVid		INTEGER,
        	ipsgEntryIp			IpAddress,
        	ipsgEntryLease		INTEGER,
        	ipsgEntryType		INTEGER,
        	ipsgEntryPort		INTEGER,
        	ipsgEntryState		RowStatus
           }

        ipsgEntryMac OBJECT-TYPE
        SYNTAX  MacAddress
        MAX-ACCESS  read-only
        STATUS  current
        DESCRIPTION
                      	""
        ::= { ipsgEntry 1 }

        ipsgEntryVid OBJECT-TYPE
        SYNTAX  INTEGER (1.. 4094)
        MAX-ACCESS  read-only
        STATUS  current
        DESCRIPTION
                      	""
        ::= { ipsgEntry 2 }

        ipsgEntryIp OBJECT-TYPE
        SYNTAX  IpAddress
        MAX-ACCESS  read-write
        STATUS  current
        DESCRIPTION
                      	""
        ::= { ipsgEntry 3 }

        ipsgEntryLease OBJECT-TYPE
        SYNTAX  INTEGER
        MAX-ACCESS  read-only
        STATUS  current
        DESCRIPTION
                      	"second"
        ::= { ipsgEntry 4 }

        ipsgEntryType OBJECT-TYPE
        SYNTAX  INTEGER { static(1), dhcp(2) }
        MAX-ACCESS  read-only
        STATUS  current
        DESCRIPTION
                      	""
        ::= { ipsgEntry 5 }

        ipsgEntryPort OBJECT-TYPE
        SYNTAX  INTEGER 
        MAX-ACCESS  read-write
        STATUS  current
        DESCRIPTION
                      	"0 means any port"
        ::= { ipsgEntry 6 }

        ipsgEntryState OBJECT-TYPE
        SYNTAX  RowStatus
        MAX-ACCESS  read-create
        STATUS  current
        DESCRIPTION
                      	""
        ::= { ipsgEntry 7 } 

-- --------------------------------------------------------------
--
-- arpInspect
--
-- --------------------------------------------------------------

	arpInspect     	OBJECT IDENTIFIER ::= { ves1724-56fanless 51 }

	arpInspectSetup  OBJECT IDENTIFIER ::= { arpInspect 1 }

        arpInspectState OBJECT-TYPE
        SYNTAX  EnabledStatus
        MAX-ACCESS  read-write
        STATUS  current
        DESCRIPTION
                      ""
        ::= { arpInspectSetup 1 }

        arpInspectFilterAgingTime OBJECT-TYPE
        SYNTAX  INTEGER (0..2147483647)
        MAX-ACCESS  read-write
        STATUS  current
        DESCRIPTION
                      ""
        ::= { arpInspectSetup 2 }

	arpInspectLog  OBJECT IDENTIFIER ::= { arpInspectSetup 3 }
	
        arpInspectLogEntries OBJECT-TYPE
        SYNTAX  INTEGER	(0..1024)
        MAX-ACCESS  read-write
        STATUS  current
        DESCRIPTION
                      ""
        ::= { arpInspectLog 1 }

        arpInspectLogRate OBJECT-TYPE
        SYNTAX  INTEGER (0..1024)
        MAX-ACCESS  read-write
        STATUS  current
        DESCRIPTION
                      ""
        ::= { arpInspectLog 2 }
        
        arpInspectLogInterval OBJECT-TYPE
        SYNTAX  INTEGER (0..2147483647)
        MAX-ACCESS  read-write
        STATUS  current
        DESCRIPTION
                      ""
        ::= { arpInspectLog 3 }                	

	--arpInspectVlanTable
        arpInspectVlanTable OBJECT-TYPE
        SYNTAX	SEQUENCE OF ArpInspectVlanEntry
        MAX-ACCESS  not-accessible
        STATUS  current
        DESCRIPTION
                 	""
        ::= { arpInspectSetup 4 }
        
	arpInspectVlanEntry OBJECT-TYPE
        SYNTAX	ArpInspectVlanEntry
        MAX-ACCESS	not-accessible
        STATUS	current
        DESCRIPTION    	""
        INDEX          	{ arpInspectVlanVid }
        ::= { arpInspectVlanTable 1 }

        ArpInspectVlanEntry ::=
           SEQUENCE {
        	arpInspectVlanVid	INTEGER,
        	arpInspectVlanLog	INTEGER,
			arpInspectVlanStatus	INTEGER       	
           }

        arpInspectVlanVid OBJECT-TYPE
        SYNTAX  INTEGER (1..4094)
        MAX-ACCESS  read-only
        STATUS  current
        DESCRIPTION
                      	""
        ::= { arpInspectVlanEntry 1 }

        arpInspectVlanLog OBJECT-TYPE
        SYNTAX  INTEGER {
        		all (1),
        		none (2),
        		permit (3),
        		deny (4)
        }
        		
        MAX-ACCESS  read-write
        STATUS  current
        DESCRIPTION
                      	""
        ::= { arpInspectVlanEntry 2 }

        arpInspectVlanStatus OBJECT-TYPE
        SYNTAX  INTEGER {
        		enabled(1),
        		disabled(2)
        }
        MAX-ACCESS  read-write
        STATUS  current
        DESCRIPTION
                      	""
        ::= { arpInspectVlanEntry 3 }

	--arpInspectPortTable
        arpInspectPortTable OBJECT-TYPE
        SYNTAX	SEQUENCE OF ArpInspectPortEntry
        MAX-ACCESS  not-accessible
        STATUS  current
        DESCRIPTION
                 	""
        ::= { arpInspectSetup 5 }
        
	arpInspectPortEntry OBJECT-TYPE
        SYNTAX	ArpInspectPortEntry
        MAX-ACCESS	not-accessible
        STATUS	current
        DESCRIPTION    	""
        INDEX          	{ arpInspectPortIndex }
        ::= { arpInspectPortTable 1 }

        ArpInspectPortEntry ::=
           SEQUENCE {
        	arpInspectPortIndex	INTEGER,
        	arpInspectPortTrust	INTEGER,
			arpInspectPortRate	INTEGER,       	
			arpInspectPortInterval	INTEGER
           }

        arpInspectPortIndex OBJECT-TYPE
        SYNTAX  INTEGER
        MAX-ACCESS  read-only
        STATUS  current
        DESCRIPTION
                      	""
        ::= { arpInspectPortEntry 1 }

        arpInspectPortTrust OBJECT-TYPE
        SYNTAX  INTEGER {
        		trusted(1),
        		untrusted(2)
        }
        MAX-ACCESS  read-write
        STATUS  current
        DESCRIPTION
                      	""
        ::= { arpInspectPortEntry 2 }

        arpInspectPortRate OBJECT-TYPE
        SYNTAX  INTEGER	(0..2048)
        MAX-ACCESS  read-write
        STATUS  current
        DESCRIPTION
                      	""
        ::= { arpInspectPortEntry 3 }

        arpInspectPortInterval OBJECT-TYPE
        SYNTAX  INTEGER	(1..15)
        MAX-ACCESS  read-write
        STATUS  current
        DESCRIPTION
                      	""
        ::= { arpInspectPortEntry 4 }

	arpInspectStatus  OBJECT IDENTIFIER ::= { arpInspect 2 }

        arpInspectFilterClear OBJECT-TYPE
        SYNTAX  EnabledStatus
        MAX-ACCESS  read-write
        STATUS  current
        DESCRIPTION
                      ""
        ::= { arpInspectStatus 1 }

        arpInspectLogClear OBJECT-TYPE
        SYNTAX  EnabledStatus
        MAX-ACCESS  read-write
        STATUS  current
        DESCRIPTION
                      ""
        ::= { arpInspectStatus 2 }

	--arpInspectFilterTable
        arpInspectFilterTable OBJECT-TYPE
        SYNTAX	SEQUENCE OF ArpInspectFilterEntry
        MAX-ACCESS  not-accessible
        STATUS  current
        DESCRIPTION
                 	""
        ::= { arpInspectStatus 3 }
        
	arpInspectFilterEntry OBJECT-TYPE
        SYNTAX	ArpInspectFilterEntry
        MAX-ACCESS	not-accessible
        STATUS	current
        DESCRIPTION    	""
        INDEX          	{ arpInspectFilterMac, arpInspectFilterVid }
        ::= { arpInspectFilterTable 1 }

        ArpInspectFilterEntry ::=
           SEQUENCE {
        	arpInspectFilterMac	MacAddress,
        	arpInspectFilterVid	INTEGER,
			arpInspectFilterPort	INTEGER,       	
			arpInspectFilterExpiry	INTEGER,
			arpInspectFilterReason	INTEGER,
			arpInspectFilterRowStatus RowStatus
           }

        arpInspectFilterMac OBJECT-TYPE
        SYNTAX  MacAddress
        MAX-ACCESS  read-only
        STATUS  current
        DESCRIPTION
                      	""
        ::= { arpInspectFilterEntry 1 }

        arpInspectFilterVid OBJECT-TYPE
        SYNTAX  INTEGER (1..4094)
        MAX-ACCESS  read-only
        STATUS  current
        DESCRIPTION
                      	""
        ::= { arpInspectFilterEntry 2 }

        arpInspectFilterPort OBJECT-TYPE
        SYNTAX  INTEGER
        MAX-ACCESS  read-only
        STATUS  current
        DESCRIPTION
                      	""
        ::= { arpInspectFilterEntry 3 }

        arpInspectFilterExpiry OBJECT-TYPE
        SYNTAX  INTEGER
        MAX-ACCESS  read-only
        STATUS  current
        DESCRIPTION
                      	""
        ::= { arpInspectFilterEntry 4 }	

        arpInspectFilterReason OBJECT-TYPE
        SYNTAX  INTEGER {
        		macVid(1),
        		port(2),
        		ip(3)
        }
        MAX-ACCESS  read-only
        STATUS  current
        DESCRIPTION
                      	""
        ::= { arpInspectFilterEntry 5 }		
        
       arpInspectFilterRowStatus OBJECT-TYPE
        SYNTAX  RowStatus
        MAX-ACCESS  read-create
        STATUS  current
        DESCRIPTION
                      	""
        ::= { arpInspectFilterEntry 6 }	

	--arpInspectLogTable
        arpInspectLogTable OBJECT-TYPE
        SYNTAX	SEQUENCE OF ArpInspectLogEntry
        MAX-ACCESS  not-accessible
        STATUS  current
        DESCRIPTION
                 	""
        ::= { arpInspectStatus 4 }
        
	arpInspectLogEntry OBJECT-TYPE
        SYNTAX	ArpInspectLogEntry
        MAX-ACCESS	not-accessible
        STATUS	current
        DESCRIPTION    	""
        INDEX          	{ arpInspectLogMac, arpInspectLogVid, arpInspectLogPort, arpInspectLogIp, arpInspectLogReason }
        ::= { arpInspectLogTable 1 }

        ArpInspectLogEntry ::=
           SEQUENCE {
        	arpInspectLogMac	MacAddress,
        	arpInspectLogVid	INTEGER,
			arpInspectLogPort	INTEGER,       	
			arpInspectLogIp	IpAddress,
			arpInspectLogNumPkt	INTEGER,
			arpInspectLogReason	INTEGER,
			arpInspectLogTime	DateAndTime
           }

        arpInspectLogMac OBJECT-TYPE
        SYNTAX  MacAddress
        MAX-ACCESS  read-only
        STATUS  current
        DESCRIPTION
                      	""
        ::= { arpInspectLogEntry 1 }

        arpInspectLogVid OBJECT-TYPE
        SYNTAX  INTEGER (1..4094)
        MAX-ACCESS  read-only
        STATUS  current
        DESCRIPTION
                      	""
        ::= { arpInspectLogEntry 2 }

        arpInspectLogPort OBJECT-TYPE
        SYNTAX  INTEGER
        MAX-ACCESS  read-only
        STATUS  current
        DESCRIPTION
                      	""
        ::= { arpInspectLogEntry 3 }

        arpInspectLogIp OBJECT-TYPE
        SYNTAX  IpAddress
        MAX-ACCESS  read-only
        STATUS  current
        DESCRIPTION
                      	""
        ::= { arpInspectLogEntry 4 }	

        arpInspectLogNumPkt OBJECT-TYPE
        SYNTAX  INTEGER
        MAX-ACCESS  read-only
        STATUS  current
        DESCRIPTION
                      	""
        ::= { arpInspectLogEntry 5 }		

        arpInspectLogReason OBJECT-TYPE
        SYNTAX  INTEGER {
        		deny (1),
        		denyStatic (2),
        		denyDHCP (3),
        		permitStatic (4),
        		permitDHCP (5)
        }
        MAX-ACCESS  read-only
        STATUS  current
        DESCRIPTION
                      	""
        ::= { arpInspectLogEntry 6 }		
        
        arpInspectLogTime OBJECT-TYPE
        SYNTAX  DateAndTime
        MAX-ACCESS  read-only
        STATUS  current
        DESCRIPTION
                      	""
        ::= { arpInspectLogEntry 7 }		
        
	--arpInspectStatisticsTable
        arpInspectStatisticsTable OBJECT-TYPE
        SYNTAX	SEQUENCE OF ArpInspectStatisticsEntry
        MAX-ACCESS  not-accessible
        STATUS  current
        DESCRIPTION
                 	""
        ::= { arpInspectStatus 5 }
        
	arpInspectStatisticsEntry OBJECT-TYPE
        SYNTAX	ArpInspectStatisticsEntry
        MAX-ACCESS	not-accessible
        STATUS	current
        DESCRIPTION    	""
        INDEX          	{ arpInspectStatisticsVid }
        ::= { arpInspectStatisticsTable 1 }

        ArpInspectStatisticsEntry ::=
           SEQUENCE {
        	arpInspectStatisticsVid	INTEGER,
			arpInspectStatisticsReceived	Counter32,       	
			arpInspectStatisticsRequest	Counter32,
			arpInspectStatisticsReply	Counter32,
			arpInspectStatisticsForward	Counter32,
			arpInspectStatisticsDrop	Counter32,
			arpInspectStatisticsClear	EnabledStatus
           }

        arpInspectStatisticsVid OBJECT-TYPE
        SYNTAX  INTEGER
        MAX-ACCESS  read-only
        STATUS  current
        DESCRIPTION
                      	""
        ::= { arpInspectStatisticsEntry 1 }

        arpInspectStatisticsReceived OBJECT-TYPE
        SYNTAX  Counter32
        MAX-ACCESS  read-only
        STATUS  current
        DESCRIPTION
                      	""
        ::= { arpInspectStatisticsEntry 2 }

        arpInspectStatisticsRequest OBJECT-TYPE
        SYNTAX  Counter32
        MAX-ACCESS  read-only
        STATUS  current
        DESCRIPTION
                      	""
        ::= { arpInspectStatisticsEntry 3 }

        arpInspectStatisticsReply OBJECT-TYPE
        SYNTAX  Counter32
        MAX-ACCESS  read-only
        STATUS  current
        DESCRIPTION
                      	""
        ::= { arpInspectStatisticsEntry 4 }	

        arpInspectStatisticsForward OBJECT-TYPE
        SYNTAX  Counter32
        MAX-ACCESS  read-only
        STATUS  current
        DESCRIPTION
                      	""
        ::= { arpInspectStatisticsEntry 5 }		

        arpInspectStatisticsDrop OBJECT-TYPE
        SYNTAX  Counter32
        MAX-ACCESS  read-only
        STATUS  current
        DESCRIPTION
                      	""
        ::= { arpInspectStatisticsEntry 6 }		

        arpInspectStatisticsClear OBJECT-TYPE
        SYNTAX  EnabledStatus
        MAX-ACCESS  read-write
        STATUS  current
        DESCRIPTION
                      	""
        ::= { arpInspectStatisticsEntry 7 } 

-- trTCMSetup
	trTCMSetup OBJECT IDENTIFIER ::= { ves1724-56fanless 52 }

        trTCMState OBJECT-TYPE
        SYNTAX  EnabledStatus
        MAX-ACCESS  read-write
        STATUS  current
        DESCRIPTION
                      	"Two-rate three color marker enabled/disabled for the switch."
        ::= { trTCMSetup 1 }  
        
        trTCMMode OBJECT-TYPE
        SYNTAX  INTEGER {
        	color_aware(0),
        	color_blind(1)
        	}
        MAX-ACCESS  read-write
        STATUS  current
        DESCRIPTION
                      	""
        ::= { trTCMSetup 2 } 

-- trTCMPortTable       
        trTCMPortTable OBJECT-TYPE
        SYNTAX	SEQUENCE OF TrTCMPortEntry
        MAX-ACCESS  not-accessible
        STATUS  current
        DESCRIPTION
                 	""
        ::= { trTCMSetup 3 }
        
	trTCMPortEntry OBJECT-TYPE
        SYNTAX	TrTCMPortEntry
        MAX-ACCESS	not-accessible
        STATUS	current
        DESCRIPTION    	"An entry in trTCMPortTable."
        INDEX          	{ dot1dBasePort }
        ::= { trTCMPortTable 1 }

        TrTCMPortEntry ::=
           SEQUENCE {
       	trTCMPortState	EnabledStatus,
		trTCMPortCIR	INTEGER,     
		trTCMPortPIR	INTEGER,  
		trTCMPortDscpGreen	INTEGER,  
		trTCMPortDscpYellow	INTEGER,  
		trTCMPortDscpRed	INTEGER
           }

        trTCMPortState OBJECT-TYPE
        SYNTAX  EnabledStatus
        MAX-ACCESS  read-create
        STATUS  current
        DESCRIPTION
                      	"Two-rate three color marker enabled/disabled on the port."
        ::= { trTCMPortEntry 1 }
        
        trTCMPortCIR OBJECT-TYPE
        SYNTAX  INTEGER
        MAX-ACCESS  read-write
        STATUS  current
        DESCRIPTION
                      	"Allowed CIR in pkts/s."
        ::= { trTCMPortEntry 2 }
        
        trTCMPortPIR OBJECT-TYPE
        SYNTAX  INTEGER
        MAX-ACCESS  read-write
        STATUS  current
        DESCRIPTION
                      	"Allowed PIR in pkts/s."
        ::= { trTCMPortEntry 3 }
        
        trTCMPortDscpGreen OBJECT-TYPE
        SYNTAX  INTEGER
        MAX-ACCESS  read-write
        STATUS  current
        DESCRIPTION
                      	"0-63"
        ::= { trTCMPortEntry 4 }

        trTCMPortDscpYellow OBJECT-TYPE
        SYNTAX  INTEGER
        MAX-ACCESS  read-write
        STATUS  current
        DESCRIPTION
                      	"0-63"
        ::= { trTCMPortEntry 5 }

        trTCMPortDscpRed OBJECT-TYPE
        SYNTAX  INTEGER
        MAX-ACCESS  read-write
        STATUS  current
        DESCRIPTION
                      	"0-63"
        ::= { trTCMPortEntry 6 }        


-- loopGuardSetup
	loopGuardSetup     	OBJECT IDENTIFIER ::= { ves1724-56fanless 53 }
                               
        loopGuardState OBJECT-TYPE
        SYNTAX  EnabledStatus
        MAX-ACCESS  read-write
        STATUS  current
        DESCRIPTION
                      	""
        ::= { loopGuardSetup 1 }

                                               
-- loopGuardPortTable

        loopGuardPortTable OBJECT-TYPE
        SYNTAX	SEQUENCE OF LoopGuardPortEntry
        MAX-ACCESS  not-accessible
        STATUS  current
        DESCRIPTION
                 	""
        ::= { loopGuardSetup 2 }
        
	loopGuardPortEntry OBJECT-TYPE
        SYNTAX	LoopGuardPortEntry
        MAX-ACCESS	not-accessible
        STATUS	current
        DESCRIPTION    	"An entry in loopGuardPortTable."
        INDEX          	{ dot1dBasePort }
        ::= { loopGuardPortTable 1 }

        LoopGuardPortEntry ::=
           SEQUENCE {
        	loopGuardPortState	EnabledStatus,
        	loopGuardPortMode	INTEGER,
        	loopGuardPortRecoverTime	INTEGER
           }

        loopGuardPortState OBJECT-TYPE
        SYNTAX  EnabledStatus
        MAX-ACCESS  read-write
        STATUS  current
        DESCRIPTION
                      	""
        ::= { loopGuardPortEntry 1 }

	loopGuardPortMode OBJECT-TYPE
        SYNTAX  INTEGER {
        	fix(1),
        	dynamic(2)
        }
        MAX-ACCESS  read-write
        STATUS  current
        DESCRIPTION
                      	"Specify loopguard mode for each port"
        ::= { loopGuardPortEntry 2 }

	loopGuardPortRecoverTime OBJECT-TYPE
        SYNTAX  INTEGER
        MAX-ACCESS  read-write
        STATUS  current
        DESCRIPTION
                      	"recover time to activate port in seconds."
        ::= { loopGuardPortEntry 3 }

-- loopGuardStatusTable

        loopGuardStatusTable OBJECT-TYPE
        SYNTAX	SEQUENCE OF LoopGuardStatusEntry
        MAX-ACCESS  not-accessible
        STATUS  current
        DESCRIPTION
                 	""
        ::= { loopGuardSetup 3 }
        
	loopGuardStatusEntry OBJECT-TYPE
        SYNTAX	LoopGuardStatusEntry
        MAX-ACCESS	not-accessible
        STATUS	current
        DESCRIPTION    	"An entry in loopGuardStatusTable."
        INDEX          	{ dot1dBasePort }
        ::= { loopGuardStatusTable 1 }

        LoopGuardStatusEntry ::=
           SEQUENCE {
        	loopGuardStatusTxPkts	Counter32,
        	loopGuardStatusRxPkts	Counter32,
        	loopGuardStatusBadPkts	Counter32,
        	loopGuardStatusShutdownTime	DisplayString
           }

        loopGuardStatusTxPkts OBJECT-TYPE
        SYNTAX  Counter32
        MAX-ACCESS  read-only
        STATUS  current
        DESCRIPTION
                      	""
        ::= { loopGuardStatusEntry 1 }

		loopGuardStatusRxPkts OBJECT-TYPE
        SYNTAX  Counter32
        MAX-ACCESS  read-only
        STATUS  current
        DESCRIPTION
                      	""
        ::= { loopGuardStatusEntry 2 }

		loopGuardStatusBadPkts OBJECT-TYPE
        SYNTAX  Counter32
        MAX-ACCESS  read-only
        STATUS  current
        DESCRIPTION
                      	""
        ::= { loopGuardStatusEntry 3 }

       	loopGuardStatusShutdownTime  OBJECT-TYPE
        SYNTAX      DisplayString
        MAX-ACCESS      read-only
        STATUS      current
        DESCRIPTION
             			""
       	::= { loopGuardStatusEntry 4 }        
        
-- subnetBasedVlanSetup
	subnetBasedVlanSetup OBJECT IDENTIFIER ::= { ves1724-56fanless 54 }

        subnetBasedVlanState OBJECT-TYPE
        SYNTAX  EnabledStatus
        MAX-ACCESS  read-write
        STATUS  current
        DESCRIPTION
        	"subnet-based vlan feature enabled/disabled for the switch."
        ::= { subnetBasedVlanSetup 1 }

        dhcpVlanOverrideState OBJECT-TYPE
        SYNTAX  EnabledStatus
        MAX-ACCESS  read-write
        STATUS  current
        DESCRIPTION
        	"dhcp vlan override enabled/disabled when subnet-based vlan is enabled."
        ::= { subnetBasedVlanSetup 2 }
             
             
	    subnetBasedVlanTable  OBJECT-TYPE
	    SYNTAX	SEQUENCE OF SubnetBasedVlanEntry 
	    MAX-ACCESS  not-accessible
	    STATUS  current
	    DESCRIPTION
	             	""
	    ::= { subnetBasedVlanSetup 3 }	

		subnetBasedVlanEntry  OBJECT-TYPE
        SYNTAX	SubnetBasedVlanEntry 
        MAX-ACCESS	not-accessible
        STATUS	current
        DESCRIPTION    	"An entry in subnetBasedVlanTable."
        INDEX          	{subnetBasedVlanSrcIp , subnetBasedVlanSrcMaskBit}
        ::= { subnetBasedVlanTable 1 }

        SubnetBasedVlanEntry ::=
           SEQUENCE {
            subnetBasedVlanSrcIp			IpAddress,
            subnetBasedVlanSrcMaskBit		INTEGER,
            subnetBasedVlanName				DisplayString,     
            subnetBasedVlanVid				INTEGER,
            subnetBasedVlanPriority			INTEGER,          
            subnetBasedVlanEntryState		RowStatus            
           }

        subnetBasedVlanSrcIp OBJECT-TYPE
        SYNTAX  IpAddress
        MAX-ACCESS  not-accessible
        STATUS  current
        DESCRIPTION
                      	"source ip for subnet-based vlan entry"
        ::= { subnetBasedVlanEntry 1 }


        subnetBasedVlanSrcMaskBit OBJECT-TYPE
        SYNTAX  INTEGER (1..32)
        MAX-ACCESS  not-accessible
        STATUS  current
        DESCRIPTION
                      	"source ip mask-bits for subnet-based vlan entry"
        ::= { subnetBasedVlanEntry 2 }
             
        subnetBasedVlanName OBJECT-TYPE
        SYNTAX  DisplayString (SIZE (0..32))
        MAX-ACCESS  read-write
        STATUS  current
        DESCRIPTION
                      	"name for subnet-based vlan entry"
        ::= { subnetBasedVlanEntry 3 }
                                                   
        subnetBasedVlanVid OBJECT-TYPE
        SYNTAX  INTEGER (1..4094)
        MAX-ACCESS  read-write
        STATUS  current
        DESCRIPTION
                      	"vid for subnet-based vlan entry"
        ::= { subnetBasedVlanEntry 4 }


        subnetBasedVlanPriority OBJECT-TYPE
        SYNTAX  INTEGER (0..7)
        MAX-ACCESS  read-write
        STATUS  current
        DESCRIPTION
                      	"priority for subnet-based vlan entry"
        ::= { subnetBasedVlanEntry 5 }

        subnetBasedVlanEntryState OBJECT-TYPE
        SYNTAX  RowStatus
        MAX-ACCESS  read-create
        STATUS  current
        DESCRIPTION
                      	""
        ::= { subnetBasedVlanEntry 6 } 
        
             
	    subnetBasedVlanInfoTable  OBJECT-TYPE
	    SYNTAX	SEQUENCE OF SubnetBasedVlanInfoEntry 
	    MAX-ACCESS  not-accessible
	    STATUS  current
	    DESCRIPTION
	             	""
	    ::= { subnetBasedVlanSetup 4 }	

		subnetBasedVlanInfoEntry  OBJECT-TYPE
        SYNTAX	SubnetBasedVlanInfoEntry 
        MAX-ACCESS	not-accessible
        STATUS	current
        DESCRIPTION    	"An entry in subnetBasedVlanInfoTable."
        INDEX          	{subnetBasedVlanInfoSrcIpType , subnetBasedVlanInfoSrcIp , subnetBasedVlanInfoSrcMaskBit}
        ::= { subnetBasedVlanInfoTable 1 }

        SubnetBasedVlanInfoEntry ::=
           SEQUENCE {
            subnetBasedVlanInfoSrcIpType		InetAddressType,
            subnetBasedVlanInfoSrcIp			InetAddress,
            subnetBasedVlanInfoSrcMaskBit		INTEGER, 
            subnetBasedVlanInfoName				DisplayString,     
            subnetBasedVlanInfoVid				INTEGER,
            subnetBasedVlanInfoPriority			INTEGER,          
            subnetBasedVlanInfoEntryState		RowStatus
           }

				subnetBasedVlanInfoSrcIpType OBJECT-TYPE
        SYNTAX  InetAddressType {ipv4(1), ipv6(2)}        
        MAX-ACCESS  not-accessible
        STATUS  current
        DESCRIPTION
                      	"Ip type for subnet-based vlan entry"
        ::= { subnetBasedVlanInfoEntry 1 }  

        subnetBasedVlanInfoSrcIp OBJECT-TYPE
        SYNTAX  InetAddress
        MAX-ACCESS  not-accessible
        STATUS  current
        DESCRIPTION
                      	"source ip of IPv4 or IPv6 for subnet-based vlan entry"
        ::= { subnetBasedVlanInfoEntry 2 }


        subnetBasedVlanInfoSrcMaskBit OBJECT-TYPE
        SYNTAX  INTEGER (1..32)
        MAX-ACCESS  not-accessible
        STATUS  current
        DESCRIPTION
                      	"source ip mask-bits for subnet-based vlan entry"
        ::= { subnetBasedVlanInfoEntry 3 }
             
        subnetBasedVlanInfoName OBJECT-TYPE
        SYNTAX  DisplayString (SIZE (0..32))
        MAX-ACCESS  read-write
        STATUS  current
        DESCRIPTION
                      	"name for subnet-based vlan entry"
        ::= { subnetBasedVlanInfoEntry 4 }
                                                   
        subnetBasedVlanInfoVid OBJECT-TYPE
        SYNTAX  INTEGER (1..4094)
        MAX-ACCESS  read-write
        STATUS  current
        DESCRIPTION
                      	"vid for subnet-based vlan entry"
        ::= { subnetBasedVlanInfoEntry 5 }


        subnetBasedVlanInfoPriority OBJECT-TYPE
        SYNTAX  INTEGER (0..7)
        MAX-ACCESS  read-write
        STATUS  current
        DESCRIPTION
                      	"priority for subnet-based vlan entry"
        ::= { subnetBasedVlanInfoEntry 6 }

        subnetBasedVlanInfoEntryState OBJECT-TYPE
        SYNTAX  RowStatus
        MAX-ACCESS  read-create
        STATUS  current
        DESCRIPTION
                      	""
        ::= { subnetBasedVlanInfoEntry 7 } 
        
        
--  MAC Authentication
				 macAuthenticationSetup      OBJECT IDENTIFIER ::= { ves1724-56fanless 55 }
                               
        macAuthenticationState OBJECT-TYPE
        SYNTAX  EnabledStatus
        MAX-ACCESS  read-write
        STATUS  current
        DESCRIPTION
                       ""
        ::= { macAuthenticationSetup 1 }
 
        macAuthenticationNamePrefix OBJECT-TYPE
        SYNTAX  DisplayString
        MAX-ACCESS  read-write
        STATUS  current
        DESCRIPTION
                       ""
        ::= { macAuthenticationSetup 2 }
 
        macAuthenticationPassword OBJECT-TYPE
        SYNTAX  DisplayString
        MAX-ACCESS  read-write
        STATUS  current
        DESCRIPTION
                       ""
        ::= { macAuthenticationSetup 3 }
 
        macAuthenticationTimeout OBJECT-TYPE
        SYNTAX  INTEGER
        MAX-ACCESS  read-write
        STATUS  current
        DESCRIPTION
                       ""
        ::= { macAuthenticationSetup 4 }
                                               
-- macAuthenticationPortTable
 
	macAuthenticationPortTable OBJECT-TYPE
        SYNTAX SEQUENCE OF MacAuthenticationPortEntry
        MAX-ACCESS  not-accessible
        STATUS  current
        DESCRIPTION
                  ""
        ::= { macAuthenticationSetup 5 }
        
 	macAuthenticationPortEntry OBJECT-TYPE
        SYNTAX MacAuthenticationPortEntry
        MAX-ACCESS not-accessible
        STATUS current
        DESCRIPTION     "An entry in macAuthenticationPortTable."
        INDEX           { dot1dBasePort }
        ::= { macAuthenticationPortTable 1 }
 
		MacAuthenticationPortEntry ::=
		SEQUENCE {
			macAuthenticationPortState EnabledStatus
		}
 
        macAuthenticationPortState OBJECT-TYPE
        SYNTAX  EnabledStatus
        MAX-ACCESS  read-write
        STATUS  current
        DESCRIPTION
                       ""
        ::= { macAuthenticationPortEntry 1 }

-- MSTP  
--****************************************************************
-- TEXTUAL-CONVENTIONs
--****************************************************************
		MstiOrCistInstanceIndex ::= TEXTUAL-CONVENTION
      		STATUS       current
    		DESCRIPTION
	            "This textual convention is an extension of the
	            MstiInstanceIndex convention.  This extension permits the
	            additional value of zero, which means Common and Internal
	            Spanning Tree (CIST)."
            SYNTAX      Integer32 (0..16) 
            
        mstp            OBJECT IDENTIFIER ::= { ves1724-56fanless 56 }    
-- mstpGen group reflects configurations/statuses
-- the Bridge as a unit  
	    mstpGen			OBJECT IDENTIFIER ::= { mstp 1}  
	    
        mstpGenState		OBJECT-TYPE
        SYNTAX    EnabledStatus
        MAX-ACCESS    read-write
        STATUS    current
        DESCRIPTION
        "Enabled/disabled on the mrstp bridge."
        ::= { mstpGen 1 }
        
        mstpGenCfgIdName    OBJECT-TYPE
        SYNTAX    DisplayString
        MAX-ACCESS    read-write
        STATUS    current 
        DESCRIPTION 
        "The configuration name that identifies the MST
         region and is used as one of the inputs in the 
         computation of the MST Configuration Identifier." 
        REFERENCE
            "12.12.3.4.2.b)"
        ::= { mstpGen 2 }
        
        mstpGenCfgIdRevLevel OBJECT-TYPE
        SYNTAX    Integer32
        MAX-ACCESS    read-write
        STATUS    current 
        DESCRIPTION 
        "This object identifies the MST revision that
         identifies the MST region and is used as one
         of the inputs in the computation of the MST 
         configuration Identifier."
        REFERENCE
            "12.12.3.4.2.c)"
        ::= { mstpGen 3 }
	    
	    
	   mstpGenCfgIdCfgDigest  OBJECT-TYPE
            SYNTAX    OCTET STRING(SIZE(16))
            MAX-ACCESS    read-only
            STATUS    current
            DESCRIPTION
              "Configuration Digest."
            REFERENCE
               "12.12.3.3.3.a.4"
            ::= { mstpGen 4 }
	    
	    mstpGenHelloTime  OBJECT-TYPE
	        SYNTAX    Timeout (1..10)
            MAX-ACCESS    read-write
            STATUS    current 
            DESCRIPTION
            ""                  
            ::= { mstpGen 5 }
       
        mstpGenMaxAge    OBJECT-TYPE
            SYNTAX  Timeout (6..40)
            MAX-ACCESS  read-write
            STATUS  current 
            DESCRIPTION
            "" 
            ::= { mstpGen 6 }
         
        mstpGenForwardDelay   OBJECT-TYPE 
            SYNTAX  Timeout (4..30)
            MAX-ACCESS  read-write
            STATUS  current
            DESCRIPTION
            ""
            ::= {mstpGen 7}
        
        mstpGenMaxHops  OBJECT-TYPE
            SYNTAX      Integer32 (1..255)
            MAX-ACCESS  read-write
            STATUS      current
            DESCRIPTION
               "13.22.f)"
            ::= { mstpGen 8 }
	    
	mstpGenCistRootPathCost  OBJECT-TYPE
            SYNTAX      Integer32
            MAX-ACCESS  read-only
            STATUS      current
            DESCRIPTION
	    "."
            ::= { mstpGen 9 }
	    
	mstpGenCistRootBrid  OBJECT-TYPE
            SYNTAX      OCTET STRING(SIZE(8))
            MAX-ACCESS  read-only
            STATUS      current
            DESCRIPTION
            "."
            ::= { mstpGen 10 }
-- MSTP MAP TABLE
        mstMapTable        OBJECT-TYPE
            SYNTAX      SEQUENCE OF MstMapEntry
            MAX-ACCESS  not-accessible
            STATUS      current
            DESCRIPTION
               "This table contains one entry for each instance of MSTP."
            ::= { mstp 20 }	
         
        mstMapEntry        OBJECT-TYPE
            SYNTAX      MstMapEntry
            MAX-ACCESS  not-accessible
            STATUS      current
            DESCRIPTION
               "A conceptual row containing the status of the MSTP instance."
            INDEX  { mstMapIndex }
            ::= { mstMapTable 1 }
        
        MstMapEntry ::= SEQUENCE {
                   mstMapIndex             MstiOrCistInstanceIndex,
                   mstMapVlans1k           OCTET STRING,
                   mstMapVlans2k           OCTET STRING,
                   mstMapVlans3k           OCTET STRING,
                   mstMapVlans4k           OCTET STRING,
                   mstMapRowStatus         RowStatus
        }
        
        mstMapIndex    OBJECT-TYPE
            SYNTAX      MstiOrCistInstanceIndex
            MAX-ACCESS  not-accessible
            STATUS      current
            DESCRIPTION
            "Uniquely identifies an instance. The entry of this table with index 0
            presents always, represents CIST. When SET operation "
            ::= { mstMapEntry 1 }  
        
        mstMapVlans1k      OBJECT-TYPE
            SYNTAX      OCTET STRING (SIZE (0..128))
            MAX-ACCESS  read-write
            STATUS      current
            DESCRIPTION
           "A string of octets containing one bit per VLAN. The
            first octet corresponds to VLANs with VlanIndex values
            1 through 8; the second octet to VLANs 9 through
            16 etc.  The most significant bit of each octet
            corresponds to the lowest VlanIndex value in that octet.

            For each VLAN that is mapped to this MSTP instance,
            the bit corresponding to that VLAN is set to '1'.
            Empty (zero) most significant octes are not current."
            ::= { mstMapEntry 2 } 
        
        mstMapVlans2k      OBJECT-TYPE
            SYNTAX  OCTET STRING (SIZE (0..128))
            MAX-ACCESS  read-write
            STATUS  current
            DESCRIPTION
            "A string of octets containing one bit per VLAN for
             VLANS with VlanIndex values 1024 through 2047. The
             first octet corresponds to VLANs with VlanIndex values
             1024 through 1031; the second octet to VLANs 1032
             through 1039 etc.  The most significant bit of each
             octet corresponds to the lowest VlanIndex value in that
             octet.
             
             For each VLAN that is mapped to this MSTP instance,
             the bit corresponding to that VLAN is set to '1'.

             Empty (zero) most significant octes are not current."
             ::= { mstMapEntry 3 }
        
        mstMapVlans3k      OBJECT-TYPE
            SYNTAX      OCTET STRING (SIZE (0..128))
            MAX-ACCESS  read-write
            STATUS      current
            DESCRIPTION
            "A string of octets containing one bit per VLAN for
             VLANS with VlanIndex values 2048 through 3071. The
             first octet corresponds to VLANs with VlanIndex values
             of 2048 through 2055; the second octet to VLANs 2056
             through 2063 etc.  The most significant bit of each
             octet corresponds to the lowest VlanIndex value in that
             octet.

             For each VLAN that is mapped to this MSTP instance,
             the bit corresponding to that VLAN is set to '1'.

             Empty (zero) most significant octes are not current."
             ::= { mstMapEntry 4 }
        
        mstMapVlans4k      OBJECT-TYPE
            SYNTAX      OCTET STRING (SIZE (0..128))
            MAX-ACCESS  read-write
            STATUS      current
            DESCRIPTION
            "A string of octets containing one bit per VLAN for
             VLANS with VlanIndex values 3072 through 4095. The
             first octet corresponds to VLANs with VlanIndex values
             3072 through 3079; the second octet to VLANs 3080
             through 3087 etc.  The most significant bit of each
             octet corresponds to the lowest VlanIndex value in that
             octet.
        
             For each VLAN that is mapped to this MSTP instance,
             the bit corresponding to that VLAN is set to '1'.
           
             Empty (zero) most significant octes are not current."
             ::= { mstMapEntry 5 }   
        
        mstMapRowStatus    OBJECT-TYPE
            SYNTAX  RowStatus
            MAX-ACCESS  read-create
            STATUS  current
            DESCRIPTION 
            ""
        ::= {  mstMapEntry 6 }
    	
-- MSTP Vlan Table, map vlan to msti
        mstVlanTable       OBJECT-TYPE
            SYNTAX      SEQUENCE OF MstVlanEntry
            MAX-ACCESS  not-accessible
            STATUS      current
            DESCRIPTION
            "This table contains one entry for each VlanId."
            ::= { mstp 30 } 
        
        mstVlanEntry  OBJECT-TYPE
            SYNTAX      MstVlanEntry
            MAX-ACCESS      not-accessible
            STATUS      current
            DESCRIPTION
                "Information regarding the instance to which each Vlan is mapped."
            INDEX  { mstVlanIndex }
            ::= { mstVlanTable 1 }
           
        MstVlanEntry ::= SEQUENCE {
              mstVlanIndex         INTEGER,
              mstVlanMstIndex      MstiOrCistInstanceIndex
        }
        
        
        mstVlanIndex     OBJECT-TYPE
            SYNTAX        INTEGER(1..4094)
            MAX-ACCESS        not-accessible
            STATUS        current
            DESCRIPTION
                "The VlanId for which this entry contains the instance mapped."
            ::= { mstVlanEntry 1 } 
         
        mstVlanMstIndex    OBJECT-TYPE
             SYNTAX      MstiOrCistInstanceIndex
             MAX-ACCESS  read-only
             STATUS      current
             DESCRIPTION
                 "An integer with values ranging from 0 to 64 that identify a 
                      the CIST/MSTI instance to which this VLAN is mapped" 
             ::= { mstVlanEntry 2 }   
-- MSTP Port Table, information for all instance of a port
        mstpPortTable      OBJECT-TYPE
            SYNTAX      SEQUENCE OF MstpPortEntry
            MAX-ACCESS  not-accessible
            STATUS      current
            DESCRIPTION
                "A table that contains generic information about
                every port that is associated with this bridge."
            ::= { mstp 40 }
        
        mstpPortEntry      OBJECT-TYPE
            SYNTAX  MstpPortEntry
            MAX-ACCESS  not-accessible
            STATUS  current
            DESCRIPTION
            "A list of information for each port of the
            bridge."
            INDEX  { mstpPortIndex }
            ::= { mstpPortTable 1 }
        
        MstpPortEntry ::= SEQUENCE {
             mstpPortIndex                    INTEGER,
             mstpPortOperEdgePort             TruthValue,
             mstpPortOperPointToPointMAC      TruthValue
        }
        
        mstpPortIndex	OBJECT-TYPE
            SYNTAX    INTEGER (1..65535)
            MAX-ACCESS  not-accessible
            STATUS      current
            DESCRIPTION
            "A unique value, greater than zero, for each Port.
            The value for each interface sub-layer
            must remain constant at least from one re-initialization
            of the entity's network management system to the next re-
            initialization."
            ::= { mstpPortEntry 1 }
        
        mstpPortOperEdgePort    OBJECT-TYPE
            SYNTAX    TruthValue
            MAX-ACCESS    read-only
            STATUS    current 
            DESCRIPTION
            ""
            REFERENCE   ""
            ::= { mstpPortEntry 2 }
        
        mstpPortOperPointToPointMAC    OBJECT-TYPE
            SYNTAX    TruthValue
            MAX-ACCESS    read-only
            STATUS    current
            DESCRIPTION
            ""
            REFERENCE    ""
            ::= {mstpPortEntry 3} 
-- MSTP Xst Table, Cist/Mst status/setting
        mstpXstTable  OBJECT-TYPE
              SYNTAX      SEQUENCE OF MstpXstEntry
              MAX-ACCESS  not-accessible
              STATUS      current
              DESCRIPTION
                "."
              ::= { mstp 50 }

        mstpXstEntry OBJECT-TYPE
              SYNTAX      MstpXstEntry
              MAX-ACCESS  not-accessible
              STATUS      current
              DESCRIPTION
                "."
              INDEX { mstpXstId }
              ::= { mstpXstTable 1 }  
        
       MstpXstEntry ::= SEQUENCE {
	           mstpXstId                      MstiOrCistInstanceIndex,
	           mstpXstBridgePriority          Integer32,
	           mstpXstBridgeId                BridgeId,
	           mstpXstInternalRootCost        Integer32,
	           mstpXstRootPort                INTEGER,
	           mstpXstTimeSinceTopologyChange TimeTicks,
	           mstpXstTopologyChangesCount    Counter32
       }
       
       mstpXstId   OBJECT-TYPE
           SYNTAX      MstiOrCistInstanceIndex
           MAX-ACCESS      read-only
           STATUS      current
           DESCRIPTION
             "0 means CIST."
           ::= { mstpXstEntry 1 }
       
       mstpXstBridgePriority   OBJECT-TYPE
           SYNTAX      Integer32 (0..61440)
           MAX-ACCESS  read-write
           STATUS      current
           DESCRIPTION
              "Bridge priority, in steps of 4096."
           DEFVAL       { 32768 }
           ::= { mstpXstEntry 2 } 
       
       mstpXstBridgeId   OBJECT-TYPE
           SYNTAX      BridgeId
           MAX-ACCESS      read-only
           STATUS      current
           DESCRIPTION
             "."
           ::= { mstpXstEntry 3 }   
        
        
       mstpXstInternalRootCost     OBJECT-TYPE
           SYNTAX      Integer32
           MAX-ACCESS      read-only
           STATUS      current
           DESCRIPTION
             "."
           ::= { mstpXstEntry 4 }

       mstpXstRootPort      OBJECT-TYPE
           SYNTAX      INTEGER 
           MAX-ACCESS      read-only
           STATUS      current
           DESCRIPTION
           "."
           ::= { mstpXstEntry 5 }
       
       mstpXstTimeSinceTopologyChange  OBJECT-TYPE
           SYNTAX      TimeTicks
           MAX-ACCESS      read-only
           STATUS      current
           DESCRIPTION
             "."
           ::= { mstpXstEntry 6 }

       mstpXstTopologyChangesCount     OBJECT-TYPE
           SYNTAX      Counter32
           MAX-ACCESS      read-only
           STATUS      current
           DESCRIPTION
             "."
           ::= { mstpXstEntry 7 }  
-- MSTP Xst Port Table, Cist/Mst Port status/setting
       mstpXstPortTable    OBJECT-TYPE
           SYNTAX  SEQUENCE OF MstpXstPortEntry
           MAX-ACCESS  not-accessible
           STATUS  current
           DESCRIPTION
             "."
           ::= { mstp 60 }
       
       mstpXstPortEntry    OBJECT-TYPE
           SYNTAX  MstpXstPortEntry
           MAX-ACCESS  not-accessible
           STATUS  current
           DESCRIPTION
             "."
           REFERENCE
             "."
           INDEX  { mstpXstPortXstId, mstpXstPortIndex }
           ::= { mstpXstPortTable 1 }
       
        
        MstpXstPortEntry ::=
        SEQUENCE {
         	mstpXstPortXstId                 MstiOrCistInstanceIndex,
          	mstpXstPortIndex                 INTEGER,
          	mstpXstPortEnable                EnabledStatus, 
          	mstpXstPortPriority              Integer32,
          	mstpXstPortPathCost              INTEGER,   
          	mstpXstPortState				 INTEGER,
          	mstpXstPortDesignatedRoot        BridgeId,
          	mstpXstPortDesignatedCost        Integer32,
          	mstpXstPortDesignatedBridge      BridgeId,
          	mstpXstPortDesignatedPort        INTEGER
        }
        
        mstpXstPortXstId     OBJECT-TYPE
            SYNTAX      MstiOrCistInstanceIndex
            MAX-ACCESS      not-accessible
            STATUS      current
            DESCRIPTION
              "0 means CIST."
            ::= { mstpXstPortEntry 1 }

        mstpXstPortIndex     OBJECT-TYPE
            SYNTAX      INTEGER(1..65535)
            MAX-ACCESS      read-only
            STATUS      current
            DESCRIPTION
              "The value of mstpPortIndex of the Port
              in mstpPortTable."
            ::= { mstpXstPortEntry 2 }
        
        
        mstpXstPortEnable     OBJECT-TYPE
            SYNTAX      EnabledStatus
            MAX-ACCESS      read-write
            STATUS      current
            DESCRIPTION
              "."
            ::= { mstpXstPortEntry 3 }
         
         mstpXstPortPriority              OBJECT-TYPE 
             SYNTAX      Integer32 (0..255)
             MAX-ACCESS      read-write
             STATUS      current
             DESCRIPTION
               "Port priority, in steps of 16."
             DEFVAL       { 128 }
             ::= { mstpXstPortEntry 4 }
        
         mstpXstPortPathCost              OBJECT-TYPE 
             SYNTAX      INTEGER (1..65535)
             MAX-ACCESS      read-write
             STATUS      current
             DESCRIPTION
               "."
             ::= { mstpXstPortEntry 5 }

         mstpXstPortState                 OBJECT-TYPE 
             SYNTAX      INTEGER {
               disabled(0),
               discarding(1),
               learning(2),
               forwarding(3),
               unknown(4)
             }
             MAX-ACCESS      read-only
             STATUS      current
             DESCRIPTION
               "."
             ::= { mstpXstPortEntry 6 }
         
         mstpXstPortDesignatedRoot        OBJECT-TYPE 
              SYNTAX      BridgeId
              MAX-ACCESS      read-only
              STATUS      current
              DESCRIPTION
              "."
              ::= { mstpXstPortEntry 7 }
         
         mstpXstPortDesignatedCost        OBJECT-TYPE
             SYNTAX      Integer32
             MAX-ACCESS      read-only
             STATUS      current
             DESCRIPTION
             "."
             ::= { mstpXstPortEntry 8 }
         
         mstpXstPortDesignatedBridge      OBJECT-TYPE
             SYNTAX      BridgeId
             MAX-ACCESS      read-only
             STATUS      current
             DESCRIPTION
             "."
             ::= { mstpXstPortEntry 9 }
        
         mstpXstPortDesignatedPort      OBJECT-TYPE
             SYNTAX      INTEGER
             MAX-ACCESS      read-only
             STATUS      current
             DESCRIPTION
             "."
             ::= { mstpXstPortEntry 10 }  
--MSTP Traps 
 	     mstpNotifications     	OBJECT IDENTIFIER ::= { mstp 70 }              
	
	     mstpNewRoot NOTIFICATION-TYPE
         OBJECTS {
                mstpXstId
         }
         STATUS  current
         DESCRIPTION
          ""
         ::= { mstpNotifications 1 }
      
         mstpTopologyChange NOTIFICATION-TYPE
         OBJECTS {
                mstpXstId
         }
         STATUS  current
         DESCRIPTION
          ""
         ::= { mstpNotifications 2 }
       
--  radiusServerSetup
				radiusServerSetup     	OBJECT IDENTIFIER ::= { ves1724-56fanless 57 }

        radiusAuthServerSetup OBJECT IDENTIFIER ::= { radiusServerSetup 1 }
        
        radiusAuthServerMode OBJECT-TYPE
        SYNTAX  INTEGER{
        		index_priority(1),
						round_robin(2)
        }
        MAX-ACCESS  read-write
        STATUS  current
        DESCRIPTION
                      	""
        ::= { radiusAuthServerSetup 1 }

        radiusAuthServerTimeout OBJECT-TYPE
        SYNTAX  INTEGER
        MAX-ACCESS  read-write
        STATUS  current
        DESCRIPTION
                      	""
        ::= { radiusAuthServerSetup 2 }

-- radiusAuthServerTable
        radiusAuthServerTable OBJECT-TYPE
        SYNTAX	SEQUENCE OF RadiusAuthServerEntry
        MAX-ACCESS  not-accessible
        STATUS  current
        DESCRIPTION
                 	""
        ::= { radiusAuthServerSetup 3 }
        
	radiusAuthServerEntry OBJECT-TYPE
        SYNTAX	RadiusAuthServerEntry
        MAX-ACCESS	not-accessible
        STATUS	current
        DESCRIPTION    	"An entry in radiusAuthServerTable."
        INDEX          	{ radiusAuthServerIndex }
        ::= { radiusAuthServerTable 1 }

        RadiusAuthServerEntry ::=
           SEQUENCE {
        	radiusAuthServerIndex		INTEGER,
        	radiusAuthServerIpAddr		IpAddress,
        	radiusAuthServerUdpPort		INTEGER,
        	radiusAuthServerSharedSecret	DisplayString,
        	radiusAuthServerIpAddressType	InetAddressType,
        	radiusAuthServerIpAddress		InetAddress
           }

        radiusAuthServerIndex OBJECT-TYPE
        SYNTAX  INTEGER
        MAX-ACCESS  not-accessible
        STATUS  current
        DESCRIPTION
                      	""
        ::= { radiusAuthServerEntry 1 }

        radiusAuthServerIpAddr OBJECT-TYPE
        SYNTAX  IpAddress
        MAX-ACCESS  read-write
        STATUS  current
        DESCRIPTION
                     	"IPv4 only"
        ::= { radiusAuthServerEntry 2 }

        radiusAuthServerUdpPort OBJECT-TYPE
        SYNTAX  INTEGER
        MAX-ACCESS  read-write
        STATUS  current
        DESCRIPTION
                     	""
        ::= { radiusAuthServerEntry 3 }

        radiusAuthServerSharedSecret OBJECT-TYPE
        SYNTAX  DisplayString
        MAX-ACCESS  read-write
        STATUS  current
        DESCRIPTION
                     	""
        ::= { radiusAuthServerEntry 4 }

        radiusAuthServerIpAddressType OBJECT-TYPE
        SYNTAX  InetAddressType { ipv4(1), ipv6(2) }
        MAX-ACCESS  read-only
        STATUS  current
        DESCRIPTION
                     	""
        ::= { radiusAuthServerEntry 5 }
        
        radiusAuthServerIpAddress OBJECT-TYPE
        SYNTAX  InetAddress
        MAX-ACCESS  read-write
        STATUS  current
        DESCRIPTION
                     	""
        ::= { radiusAuthServerEntry 6 }
        
        radiusAcctServerSetup OBJECT IDENTIFIER ::= { radiusServerSetup 2 }
        
        radiusAcctServerTimeout OBJECT-TYPE
        SYNTAX  INTEGER
        MAX-ACCESS  read-write
        STATUS  current
        DESCRIPTION
                      	""
        ::= { radiusAcctServerSetup 1 }

-- radiusAcctServerTable
        radiusAcctServerTable OBJECT-TYPE
        SYNTAX	SEQUENCE OF RadiusAcctServerEntry
        MAX-ACCESS  not-accessible
        STATUS  current
        DESCRIPTION
                 	""
        ::= { radiusAcctServerSetup 2 }
        
	radiusAcctServerEntry OBJECT-TYPE
        SYNTAX	RadiusAcctServerEntry
        MAX-ACCESS	not-accessible
        STATUS	current
        DESCRIPTION    	"An entry in radiusAcctServerTable."
        INDEX          	{ radiusAcctServerIndex }
        ::= { radiusAcctServerTable 1 }

        RadiusAcctServerEntry ::=
           SEQUENCE {
        	radiusAcctServerIndex		INTEGER,
        	radiusAcctServerIpAddr		IpAddress,
        	radiusAcctServerUdpPort		INTEGER,
        	radiusAcctServerSharedSecret	DisplayString,
        	radiusAcctServerIpAddressType	InetAddressType,
        	radiusAcctServerIpAddress		InetAddress
           }

        radiusAcctServerIndex OBJECT-TYPE
        SYNTAX  INTEGER
        MAX-ACCESS  not-accessible
        STATUS  current
        DESCRIPTION
                      	""
        ::= { radiusAcctServerEntry 1 }

        radiusAcctServerIpAddr OBJECT-TYPE
        SYNTAX  IpAddress
        MAX-ACCESS  read-write
        STATUS  current
        DESCRIPTION
                     	"IPv4 only"
        ::= { radiusAcctServerEntry 2 }

        radiusAcctServerUdpPort OBJECT-TYPE
        SYNTAX  INTEGER
        MAX-ACCESS  read-write
        STATUS  current
        DESCRIPTION
                     	""
        ::= { radiusAcctServerEntry 3 }

        radiusAcctServerSharedSecret OBJECT-TYPE
        SYNTAX  DisplayString
        MAX-ACCESS  read-write
        STATUS  current
        DESCRIPTION
                     	""
        ::= { radiusAcctServerEntry 4 }
        
        radiusAcctServerIpAddressType OBJECT-TYPE
        SYNTAX  InetAddressType { ipv4(1), ipv6(2) }
        MAX-ACCESS  read-only
        STATUS  current
        DESCRIPTION
                     	""
        ::= { radiusAcctServerEntry 5 }
        
        radiusAcctServerIpAddress OBJECT-TYPE
        SYNTAX  InetAddress
        MAX-ACCESS  read-write
        STATUS  current
        DESCRIPTION
                     	""
        ::= { radiusAcctServerEntry 6 }

--  tacacsServerSetup
	tacacsServerSetup     	OBJECT IDENTIFIER ::= { ves1724-56fanless 58 }

        tacacsAuthServerSetup OBJECT IDENTIFIER ::= { tacacsServerSetup 1 }
        
        tacacsAuthServerMode OBJECT-TYPE
        SYNTAX  INTEGER{
        		index_priority(1),
		round_robin(2)
        }
        MAX-ACCESS  read-write
        STATUS  current
        DESCRIPTION
                      	""
        ::= { tacacsAuthServerSetup 1 }

        tacacsAuthServerTimeout OBJECT-TYPE
        SYNTAX  INTEGER
        MAX-ACCESS  read-write
        STATUS  current
        DESCRIPTION
                      	""
        ::= { tacacsAuthServerSetup 2 }

-- tacacsAuthServerTable
        tacacsAuthServerTable OBJECT-TYPE
        SYNTAX	SEQUENCE OF TacacsAuthServerEntry
        MAX-ACCESS  not-accessible
        STATUS  current
        DESCRIPTION
                 	""
        ::= { tacacsAuthServerSetup 3 }
        
	tacacsAuthServerEntry OBJECT-TYPE
        SYNTAX	TacacsAuthServerEntry
        MAX-ACCESS	not-accessible
        STATUS	current
        DESCRIPTION    	"An entry in tacacsAuthServerTable."
        INDEX          	{ tacacsAuthServerIndex }
        ::= { tacacsAuthServerTable 1 }

        TacacsAuthServerEntry ::=
           SEQUENCE {
        	tacacsAuthServerIndex		INTEGER,
        	tacacsAuthServerIpAddr		IpAddress,
        	tacacsAuthServerTcpPort		INTEGER,
        	tacacsAuthServerSharedSecret	DisplayString,
        	tacacsAuthServerIpAddressType		InetAddressType,
        	tacacsAuthServerIpAddress	InetAddress
           }

        tacacsAuthServerIndex OBJECT-TYPE
        SYNTAX  INTEGER
        MAX-ACCESS  not-accessible
        STATUS  current
        DESCRIPTION
                      	""
        ::= { tacacsAuthServerEntry 1 }

        tacacsAuthServerIpAddr OBJECT-TYPE
        SYNTAX  IpAddress
        MAX-ACCESS  read-write
        STATUS  current
        DESCRIPTION
                     	"IPv4 only"
        ::= { tacacsAuthServerEntry 2 }

        tacacsAuthServerTcpPort OBJECT-TYPE
        SYNTAX  INTEGER
        MAX-ACCESS  read-write
        STATUS  current
        DESCRIPTION
                     	""
        ::= { tacacsAuthServerEntry 3 }

        tacacsAuthServerSharedSecret OBJECT-TYPE
        SYNTAX  DisplayString
        MAX-ACCESS  read-write
        STATUS  current
        DESCRIPTION
                     	""
        ::= { tacacsAuthServerEntry 4 }

        tacacsAuthServerIpAddressType OBJECT-TYPE
        SYNTAX  InetAddressType { ipv4(1), ipv6(2) }
        MAX-ACCESS  read-only
        STATUS  current
        DESCRIPTION
                     	""
        ::= { tacacsAuthServerEntry 5 }
        
        tacacsAuthServerIpAddress OBJECT-TYPE
        SYNTAX  InetAddress
        MAX-ACCESS  read-write
        STATUS  current
        DESCRIPTION
                     	""
        ::= { tacacsAuthServerEntry 6 }
        
        tacacsAcctServerSetup OBJECT IDENTIFIER ::= { tacacsServerSetup 2 }

        tacacsAcctServerTimeout OBJECT-TYPE
        SYNTAX  INTEGER
        MAX-ACCESS  read-write
        STATUS  current
        DESCRIPTION
                      	""
        ::= { tacacsAcctServerSetup 1 }

-- tacacsAcctServerTable
        tacacsAcctServerTable OBJECT-TYPE
        SYNTAX	SEQUENCE OF TacacsAcctServerEntry
        MAX-ACCESS  not-accessible
        STATUS  current
        DESCRIPTION
                 	""
        ::= { tacacsAcctServerSetup 2 }
        
	tacacsAcctServerEntry OBJECT-TYPE
        SYNTAX	TacacsAcctServerEntry
        MAX-ACCESS	not-accessible
        STATUS	current
        DESCRIPTION    	"An entry in tacacsAcctServerTable."
        INDEX          	{ tacacsAcctServerIndex }
        ::= { tacacsAcctServerTable 1 }

        TacacsAcctServerEntry ::=
           SEQUENCE {
        	tacacsAcctServerIndex		INTEGER,
        	tacacsAcctServerIpAddr		IpAddress,
        	tacacsAcctServerTcpPort		INTEGER,
        	tacacsAcctServerSharedSecret	DisplayString,
        	tacacsAcctServerIpAddressType		InetAddressType,
        	tacacsAcctServerIpAddress	InetAddress
           }

        tacacsAcctServerIndex OBJECT-TYPE
        SYNTAX  INTEGER
        MAX-ACCESS  not-accessible
        STATUS  current
        DESCRIPTION
                      	""
        ::= { tacacsAcctServerEntry 1 }

        tacacsAcctServerIpAddr OBJECT-TYPE
        SYNTAX  IpAddress
        MAX-ACCESS  read-write
        STATUS  current
        DESCRIPTION
                     	"IPv4 only"
        ::= { tacacsAcctServerEntry 2 }

        tacacsAcctServerTcpPort OBJECT-TYPE
        SYNTAX  INTEGER
        MAX-ACCESS  read-write
        STATUS  current
        DESCRIPTION
                     	""
        ::= { tacacsAcctServerEntry 3 }

        tacacsAcctServerSharedSecret OBJECT-TYPE
        SYNTAX  DisplayString
        MAX-ACCESS  read-write
        STATUS  current
        DESCRIPTION
                     	""
        ::= { tacacsAcctServerEntry 4 }
        
        tacacsAcctServerIpAddressType OBJECT-TYPE
        SYNTAX  InetAddressType { ipv4(1), ipv6(2) }
        MAX-ACCESS  read-only
        STATUS  current
        DESCRIPTION
                     	""
        ::= { tacacsAcctServerEntry 5 }
        
        tacacsAcctServerIpAddress OBJECT-TYPE
        SYNTAX  InetAddress
        MAX-ACCESS  read-write
        STATUS  current
        DESCRIPTION
                     	""
        ::= { tacacsAcctServerEntry 6 }

--  aaaSetup
	aaaSetup     	OBJECT IDENTIFIER ::= { ves1724-56fanless 59 }

        authenticationSetup OBJECT IDENTIFIER ::= { aaaSetup 1 }

-- authenticationTypeTable
        authenticationTypeTable OBJECT-TYPE
        SYNTAX	SEQUENCE OF AuthenticationTypeEntry
        MAX-ACCESS  not-accessible
        STATUS  current
        DESCRIPTION
                 	""
        ::= { authenticationSetup 1 }
        
	authenticationTypeEntry OBJECT-TYPE
        SYNTAX	AuthenticationTypeEntry
        MAX-ACCESS	not-accessible
        STATUS	current
        DESCRIPTION    	"An entry in authenticationTypeTable."
        INDEX          	{ authenticationTypeName }
        ::= { authenticationTypeTable 1 }

        AuthenticationTypeEntry ::=
           SEQUENCE {
        	authenticationTypeName	DisplayString,
        	authenticationTypeMethodList	OCTET STRING
           }

        authenticationTypeName OBJECT-TYPE
        SYNTAX  DisplayString
        MAX-ACCESS  read-only
        STATUS  current
        DESCRIPTION
                      	""
        ::= { authenticationTypeEntry 1 }

        authenticationTypeMethodList OBJECT-TYPE
        SYNTAX  OCTET STRING
        MAX-ACCESS  read-write
        STATUS  current
        DESCRIPTION
                     	"Enable-local: 1, Login-local: 2, radius: 3, tacacs+: 4"
        ::= { authenticationTypeEntry 2 }

    accountingSetup      	OBJECT IDENTIFIER ::= { aaaSetup 2 }      
	accountingUpdatePeriod OBJECT-TYPE
	SYNTAX  Integer32
	MAX-ACCESS  read-write
	STATUS  current
	DESCRIPTION
                      	""
	::= { accountingSetup 1 }		
	
-- accountingTypeTable
        accountingTypeTable OBJECT-TYPE
        SYNTAX	SEQUENCE OF AccountingTypeEntry
        MAX-ACCESS  not-accessible
        STATUS  current
        DESCRIPTION
                 	""
        ::= { accountingSetup 2 }
        
	accountingTypeEntry OBJECT-TYPE
        SYNTAX	AccountingTypeEntry
        MAX-ACCESS	not-accessible
        STATUS	current
        DESCRIPTION    	"An entry in accountingTypeTable."
        INDEX          	{ accountingTypeName }
        ::= { accountingTypeTable 1 }

        AccountingTypeEntry ::=
           SEQUENCE {
         	accountingTypeName		DisplayString,
         	accountingTypeActive		EnabledStatus,	         	
         	accountingTypeBroadcast		EnabledStatus,	         	
         	accountingTypeMode		INTEGER,
         	accountingTypeMethod		INTEGER,
         	accountingTypePrivilege		INTEGER        	
           }

	accountingTypeName OBJECT-TYPE
	SYNTAX  DisplayString
	MAX-ACCESS  read-only
	STATUS  current
	DESCRIPTION
                      	""
	::= { accountingTypeEntry 1 }

	accountingTypeActive OBJECT-TYPE
	SYNTAX  EnabledStatus
	MAX-ACCESS  read-write
	STATUS  current
	DESCRIPTION
                      	""
	::= { accountingTypeEntry 2 }

	accountingTypeBroadcast OBJECT-TYPE
	SYNTAX  EnabledStatus
	MAX-ACCESS  read-write
	STATUS  current
	DESCRIPTION
                      	""
	::= { accountingTypeEntry 3 }

	accountingTypeMode OBJECT-TYPE
	SYNTAX  INTEGER{
		not_available(255),
        		start_stop(1),
		stop_only(2)		
	}
	MAX-ACCESS  read-write
	STATUS  current
	DESCRIPTION
                      	""
	::= { accountingTypeEntry 4 }

	accountingTypeMethod OBJECT-TYPE
	SYNTAX  INTEGER{		
        		radius(1),
		tacacs(2)		
	}
	MAX-ACCESS  read-write
	STATUS  current
	DESCRIPTION
                      	""
	::= { accountingTypeEntry 5 }

	accountingTypePrivilege OBJECT-TYPE
	SYNTAX  INTEGER{	
		not_available(255),
		privilege_0(0),
		privilege_1(1),
		privilege_2(2),
		privilege_3(3),
		privilege_4(4),
		privilege_5(5),
		privilege_6(6),
		privilege_7(7),
		privilege_8(8),
		privilege_9(9),
		privilege_10(10),
		privilege_11(11),
		privilege_12(12),
		privilege_13(13),
		privilege_14(14)        		
	}
	MAX-ACCESS  read-write
	STATUS  current
	DESCRIPTION
                      	""
	::= { accountingTypeEntry 6 }

--  VDSL2Extensions

	vdsl2Ext            OBJECT IDENTIFIER ::= { ves1724-56fanless 60 }
	------------------------------------------------      
	xdsl2ExtNotifications OBJECT IDENTIFIER ::= { vdsl2Ext 0 }
	xdsl2ExtLine          OBJECT IDENTIFIER ::= { vdsl2Ext 1 }
	xdsl2ExtStatus        OBJECT IDENTIFIER ::= { vdsl2Ext 2 }
	--xdsl2ExtInventory     OBJECT IDENTIFIER ::= { vdsl2Ext 3 }
	xdsl2ExtPM            OBJECT IDENTIFIER ::= { vdsl2Ext 4 }
	xdsl2ExtProfile       OBJECT IDENTIFIER ::= { vdsl2Ext 5 }
	--xdsl2ExtScalar        OBJECT IDENTIFIER ::= { vdsl2Ext 6 }
	--xdsl2ExtConformance   OBJECT IDENTIFIER ::= { vdsl2Ext 7 }
	------------------------------------------------
	xdsl2ExtPMLine      OBJECT IDENTIFIER ::= { xdsl2ExtPM 1 }
	xdsl2ExtPMChannel   OBJECT IDENTIFIER ::= { xdsl2ExtPM 2 }
	------------------------------------------------
	xdsl2ExtProfileLine      OBJECT IDENTIFIER ::= { xdsl2ExtProfile 1 }
	xdsl2ExtProfileChannel   OBJECT IDENTIFIER ::= { xdsl2ExtProfile 2 }
	xdsl2ExtProfileAlarmConf OBJECT IDENTIFIER ::= { xdsl2ExtProfile 3 }
	------------------------------------------------
	--xdsl2ExtScalarSC         OBJECT IDENTIFIER ::= { xdsl2Scalar 1 }
	------------------------------------------------


------------------------------------------------
--          xdsl2ExtLineTable                    --
------------------------------------------------
    xdsl2ExtLineTable  OBJECT-TYPE
    SYNTAX      SEQUENCE  OF  Xdsl2ExtLineEntry
    MAX-ACCESS  not-accessible
    STATUS      current
    DESCRIPTION
       "The table xdsl2ExtLineTable extends xdsl2LineTable for ZyXEL product."
    ::= { xdsl2ExtLine 1 }

    xdsl2ExtLineEntry  OBJECT-TYPE
    SYNTAX      Xdsl2ExtLineEntry
    MAX-ACCESS  not-accessible
    STATUS      current
    DESCRIPTION
       "The table xdsl2ExtLineTable contains extra functions besides those in
        xdsl2LineTable."
    INDEX  { ifIndex }
    ::= { xdsl2ExtLineTable 1 }    

    Xdsl2ExtLineEntry  ::=
    SEQUENCE {
       xdsl2LineCmndConfSelt            Xdsl2LineLdsf
    }
   
    xdsl2LineCmndConfSelt  OBJECT-TYPE
    SYNTAX      Xdsl2LineLdsf
    MAX-ACCESS  read-write
    STATUS      current
    DESCRIPTION
       "Trigger a SELT(Single End Loop Test) for the line. Note the loop
        should be open."
    DEFVAL       { inhibit }
    ::= { xdsl2ExtLineEntry 1 } 

------------------------------------------------
--          xdsl2ExtLineBandTable                --
------------------------------------------------
    xdsl2ExtLineBandTable  OBJECT-TYPE
    SYNTAX      SEQUENCE  OF  Xdsl2ExtLineBandEntry
    MAX-ACCESS  not-accessible
    STATUS      current
    DESCRIPTION
       "The table xdsl2ExtLineBandTable extends xdsl2LineBandTable for 
        ZyXEL product."
    ::= { xdsl2ExtLine 2 }

    xdsl2ExtLineBandEntry  OBJECT-TYPE
    SYNTAX      Xdsl2ExtLineBandEntry
    MAX-ACCESS  not-accessible
    STATUS      current
    DESCRIPTION
       "The table xdsl2ExtLineBandTable contains extra per-band line 
        status parameters besides those in xdsl2LineBandTable."
    INDEX  { ifIndex, xdsl2LineBand }
    ::= { xdsl2ExtLineBandTable 1 }
    
    Xdsl2ExtLineBandEntry  ::=
    SEQUENCE {
       xdsl2LineBandStatusActAtp           Integer32,
       xdsl2LineBandStatusActRxPwr         Integer32
    }
    
    xdsl2LineBandStatusActAtp  OBJECT-TYPE
    SYNTAX      Integer32 (-310..310 | 2147483647)
    UNITS       "0.1 dBm"
    MAX-ACCESS  read-only
    STATUS      current
    DESCRIPTION
       "Actual Aggregate Transmit Power per band.
        A value of 0x7FFFFFFF (2147483647) indicates the measurement is
        out of range to be represented."
    DEFVAL       { 2147483646 }
    ::= { xdsl2ExtLineBandEntry 1 } 
        
    xdsl2LineBandStatusActRxPwr  OBJECT-TYPE
    SYNTAX      Integer32 (-255..255 | 2147483647)
    UNITS       "0.1 dBm"
    MAX-ACCESS  read-only
    STATUS      current
    DESCRIPTION
       "Actual Aggregate Receive Power per band.
        A value of 0x7FFFFFFF (2147483647) indicates the measurement is
        out of range to be represented."
    DEFVAL       { 2147483646 }
    ::= { xdsl2ExtLineBandEntry 2 }

------------------------------------------------
--          xdsl2ExtSeltUerTable              --
------------------------------------------------
    xdsl2ExtSeltUerTable  OBJECT-TYPE
	SYNTAX      SEQUENCE  OF  Xdsl2ExtSeltUerEntry
    MAX-ACCESS  not-accessible
    STATUS      current
    DESCRIPTION
       "The table xdsl2ExtSeltUerTable extends xdsl2LineTable for ZyXEL product."
    ::= { xdsl2ExtLine 3 }

    xdsl2ExtSeltUerEntry  OBJECT-TYPE
    SYNTAX      Xdsl2ExtSeltUerEntry
    MAX-ACCESS  not-accessible
    STATUS      current
    DESCRIPTION
       "The table xdsl2ExtSeltUerTable contains extra functions besides those in
        xdsl2LineTable."
    INDEX  { ifIndex }
    ::= { xdsl2ExtSeltUerTable 1 }    

    Xdsl2ExtSeltUerEntry  ::=
    SEQUENCE { 
       xdsl2ExtSeltUerDuration      Integer32,
       xdsl2ExtSeltUerAgcGain 		Integer32,
       xdsl2ExtSeltUerMeasureTone	Integer32,
       xdsl2ExtSeltUerAction        Xdsl2LineLdsf
    }  
   
    xdsl2ExtSeltUerDuration  OBJECT-TYPE
    SYNTAX      Integer32 (1..255)
    MAX-ACCESS  read-write
    STATUS      current
    DESCRIPTION
       "The measure duration of SELT(Single End Loop Test) UER for the line. the range from 1 to 255.
       Note the loop should be open."
    DEFVAL       { 10 }
    ::= { xdsl2ExtSeltUerEntry 1 } 

    xdsl2ExtSeltUerAgcGain  OBJECT-TYPE
    SYNTAX      Integer32 (0..32)
    MAX-ACCESS  read-write
    STATUS      current
    DESCRIPTION
       "The AGC Gain setting of SELT(Single End Loop Test) UER for the line. the range from 0 to 32.
       0 means auto, chip will assign a value automatic. Note the loop should be open."
    DEFVAL       { 0 }
    ::= { xdsl2ExtSeltUerEntry 2 } 

    xdsl2ExtSeltUerMeasureTone  OBJECT-TYPE
    SYNTAX      Integer32 (1..4)
    MAX-ACCESS  read-write
    STATUS      current
    DESCRIPTION
       "The measure tones of SELT QLN for the line. 1 means 1024, 2 means 2048, 3 means 3072 and
       4 means SELT QLN will measure 4096 tones. Note the loop should be open."
    DEFVAL       { 4 }
    ::= { xdsl2ExtSeltUerEntry 3 }
    
    xdsl2ExtSeltUerAction  OBJECT-TYPE
    SYNTAX      Xdsl2LineLdsf
    MAX-ACCESS  read-write
    STATUS      current
    DESCRIPTION
       "Trigger a SELT(Single End Loop Test)UER for the line. Note the loop
        should be open."
    DEFVAL       { inhibit }
    ::= { xdsl2ExtSeltUerEntry 4 } 

------------------------------------------------
--          xdsl2ExtSeltQlnTable              --
------------------------------------------------
    xdsl2ExtSeltQlnTable  OBJECT-TYPE
    SYNTAX      SEQUENCE  OF  Xdsl2ExtSeltQlnEntry
    MAX-ACCESS  not-accessible
    STATUS      current
    DESCRIPTION
       "The table xdsl2ExtSeltQlnTable extends xdsl2LineTable for ZyXEL product."
    ::= { xdsl2ExtLine 4 }

    xdsl2ExtSeltQlnEntry  OBJECT-TYPE
    SYNTAX      Xdsl2ExtSeltQlnEntry
    MAX-ACCESS  not-accessible
    STATUS      current
    DESCRIPTION
       "The table xdsl2ExtSeltQlnTable contains extra functions besides those in
        xdsl2LineTable."
    INDEX  { ifIndex }
    ::= { xdsl2ExtSeltQlnTable 1 }    

    Xdsl2ExtSeltQlnEntry  ::=
    SEQUENCE { 
       xdsl2ExtSeltQlnDuration      		Integer32,
       xdsl2ExtSeltQlnMeasurementTone 		Integer32,
       xdsl2ExtSeltQlnAction        		Xdsl2LineLdsf
    }  
   
    xdsl2ExtSeltQlnDuration  OBJECT-TYPE
    SYNTAX      Integer32 (0..15)
    MAX-ACCESS  read-write
    STATUS      current
    DESCRIPTION
       "The measure duration of SELT QLN for the line. the range from 0 to 15.
       The measurement is performed over a period equal to 2^measure_duration DMT signals.
       A value of 12 corresponds approximately to one second. Note the loop should be open."
    DEFVAL       { 12 }
    ::= { xdsl2ExtSeltQlnEntry 1 } 

    xdsl2ExtSeltQlnMeasurementTone  OBJECT-TYPE
    SYNTAX      Integer32 (1..4)
    MAX-ACCESS  read-write
    STATUS      current
    DESCRIPTION
       "The measure tones of SELT QLN for the line. 1 means 1024, 2 means 2048, 3 means 3072 and
       4 means SELT QLN will measure 4096 tones. Note the loop should be open."
    DEFVAL       { 4 }
    ::= { xdsl2ExtSeltQlnEntry 2 } 

    xdsl2ExtSeltQlnAction  OBJECT-TYPE
    SYNTAX      Xdsl2LineLdsf
    MAX-ACCESS  read-write
    STATUS      current
    DESCRIPTION
       "Trigger a SELT(Single End Loop Test)QLN for the line. Note the loop
        should be open. If the line was in show-time, performance the SELT QLN will
        cause it link down."
    DEFVAL       { inhibit }
    ::= { xdsl2ExtSeltQlnEntry 3 } 


------------------------------------------------
--          xdsl2ExtLineSegmentTable             --
------------------------------------------------
    xdsl2ExtLineSegmentTable  OBJECT-TYPE
    SYNTAX      SEQUENCE  OF  Xdsl2ExtLineSegmentEntry
    MAX-ACCESS  not-accessible
    STATUS      current
    DESCRIPTION
       "The table xdsl2ExtLineSegmentTable extends xdsl2LineSegmentTable for 
         ZyXEL product."
    ::= { xdsl2ExtStatus 1 }

    xdsl2ExtLineSegmentEntry  OBJECT-TYPE
    SYNTAX      Xdsl2ExtLineSegmentEntry
    MAX-ACCESS  not-accessible
    STATUS      current
    DESCRIPTION
       "The table xdsl2LineExtSegmentEntry contains extra line segment 
         status parameters besides those in xdsl2LineSegmentTable.

        This table stores HLOG/QLN/SNR measured during initialization."
    INDEX  { ifIndex,
             xdsl2LineSegmentDirection,
             xdsl2LineSegment   }
    ::= { xdsl2ExtLineSegmentTable 1 }
   
    Xdsl2ExtLineSegmentEntry  ::=
    SEQUENCE {
       xdsl2LineSegmentLog         OCTET STRING,
       xdsl2LineSegmentQln         OCTET STRING,
       xdsl2LineSegmentSnr         OCTET STRING,
       xdsl2LineSegmentStatus      BITS,
       xdsl2LineSegmentLogScGroupSize    Unsigned32,
       xdsl2LineSegmentQlnScGroupSize    Unsigned32,
       xdsl2LineSegmentSnrScGroupSize    Unsigned32
    }
    
    xdsl2LineSegmentLog  OBJECT-TYPE
    SYNTAX      OCTET STRING  (SIZE(0..1024))
    UNITS       "dB"
    MAX-ACCESS  read-only
    STATUS      current
    DESCRIPTION
     "This parameter is applicable in initialization and use the same
      format as xdsl2SCStatusSegmentLog."
     ::= { xdsl2ExtLineSegmentEntry 1 }

    xdsl2LineSegmentQln  OBJECT-TYPE
    SYNTAX      OCTET STRING  (SIZE(0..512))
    UNITS       "dBm/Hz"
    MAX-ACCESS  read-only
    STATUS      current
    DESCRIPTION
     "This parameter is applicable in initialization and use the same
      format as xdsl2SCStatusSegmentQln."
     ::= { xdsl2ExtLineSegmentEntry 2 }

    xdsl2LineSegmentSnr  OBJECT-TYPE
    SYNTAX      OCTET STRING  (SIZE(0..512))
    UNITS       "0.5 dB"
    MAX-ACCESS  read-only
    STATUS      current
    DESCRIPTION
     "This parameter is applicable in initialization and use the same
      format as xdsl2SCStatusSegmentSnr."
    ::= { xdsl2ExtLineSegmentEntry 3 }
    
    xdsl2LineSegmentStatus  OBJECT-TYPE
    SYNTAX      BITS {
                  hlogReady(0),
                  qlnReady(1),
                  snrReady(2)
               }
    MAX-ACCESS  read-only
    STATUS      current
    DESCRIPTION
     "This parameter indicates whether the Hlog/Qln/Snr data is ready."
    ::= { xdsl2ExtLineSegmentEntry 4 }

    xdsl2LineSegmentLogScGroupSize OBJECT-TYPE
    SYNTAX      Unsigned32(1 | 2 | 4 | 8)
    MAX-ACCESS  read-only
    STATUS      current
    DESCRIPTION
     "Number of subcarriers per group used to report the H(f)
      logarithmic representation values for the respective
      transmission direction. The valid values are 1, 2, 4 and 8.
      For ADSL, this parameter is equal to one and, for VDSL2, it is
      equal to the size of a subcarrier group used to compute these
      parameters."
    REFERENCE  "ITU-T G.997.1, paragraph #7.5.1.26.5 (HLOGGds)
               and paragraph #7.5.1.26.11 (HLOGGus)"
    ::= { xdsl2ExtLineSegmentEntry 5 }

    xdsl2LineSegmentQlnScGroupSize OBJECT-TYPE
    SYNTAX      Unsigned32(1 | 2 | 4 | 8)
    MAX-ACCESS  read-only
    STATUS      current
    DESCRIPTION
     "Number of subcarriers per group used to report the Quiet
     Line Noise values for the respective transmission direction.
     The valid values are 1, 2, 4 and 8.
     For ADSL, this parameter is equal to one and, for VDSL2, it is
     equal to the size of a subcarrier group used to compute these
     parameters."
    REFERENCE  "ITU-T G.997.1, paragraph #7.5.1.27.2 (QLNGds)
               and paragraph #7.5.1.27.5 (QLNGus)"
    ::= { xdsl2ExtLineSegmentEntry 6 } 
    
    xdsl2LineSegmentSnrScGroupSize OBJECT-TYPE
    SYNTAX      Unsigned32(1 | 2 | 4 | 8)
    MAX-ACCESS  read-only
    STATUS      current
    DESCRIPTION
     "Number of subcarriers per group used to report the SNR values
      on the respective transmission direction.
      The valid values are 1, 2, 4 and 8.
      For ADSL, this parameter is equal to one and, for VDSL2, it is
      equal to the size of a subcarrier group used to compute these
      parameters."
    REFERENCE  "ITU-T G.997.1, paragraph #7.5.1.28.2 (SNRGds)
               and paragraph #7.5.1.28.5 (SNRGus)"
    ::= { xdsl2ExtLineSegmentEntry 7 }


------------------------------------------------
--        xdsl2ExtChannelStatusTable                  --
------------------------------------------------

    xdsl2ExtChannelStatusTable  OBJECT-TYPE
    SYNTAX      SEQUENCE  OF  Xdsl2ExtChannelStatusEntry
    MAX-ACCESS  not-accessible
    STATUS      current
    DESCRIPTION
       "The table xdsl2ExtChannelStatusTable extends xdsl2ChannelStatusTable for 
         ZyXEL product."
    ::= { xdsl2ExtStatus 2 }

    Xdsl2StatusActualRaMode ::= TEXTUAL-CONVENTION
    STATUS      current
    DESCRIPTION
       "fixedRateMode(1) - Fixed rate mode
        raInit(2)        - Adaptive rate mode at initialization
        dynamicRa(3)     - Dynamic rate adaptation
        sosEnabled(4)    - SOS enabled"
    SYNTAX      INTEGER {
        none(0),
        fixedRateMode(1),
        raInit(2),
        dynamicRa(3),
        sosEnabled(4)
    }
    
    Xdsl2StatusRtxMode ::= TEXTUAL-CONVENTION
    STATUS      current
    DESCRIPTION
       "rtxInUse(1)            - RTX in use.
        rtxForbidden(2)        - RTX not in use because RTX_MODE = FORBIDDEN.
        rtxNotSupportedXtuC(3) - RTX not in use because it is not supported by the XTU-C.
        rtxNotSupportedXtuR(4) - RTX not in use because it is not supported by the XTU-R.
        rtxNotSupportedBoth(5) - RTX not in use because it is not supported by the XTU-C and XTU-R."
    SYNTAX      INTEGER {
    	none(0),
        rtxInUse(1),
        rtxForbidden(2),
        rtxNotSupportedXtuC(3),
        rtxNotSupportedXtuR(4),
        rtxNotSupportedBoth(5)
    }

    xdsl2ExtChannelStatusEntry  OBJECT-TYPE
    SYNTAX      Xdsl2ExtChannelStatusEntry
    MAX-ACCESS  not-accessible
    STATUS      current
    DESCRIPTION
       "The table xdsl2ExtChannelStatusTable contains extra subcarrier  
        status parameters besides those in xdsl2ChannelStatusTable."
    INDEX  { ifIndex, xdsl2ChStatusUnit }
    ::= { xdsl2ExtChannelStatusTable 1 }

    Xdsl2ExtChannelStatusEntry  ::=
    SEQUENCE {
       xdsl2ChannelStatusActualRaMode    Xdsl2StatusActualRaMode,
       xdsl2ChannelStatusRetransmissionMode    Xdsl2StatusRtxMode,
       xdsl2ChannelStatusRetransmissionOverhead    Unsigned32,
       xdsl2ChannelStatusGinpFramingType    Unsigned32,
       xdsl2ChannelStatusActualInpAgainstREIN    Unsigned32,
       xdsl2ChannelStatusReedSolomonCodeWordPerDtu    Unsigned32
    }
    
    xdsl2ChannelStatusActualRaMode  OBJECT-TYPE
    SYNTAX      Xdsl2StatusActualRaMode
    UNITS       ""
    MAX-ACCESS  read-only
    STATUS      current
    DESCRIPTION
     "The actual RA mode.
      The possible values are:
        fixedRateMode(1) - Fixed rate mode
        raInit(2)        - Adaptive rate mode at initialization
        dynamicRa(3)     - Dynamic rate adaptation
        sosEnabled(4)    - SOS enabled"
    ::= { xdsl2ExtChannelStatusEntry 1 }
    
    xdsl2ChannelStatusRetransmissionMode  OBJECT-TYPE
    SYNTAX      Xdsl2StatusRtxMode
    UNITS       ""
    MAX-ACCESS  read-only
    STATUS      current
    DESCRIPTION
     "RTX_USED operational data parameter.
      The possible values are:
        rtxInUse(1)            - RTX in use.
        rtxForbidden(2)        - RTX not in use because RTX_MODE = FORBIDDEN.
        rtxNotSupportedXtuC(3) - RTX not in use because it is not supported by the XTU-C.
        rtxNotSupportedXtuR(4) - RTX not in use because it is not supported by the XTU-R.
        rtxNotSupportedBoth(5) - RTX not in use because it is not supported by the XTU-C and XTU-R."
    ::= { xdsl2ExtChannelStatusEntry 2 }
    
    xdsl2ChannelStatusRetransmissionOverhead  OBJECT-TYPE
    SYNTAX      Unsigned32
    UNITS       "kbps"
    MAX-ACCESS  read-only
    STATUS      current
    DESCRIPTION
       "Expected retransmission overhead in G.inp due to REIN and SHINE noise. Unit is kbps."
    ::= { xdsl2ExtChannelStatusEntry 3 }
    
    xdsl2ChannelStatusGinpFramingType  OBJECT-TYPE
    SYNTAX      Unsigned32
    UNITS       ""
    MAX-ACCESS  read-only
    STATUS      current
    DESCRIPTION
       "This parameter is equal to zero if G.inp is 
        not enabled. If G.inp is enabled, it reports 
        the framing type in use (1, 2, 3, or 4)."
    ::= { xdsl2ExtChannelStatusEntry 4 }
    
    xdsl2ChannelStatusActualInpAgainstREIN  OBJECT-TYPE
    SYNTAX      Unsigned32
    UNITS       "1/2 symbol"
    MAX-ACCESS  read-only
    STATUS      current
    DESCRIPTION
       "This parameter reports the actual INP against REIN noise. Unit is 1/2 symbol."
    ::= { xdsl2ExtChannelStatusEntry 5 }
    
    xdsl2ChannelStatusReedSolomonCodeWordPerDtu  OBJECT-TYPE
    SYNTAX      Unsigned32
    UNITS       ""
    MAX-ACCESS  read-only
    STATUS      current
    DESCRIPTION
       "This parameter reports the number of RS codewords per DTU.
        It is equal to D when PhyR is enabled."
    ::= { xdsl2ExtChannelStatusEntry 6 }
    

------------------------------------------------
--        xdsl2ExtSCStatusTable                  --
------------------------------------------------

    xdsl2ExtSCStatusTable  OBJECT-TYPE
    SYNTAX      SEQUENCE  OF  Xdsl2ExtSCStatusEntry
    MAX-ACCESS  not-accessible
    STATUS      current
    DESCRIPTION
       "The table xdsl2ExtSCStatusTable extends xdsl2SCStatusTable for 
         ZyXEL product."
    ::= { xdsl2ExtStatus 3 }

    xdsl2ExtSCStatusEntry  OBJECT-TYPE
    SYNTAX      Xdsl2ExtSCStatusEntry
    MAX-ACCESS  not-accessible
    STATUS      current
    DESCRIPTION
       "The table xdsl2ExtSCStatusTable contains extra subcarrier  
        status parameters besides those in xdsl2SCStatusTable."
    INDEX  { ifIndex, xdsl2SCStatusDirection }
    ::= { xdsl2ExtSCStatusTable 1 }

    Xdsl2ExtSCStatusEntry  ::=
    SEQUENCE {
       xdsl2SCStatusActAtp    Integer32
    }
    
    xdsl2SCStatusActAtp  OBJECT-TYPE
    SYNTAX      Integer32 (-310..310 | 2147483647)
    UNITS       "0.1 dBm"
    MAX-ACCESS  read-only
    STATUS      current
    DESCRIPTION
       "Actual Aggregate Transmit Power Downstream. 
        The total amount of transmit power delivered by the xTU-C at
        the U-C reference point, at the instant of measurement.  It
        ranges from -310 to 310 units of 0.1 dBm (Physical values are -31
        to 31 dBm).
        A value of 0x7FFFFFFF (2147483647) indicates the measurement is
        out of range to be represented.
        This object reflects the value of the parameter following the
        most recent DELT performed on the associated line.  Once the DELT
        process is over, the parameter no longer changes until the row is
        deleted or a new DELT process is initiated.
        "
    DEFVAL       { 2147483647 }
    ::= { xdsl2ExtSCStatusEntry 1 }    
    
------------------------------------------------
--        xdsl2ExtSCStatusBandTable              --
------------------------------------------------

    xdsl2ExtSCStatusBandTable  OBJECT-TYPE
    SYNTAX      SEQUENCE  OF  Xdsl2ExtSCStatusBandEntry
    MAX-ACCESS  not-accessible
    STATUS      current
    DESCRIPTION
       "The table xdsl2ExtSCStatusBandTable extends xdsl2SCStatusBandTable for 
         ZyXEL product."
    ::= { xdsl2ExtStatus 4 }

    xdsl2ExtSCStatusBandEntry  OBJECT-TYPE
    SYNTAX      Xdsl2ExtSCStatusBandEntry
    MAX-ACCESS  not-accessible
    STATUS      current
    DESCRIPTION
       "The table xdsl2ExtSCStatusBandTable contains extra subcarrier  
        status parameters that are grouped per-band besides those in 
        xdsl2SCStatusBandTable."
    INDEX  { ifIndex, xdsl2SCStatusBand }
    ::= { xdsl2ExtSCStatusBandTable 1 }

    Xdsl2ExtSCStatusBandEntry  ::=
    SEQUENCE {
       xdsl2SCStatusBandSnrMargin          Integer32
    }    

    xdsl2SCStatusBandSnrMargin  OBJECT-TYPE
    SYNTAX      Integer32 (-640..630 | 2147483646 | 2147483647)
    UNITS       "0.1 dB"
    MAX-ACCESS  read-only
    STATUS      current
    DESCRIPTION
       "SNR Margin is the maximum increase in dB of the noise power
        received at the xTU (xTU-R for a band in the downstream direction
        and xTU-C for a band in the upstream direction), such that the
        BER requirements are met for all bearer channels received at the
        xTU. Values range from -640 to 630 in units of 0.1 dB (Physical
        values are -64 to 63 dB).
        A special value of 0x7FFFFFFF (2147483647) indicates the SNR
        Margin is out of range to be represented.
        A special value of 0x7FFFFFFE (2147483646) indicates the SNR
        Margin measurement is currently unavailable.
        This object reflects the value of the parameter following the
        most recent DELT performed on the associated line.  Once the DELT
        process is over, the parameter no longer changes until the row is
        deleted or a new DELT process is initiated."
    DEFVAL       { 2147483646 }
    ::= { xdsl2ExtSCStatusBandEntry 1 }


------------------------------------------------
--        xdsl2ExtSeltStatusTable             --
------------------------------------------------

    xdsl2ExtSeltStatusTable  OBJECT-TYPE
    SYNTAX      SEQUENCE  OF  Xdsl2ExtSeltStatusEntry
    MAX-ACCESS  not-accessible
    STATUS      current
    DESCRIPTION
       "The table xdsl2ExtSeltStatusTable contains SELT status."
    ::= { xdsl2ExtStatus 6 }

    xdsl2ExtSeltStatusEntry  OBJECT-TYPE
    SYNTAX      Xdsl2ExtSeltStatusEntry
    MAX-ACCESS  not-accessible
    STATUS      current
    DESCRIPTION
       "The table xdsl2ExtSeltStatusEntry contains SELT status."
    INDEX  { ifIndex }
    ::= { xdsl2ExtSeltStatusTable 1 }

    Xdsl2ExtSeltStatusEntry  ::=
    SEQUENCE {
       xdsl2SeltStatus		Integer32,
       xdsl2SeltStatusLineType	DisplayString, 
       xdsl2SeltStatusLineLength	Integer32
    }    

    xdsl2SeltStatus  OBJECT-TYPE
    SYNTAX  Integer32 {
	idle(0),
	inProgress(1),
	failed(2),
	done(3)
	}
    MAX-ACCESS  read-only
    STATUS      current
    DESCRIPTION
    " "
    ::= { xdsl2ExtSeltStatusEntry 1 }

    xdsl2SeltStatusLineType  OBJECT-TYPE
    SYNTAX  DisplayString
    MAX-ACCESS  read-only
    STATUS      current
    DESCRIPTION
    " "
    ::= { xdsl2ExtSeltStatusEntry 2 }
	
    xdsl2SeltStatusLineLength  OBJECT-TYPE
    SYNTAX  Integer32
    MAX-ACCESS  read-only
    STATUS      current
    DESCRIPTION
    " "
    ::= { xdsl2ExtSeltStatusEntry 3 }
    
------------------------------------------------
--        xdsl2ExtSeltReflectionStatus        --
------------------------------------------------

    xdsl2ExtSeltReflectionStatusTable  OBJECT-TYPE
    SYNTAX      SEQUENCE  OF  Xdsl2ExtSeltReflectionStatusEntry
    MAX-ACCESS  not-accessible
    STATUS      current
    DESCRIPTION
       "The table xdsl2ExtSeltReflectionStatusTable contains SELT status 
        for each reflection."
    ::= { xdsl2ExtStatus 7 }

    xdsl2ExtSeltReflectionStatusEntry  OBJECT-TYPE
    SYNTAX      Xdsl2ExtSeltReflectionStatusEntry
    MAX-ACCESS  not-accessible
    STATUS      current
    DESCRIPTION
       "The table xdsl2ExtSeltReflectionStatusTable contains SELT status 
        for each reflection."
    INDEX  { ifIndex, xdsl2SeltReflection }
    ::= { xdsl2ExtSeltReflectionStatusTable 1 }

    Xdsl2ExtSeltReflectionStatusEntry  ::=
    SEQUENCE {
      xdsl2SeltReflection		Unsigned32,
      xdsl2SeltDelay		Integer32,
      xdsl2SeltError		Integer32,
      xdsl2SeltAtn180kHz		Integer32,
      xdsl2SeltAtn300kHz		Integer32,
      xdsl2SeltFitError		Integer32, 
      xdsl2SeltFitTermination	Integer32
    }

    xdsl2SeltReflection OBJECT-TYPE
     SYNTAX      Unsigned32
     MAX-ACCESS  not-accessible
     STATUS      current
     DESCRIPTION
     ""
     ::= { xdsl2ExtSeltReflectionStatusEntry 1 }

    xdsl2SeltDelay  OBJECT-TYPE
    SYNTAX      Integer32
    UNITS       "0.1"
    MAX-ACCESS  read-only
    STATUS      current
    DESCRIPTION
    " "
    ::= { xdsl2ExtSeltReflectionStatusEntry 2 }

    xdsl2SeltError  OBJECT-TYPE
    SYNTAX      Integer32
    UNITS       "0.1"
    MAX-ACCESS  read-only
    STATUS      current
    DESCRIPTION
    " "
    ::= { xdsl2ExtSeltReflectionStatusEntry 3 }

    xdsl2SeltAtn180kHz  OBJECT-TYPE
    SYNTAX      Integer32
    UNITS       "0.1"
    MAX-ACCESS  read-only
    STATUS      current
    DESCRIPTION
    " "
    ::= { xdsl2ExtSeltReflectionStatusEntry 4 }

    xdsl2SeltAtn300kHz  OBJECT-TYPE
    SYNTAX      Integer32
    UNITS       "0.1"
    MAX-ACCESS  read-only
    STATUS      current
    DESCRIPTION
    " "
    ::= { xdsl2ExtSeltReflectionStatusEntry 5 }
   
    xdsl2SeltFitError  OBJECT-TYPE
    SYNTAX      Integer32
    UNITS       "0.1"
    MAX-ACCESS  read-only
    STATUS      current
    DESCRIPTION
    " "
    ::= { xdsl2ExtSeltReflectionStatusEntry 6 }

    xdsl2SeltFitTermination  OBJECT-TYPE
    SYNTAX      Integer32
    UNITS       "0.2"
    MAX-ACCESS  read-only
    STATUS      current
    DESCRIPTION
    " "
    ::= { xdsl2ExtSeltReflectionStatusEntry 7 }
    
------------------------------------------------
--        xdsl2ExtSeltUerStatusTable          --
------------------------------------------------

	xdsl2ExtSeltUerStatusTable  OBJECT-TYPE
    SYNTAX      SEQUENCE  OF  Xdsl2ExtSeltUerStatusEntry
    MAX-ACCESS  not-accessible
    STATUS      current
    DESCRIPTION
       "The table xdsl2ExtSeltUerStatusTable contains SELT UER status for each tones."
    ::= { xdsl2ExtStatus 8 }

    xdsl2ExtSeltUerStatusEntry  OBJECT-TYPE
    SYNTAX      Xdsl2ExtSeltUerStatusEntry
    MAX-ACCESS  not-accessible
    STATUS      current
    DESCRIPTION
       "The table xdsl2ExtSeltUerStatusTable contains SELT UER status for each tones."
    INDEX  { ifIndex,xdsl2SCStatusSegment }
    ::= { xdsl2ExtSeltUerStatusTable 1 }

	Xdsl2ExtSeltUerStatusEntry  ::=
    SEQUENCE {
      xdsl2ExtSeltUerSegment                Unsigned32, 
      xdsl2ExtSeltUerStatus                 INTEGER,
      xdsl2ExtSeltUerSegmentEchoReal		OCTET STRING,
      xdsl2ExtSeltUerSegmentEchoImg			OCTET STRING,
      xdsl2ExtSeltUerSegmentEchoExp			OCTET STRING,  
      xdsl2ExtSeltUerSegmentTotalRxGain    	OCTET STRING,
      xdsl2ExtSeltUerSegmentAnalogRxGain    OCTET STRING
    }
	xdsl2ExtSeltUerSegment  OBJECT-TYPE
     SYNTAX      Unsigned32(1..8)
     MAX-ACCESS  not-accessible
     STATUS      current
     DESCRIPTION
     "The segment of the subcarriers status information provided by
      this row.
      Several status parameters in this table are retrieved in segments.
      The first segment of the status information is retrieved with
      xdsl2SCStatusSegment=1, the second segment is retrieved with
      xdsl2SCStatusSegment=2, and so on.  When any status parameter is
      retrieved in n segments where n<8), then for that parameter,
      GET operations for the remaining segment numbers (n+1 to 8) will
      respond with a zero-length OCTET STRING."
     ::= { xdsl2ExtSeltUerStatusEntry 1 }
 
    xdsl2ExtSeltUerStatus OBJECT-TYPE
    SYNTAX      INTEGER {
	idle(0),
	inProgress(1),
	failed(2),
	done(3)
	}
	MAX-ACCESS  read-only
	STATUS      current
	DESCRIPTION
	""
     ::= { xdsl2ExtSeltUerStatusEntry 2 }
	
	xdsl2ExtSeltUerSegmentEchoReal  OBJECT-TYPE
     SYNTAX      OCTET STRING  (SIZE(0..4096))
     MAX-ACCESS  read-only
     STATUS      current
     DESCRIPTION
     "An array of up to 4096 tones. 
      It is designed to support up to 4096 subcarriers for SELT UER real part in the range (-2^15+1) to (+2^15-1).
      A special value -2^15 indicates that no measurement could be done for the subcarrier.
      Each value in this array is 16 bits wide and is stored in big	endian format"
     ::= { xdsl2ExtSeltUerStatusEntry 3 }
     
	xdsl2ExtSeltUerSegmentEchoImg  OBJECT-TYPE
     SYNTAX      OCTET STRING  (SIZE(0..4096))
     MAX-ACCESS  read-only
     STATUS      current
     DESCRIPTION
     "An array of up to 4096 tones. 
      It is designed to support up to 4096 subcarriers for SELT UER imaginary part in the range (-2^15+1) to (+2^15-1). 
      A special value -2^15 indicates that no measurement could be done for the subcarrier,
      Each value in this array is 16 bits wide and is stored in big	endian format"
     ::= { xdsl2ExtSeltUerStatusEntry 4 }

	xdsl2ExtSeltUerSegmentEchoExp  OBJECT-TYPE
     SYNTAX      OCTET STRING  (SIZE(0..4096))
     MAX-ACCESS  read-only
     STATUS      current
     DESCRIPTION
     "An array of up to 4096 tones. 
      It is designed to support up to 4096 subcarriers for SELT UER exponent element. A special value 1023 indicates that
      no measurement could be done for the subcarrier.Each value in this array is 8 bits wide."
     ::= { xdsl2ExtSeltUerStatusEntry 5 }  

	xdsl2ExtSeltUerSegmentTotalRxGain  OBJECT-TYPE
    SYNTAX      OCTET STRING  (SIZE(0..3))   
    UNITS       "0.01 dB"
    MAX-ACCESS  read-only    
    STATUS      current
    DESCRIPTION
    "To performance the measurment of SELT need repetitive 4 times. The array to record total Rx gain for each time. 
     A special value 1023 indicates that no measurement could be done.
     Each value in this array is 16 bits wide"
    ::= { xdsl2ExtSeltUerStatusEntry 6 }  
     
	xdsl2ExtSeltUerSegmentAnalogRxGain  OBJECT-TYPE
    SYNTAX      OCTET STRING  (SIZE(0..3))  
    UNITS       "0.01 dB"
    MAX-ACCESS  read-only   
    STATUS      current
    DESCRIPTION
    "To performance the measurment of SELT need repetitive 4 times. The array to record analog Rx gain for each time. 
     A special value 1023 indicates that no measurement could be done.
     Each value in this array is 16 bits wide"
    ::= { xdsl2ExtSeltUerStatusEntry 7 }  

------------------------------------------------
--        xdsl2ExtSeltQlnStatusTable          --
------------------------------------------------

	xdsl2ExtSeltQlnStatusTable  OBJECT-TYPE
    SYNTAX      SEQUENCE  OF  Xdsl2ExtSeltQlnStatusEntry
    MAX-ACCESS  not-accessible
    STATUS      current
    DESCRIPTION
       "The table xdsl2ExtSeltQlnStatusTableTable contains SELT Qln status 
        for each tones."
    ::= { xdsl2ExtStatus 9 }

    xdsl2ExtSeltQlnStatusEntry  OBJECT-TYPE
    SYNTAX      Xdsl2ExtSeltQlnStatusEntry
    MAX-ACCESS  not-accessible
    STATUS      current
    DESCRIPTION
       "The table xdsl2ExtSeltQlnStatusTable contains SELT UER status for each tones."
    INDEX  { ifIndex }
    ::= { xdsl2ExtSeltQlnStatusTable 1 }

	Xdsl2ExtSeltQlnStatusEntry  ::=
    SEQUENCE {
      xdsl2ExtSeltQlnStatus			Integer32,
      xdsl2ExtSeltQlnSegmentQln		OCTET STRING
    }

    xdsl2ExtSeltQlnStatus OBJECT-TYPE
    SYNTAX      Integer32 {
	idle(0),
	inProgress(1),
	failed(2),
	done(3)
	}
	MAX-ACCESS  read-only
	STATUS      current
	DESCRIPTION
	""
     ::= { xdsl2ExtSeltQlnStatusEntry 1 }

	xdsl2ExtSeltQlnSegmentQln  OBJECT-TYPE
     SYNTAX      OCTET STRING  (SIZE(0..4096))
     UNITS       "dBm/Hz"
     MAX-ACCESS  read-only
     STATUS      current
     DESCRIPTION
     "An array of up to 4096 tones . 
      It is designed to support up to 4096 subcarriers for real Quiet Line Noise values in dBm/Hz.
      The QLN(f) is represented as ( -23-n(i)/2), with n(i) in the range 0 to 254.
      A special value n(i)=255 indicates that no measurement could be done for the subcarrier.
      Each value in this array is 8 bits wide."
     ::= { xdsl2ExtSeltQlnStatusEntry 2 }


------------------------------------------------
--      Extended PM line current counters     --
------------------------------------------------
    xdsl2ExtPMLineCurrTable  OBJECT-TYPE
    SYNTAX      SEQUENCE  OF  Xdsl2ExtPMLineCurrEntry
    MAX-ACCESS  not-accessible
    STATUS      current
    DESCRIPTION
       "The table xdsl2ExtPMLineCurrTable extends xdsl2PMLineCurrTable."
    ::= { xdsl2ExtPMLine 1 }

    xdsl2ExtPMLineCurrEntry  OBJECT-TYPE
    SYNTAX      Xdsl2ExtPMLineCurrEntry
    MAX-ACCESS  not-accessible
    STATUS      current
    DESCRIPTION
       "The table xdsl2ExtPMLineCurrTable extends xdsl2PMLineCurrTable."
    INDEX  { ifIndex, xdsl2PMLCurrUnit }
    ::= { xdsl2ExtPMLineCurrTable 1 }

    Xdsl2ExtPMLineCurrEntry  ::=
    SEQUENCE {
       xdsl2PMLSinceLinkFecs   Counter32,
       xdsl2PMLSinceLinkEs     Counter32,
       xdsl2PMLSinceLinkSes    Counter32,
       xdsl2PMLSinceLinkLoss   Counter32,
       xdsl2PMLSinceLinkUas    Counter32,
       xdsl2PMLSinceLinkLofs   Counter32,
       xdsl2PMLSinceLinkLol    Counter32,
       xdsl2PMLSinceLinkLols   Counter32,
       xdsl2PMLSinceLinkLpr    Counter32,
       xdsl2PMLSinceLinkLprs   Counter32,
       xdsl2PMLCurr15MLofs     Counter32,
       xdsl2PMLCurr15MLol      Counter32,
       xdsl2PMLCurr15MLols     Counter32,
       xdsl2PMLCurr15MLpr      Counter32,
       xdsl2PMLCurr15MLprs     Counter32,
       xdsl2PMLCurr1DayLofs    Counter32,
       xdsl2PMLCurr1DayLol     Counter32,
       xdsl2PMLCurr1DayLols    Counter32,
       xdsl2PMLCurr1DayLpr     Counter32,
       xdsl2PMLCurr1DayLprs    Counter32,
       xdsl2PMLSinceLinkInmEqInp	Counter32,
       xdsl2PMLSinceLinkInmIAT		Counter32,
       xdsl2PMLSinceLinkInmME		Counter32,
       xdsl2PMLCurr15MInmEqInp		Counter32,
       xdsl2PMLCurr15MInmIAT		Counter32,
       xdsl2PMLCurr15MInmME			Counter32,
       xdsl2PMLCurr1DayInmEqInp		Counter32,
       xdsl2PMLCurr1DayInmIAT		Counter32,
       xdsl2PMLCurr1DayInmME		Counter32
    }

    xdsl2PMLSinceLinkFecs  OBJECT-TYPE
    SYNTAX      Counter32
    UNITS       "seconds"
    MAX-ACCESS  read-only
    STATUS      current
    DESCRIPTION
       "Count of seconds since last link up that there was at
        least one FEC correction event for one or more bearer channels in
        this line.  This parameter is inhibited during UAS or SES."
    ::= { xdsl2ExtPMLineCurrEntry 1 }

    xdsl2PMLSinceLinkEs  OBJECT-TYPE
    SYNTAX      Counter32
    UNITS       "seconds"
    MAX-ACCESS  read-only
    STATUS      current
    DESCRIPTION
      "Count of seconds since last link up that there was:
          xTU-C: CRC-8 >= 1 for one or more bearer channels OR
                 LOS >= 1 OR SEF >=1 OR LPR >= 1
          xTU-R: FEBE >= 1 for one or more bearer channels OR
                 LOS-FE >=1 OR RDI >=1 OR LPR-FE >=1 .
       This parameter is inhibited during UAS."
    ::= { xdsl2ExtPMLineCurrEntry 2 }

    xdsl2PMLSinceLinkSes  OBJECT-TYPE
    SYNTAX      Counter32
    UNITS       "seconds"
    MAX-ACCESS  read-only
    STATUS      current
    DESCRIPTION
      "Count of seconds since last link up that that there was:
          xTU-C: (CRC-8 anomalies in one or more of the
                 received bearer channels) >= 18 OR LOS >= 1
                 OR SEF >= 1 OR LPR >= 1
          xTU-R: (FEBE anomalies in one or more of the
                 received bearer channels) >= 18 OR LOS-FE >= 1
                 OR RDI >= 1 OR LPR-FE >= 1 .
       This parameter is inhibited during UAS."
    ::= { xdsl2ExtPMLineCurrEntry 3 }

    xdsl2PMLSinceLinkLoss  OBJECT-TYPE
    SYNTAX      Counter32
    UNITS       "seconds"
    MAX-ACCESS  read-only
    STATUS      current
    DESCRIPTION
      "Count of seconds since last link up that there was LOS (or
       LOS-FE for xTU-R)."
    ::= { xdsl2ExtPMLineCurrEntry 4 }

    xdsl2PMLSinceLinkUas  OBJECT-TYPE
    SYNTAX      Counter32
    UNITS       "seconds"
    MAX-ACCESS  read-only
    STATUS      current
    DESCRIPTION
      "Count of seconds in Unavailability State since last line up.
       Unavailability begins at the onset of 10 contiguous
       severely-errored seconds, and ends at the onset of 10 contiguous
       seconds with no severely-errored seconds."
    ::= { xdsl2ExtPMLineCurrEntry 5 }

    xdsl2PMLSinceLinkLofs  OBJECT-TYPE
    SYNTAX      Counter32
    UNITS       "seconds"
    MAX-ACCESS  read-only
    STATUS      current
    DESCRIPTION
      "Count of seconds since last link up that there was LOF."
    ::= { xdsl2ExtPMLineCurrEntry 6 }

    xdsl2PMLSinceLinkLol  OBJECT-TYPE
    SYNTAX      Counter32
    MAX-ACCESS  read-only
    STATUS      current
    DESCRIPTION
      "Count of times the line loss of link since last link up."
    ::= { xdsl2ExtPMLineCurrEntry 7 }

    xdsl2PMLSinceLinkLols  OBJECT-TYPE
    SYNTAX      Counter32
    UNITS       "seconds"
    MAX-ACCESS  read-only
    STATUS      current
    DESCRIPTION
      "Count of seconds since last link up that there 
       was Loss of Link ."
    ::= { xdsl2ExtPMLineCurrEntry 8 }

    xdsl2PMLSinceLinkLpr  OBJECT-TYPE
    SYNTAX      Counter32
    MAX-ACCESS  read-only
    STATUS      current
    DESCRIPTION
      "Count of the line loss of power since last link up."
    ::= { xdsl2ExtPMLineCurrEntry 9 }

    xdsl2PMLSinceLinkLprs  OBJECT-TYPE
    SYNTAX      Counter32
    UNITS       "seconds"
    MAX-ACCESS  read-only
    STATUS      current
    DESCRIPTION
      "Count of seconds since last link up that there 
       was Loss of Power ."
    ::= { xdsl2ExtPMLineCurrEntry 10 }

    xdsl2PMLCurr15MLofs  OBJECT-TYPE
    SYNTAX      Counter32
    UNITS       "seconds"
    MAX-ACCESS  read-only
    STATUS      current
    DESCRIPTION
       "Count of seconds during this interval that there was LOF."
    ::= { xdsl2ExtPMLineCurrEntry 11 }

    xdsl2PMLCurr15MLol  OBJECT-TYPE
    SYNTAX      Counter32
    UNITS       "seconds"
    MAX-ACCESS  read-only
    STATUS      current
    DESCRIPTION
       "Count of times during this interval that the line Loss of Link."
    ::= { xdsl2ExtPMLineCurrEntry 12 }

    xdsl2PMLCurr15MLols  OBJECT-TYPE
    SYNTAX      Counter32
    UNITS       "seconds"
    MAX-ACCESS  read-only
    STATUS      current
    DESCRIPTION
       "Count of seconds during this interval that there was Loss of Link."
    ::= { xdsl2ExtPMLineCurrEntry 13 }

    xdsl2PMLCurr15MLpr  OBJECT-TYPE
    SYNTAX      Counter32
    UNITS       "seconds"
    MAX-ACCESS  read-only
    STATUS      current
    DESCRIPTION
       "Count of times during this interval that the line Loss of Power."
    ::= { xdsl2ExtPMLineCurrEntry 14 }

    xdsl2PMLCurr15MLprs  OBJECT-TYPE
    SYNTAX      Counter32
    UNITS       "seconds"
    MAX-ACCESS  read-only
    STATUS      current
    DESCRIPTION
       "Count of seconds during this interval that there was Loss of Power."
    ::= { xdsl2ExtPMLineCurrEntry 15 }

    xdsl2PMLCurr1DayLofs  OBJECT-TYPE
    SYNTAX      Counter32
    UNITS       "seconds"
    MAX-ACCESS  read-only
    STATUS      current
    DESCRIPTION
       "Count of seconds during this interval that there was LOF."
    ::= { xdsl2ExtPMLineCurrEntry 16 }

    xdsl2PMLCurr1DayLol  OBJECT-TYPE
    SYNTAX      Counter32
    MAX-ACCESS  read-only
    STATUS      current
    DESCRIPTION
       "Count of times during this interval that the line Loss of Link."
    ::= { xdsl2ExtPMLineCurrEntry 17 }

    xdsl2PMLCurr1DayLols  OBJECT-TYPE
    SYNTAX      Counter32
    UNITS       "seconds"
    MAX-ACCESS  read-only
    STATUS      current
    DESCRIPTION
       "Count of seconds during this interval that there was Loss of Link."
    ::= { xdsl2ExtPMLineCurrEntry 18 }

    xdsl2PMLCurr1DayLpr  OBJECT-TYPE
    SYNTAX      Counter32
    MAX-ACCESS  read-only
    STATUS      current
    DESCRIPTION
       "Count of times during this interval that the line Loss of Power."
    ::= { xdsl2ExtPMLineCurrEntry 19 }

    xdsl2PMLCurr1DayLprs  OBJECT-TYPE
    SYNTAX      Counter32
    UNITS       "seconds"
    MAX-ACCESS  read-only
    STATUS      current
    DESCRIPTION
       "Count of seconds during this interval that there was Loss of Power."
    ::= { xdsl2ExtPMLineCurrEntry 20 }
    
    
    xdsl2PMLSinceLinkInmEqInp  OBJECT-TYPE
    SYNTAX      Counter32
    MAX-ACCESS  read-only
    STATUS      current
    DESCRIPTION
       "The INM Equivalent Inp histogram since last link up. An 
    array of 68 octets (each 4 octets means amount of a bin of 
    histogram), designed for supporting from 1 to 17 bins of 
    the histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2ExtPMLineCurrEntry 21 }    
    
    xdsl2PMLSinceLinkInmIAT  OBJECT-TYPE
    SYNTAX      Counter32
    MAX-ACCESS  read-only
    STATUS      current
    DESCRIPTION
       "The INM Inter Arrival Time histogram since last link up. 
    An array of 32 octets (each 4 octets means amount of a bin 
    of histogram), designed for supporting from 0 to 7 bins of 
    the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2ExtPMLineCurrEntry 22 }    
    
    xdsl2PMLSinceLinkInmME  OBJECT-TYPE
    SYNTAX      Counter32
    UNITS       "symbols"
    MAX-ACCESS  read-only
    STATUS      current
    DESCRIPTION
       "The INM total measurement since last link up. This 
    indication occurs every time a data symbol is processed by 
    the Impulse Noise Sensor.
       The range of the value is from 0x0 to 0xFFFFFFFF" 
    REFERENCE    "ITU-T G.993.2 Amd2, paragraph 11.4.2.2.1 (INM 
    			 procedure)"   
    ::= { xdsl2ExtPMLineCurrEntry 23 }    
    
    xdsl2PMLCurr15MInmEqInp  OBJECT-TYPE
    SYNTAX      Counter32
    MAX-ACCESS  read-only
    STATUS      current
    DESCRIPTION
       "The INM Equivalent Inp histogram during this 15min 
    interval. An array of 68 octets (each 4 octets means amount of
    a bin of histogram), designed for supporting from 1 to 17 bins
    of the histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"   
    ::= { xdsl2ExtPMLineCurrEntry 24 }    
    
    xdsl2PMLCurr15MInmIAT  OBJECT-TYPE
    SYNTAX      Counter32
    MAX-ACCESS  read-only
    STATUS      current
    DESCRIPTION
       "The INM Inter Arrival Time histogram during this 15min 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2ExtPMLineCurrEntry 25 }    
    
    xdsl2PMLCurr15MInmME  OBJECT-TYPE
    SYNTAX      Counter32
    MAX-ACCESS  read-only
    STATUS      current
    DESCRIPTION
       "The INM total measurement during this 15min interval. 
    This indication occurs every time a data symbol is processed 
    by the Impulse Noise Sensor.
       The range of the value is from 0x0 to 0xFFFFFFFF"
    REFERENCE    "ITU-T G.993.2 Amd2, paragraph 11.4.2.2.1 (INM 
    			 procedure)"   
    ::= { xdsl2ExtPMLineCurrEntry 26 }    
    
    xdsl2PMLCurr1DayInmEqInp  OBJECT-TYPE
    SYNTAX      Counter32
    MAX-ACCESS  read-only
    STATUS      current
    DESCRIPTION
       "The INM Equivalent Inp histogram during this 1Day interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"   
    ::= { xdsl2ExtPMLineCurrEntry 27 }    
    
    xdsl2PMLCurr1DayInmIAT  OBJECT-TYPE
    SYNTAX      Counter32
    MAX-ACCESS  read-only
    STATUS      current
    DESCRIPTION
       "The INM Inter Arrival Time histogram during this 1Day 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"   
    ::= { xdsl2ExtPMLineCurrEntry 28 }    
    
    xdsl2PMLCurr1DayInmME  OBJECT-TYPE
    SYNTAX      Counter32
    MAX-ACCESS  read-only
    STATUS      current
    DESCRIPTION
       "The INM total measurement during this 1Day interval. 
    This indication occurs every time a data symbol is processed 
    by the Impulse Noise Sensor.
       The range of the value is from 0x0 to 0xFFFFFFFF"
    REFERENCE    "ITU-T G.993.2 Amd2, paragraph 11.4.2.2.1 (INM 
    			 procedure)"   
    ::= { xdsl2ExtPMLineCurrEntry 29 }       
    
    
-------------------------------------------
-- xdsl2 ext PM line history 15 Minutes  --
-------------------------------------------
    xdsl2ExtPMLineHist15MinTable    OBJECT-TYPE
    SYNTAX      SEQUENCE  OF  Xdsl2ExtPMLineHist15MinEntry
    MAX-ACCESS  not-accessible
    STATUS      current
    DESCRIPTION
       "The table xdsl2ExtPMLineHist15MinTable extends xdsl2PMLineHist15MinTable."
    ::= { xdsl2ExtPMLine 3 }

    xdsl2ExtPMLineHist15MinEntry  OBJECT-TYPE
    SYNTAX      Xdsl2ExtPMLineHist15MinEntry
    MAX-ACCESS  not-accessible
    STATUS      current
    DESCRIPTION
       "The table xdsl2ExtPMLineHist15MinTable extends xdsl2PMLineHist15MinTable."
    INDEX  { ifIndex,
            xdsl2PMLHist15MUnit,
             xdsl2PMLHist15MInterval }
    ::= { xdsl2ExtPMLineHist15MinTable 1 }

    Xdsl2ExtPMLineHist15MinEntry  ::=
    SEQUENCE {
       xdsl2PMLHist15MLofs                Counter32,
       xdsl2PMLHist15MLol                 Counter32,
       xdsl2PMLHist15MLols                Counter32,
       xdsl2PMLHist15MLpr                 Counter32,
       xdsl2PMLHist15MLprs                Counter32,
       xdsl2PMLHist15MInmEqInp            Counter32,
       xdsl2PMLHist15MInmIAT              Counter32,
       xdsl2PMLHist15MInmME               Counter32,
       xdsl2PMLHist15MSnrmAvgUsDs         Counter32,
       xdsl2PMLHist15MSnrmU0D1            Counter32,
       xdsl2PMLHist15MSnrmU1D2            Counter32,
       xdsl2PMLHist15MSnrmU2D3            Counter32,
       xdsl2PMLHist15MSnrmU3D4            Counter32, 
    }

    xdsl2PMLHist15MLofs  OBJECT-TYPE
    SYNTAX      Counter32
    UNITS       "seconds"
    MAX-ACCESS  read-only
    STATUS      current
    DESCRIPTION
       "Count of seconds during this interval that there was LOF."
    ::= { xdsl2ExtPMLineHist15MinEntry 1 }

    xdsl2PMLHist15MLol  OBJECT-TYPE
    SYNTAX      Counter32
    MAX-ACCESS  read-only
    STATUS      current
    DESCRIPTION
       "Count of times during this interval that the line Loss of Link."
    ::= { xdsl2ExtPMLineHist15MinEntry 2 }

    xdsl2PMLHist15MLols  OBJECT-TYPE
    SYNTAX      Counter32
    UNITS       "seconds"
    MAX-ACCESS  read-only
    STATUS      current
    DESCRIPTION
       "Count of seconds during this interval that the line Loss of Link."
    ::= { xdsl2ExtPMLineHist15MinEntry 3 }

    xdsl2PMLHist15MLpr  OBJECT-TYPE
    SYNTAX      Counter32
    MAX-ACCESS  read-only
    STATUS      current
    DESCRIPTION
       "Count of times during this interval that the line Loss of Power."
    ::= { xdsl2ExtPMLineHist15MinEntry 4 }

    xdsl2PMLHist15MLprs  OBJECT-TYPE
    SYNTAX      Counter32
    UNITS       "seconds"
    MAX-ACCESS  read-only
    STATUS      current
    DESCRIPTION
       "Count of seconds during this interval that the line Loss of Power."
    ::= { xdsl2ExtPMLineHist15MinEntry 5 }

    
    xdsl2PMLHist15MInmEqInp  OBJECT-TYPE
    SYNTAX      Counter32
    MAX-ACCESS  read-only
    STATUS      current
    DESCRIPTION
       "The INM Equivalent Inp histogram during 15min interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2ExtPMLineHist15MinEntry 6 }
       
    xdsl2PMLHist15MInmIAT  OBJECT-TYPE
    SYNTAX      Counter32
    MAX-ACCESS  read-only
    STATUS      current
    DESCRIPTION
       "The INM Inter Arrival Time histogram during 15min 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"
    ::= { xdsl2ExtPMLineHist15MinEntry 7 }

    xdsl2PMLHist15MInmME  OBJECT-TYPE
    SYNTAX      Counter32
    MAX-ACCESS  read-only
    STATUS      current
    DESCRIPTION
       "The INM total measurement during 15min interval. 
    This indication occurs every time a data symbol is processed 
    by the Impulse Noise Sensor.
       The range of the value is from 0x0 to 0xFFFFFFFF"
    REFERENCE    "ITU-T G.993.2 Amd2, paragraph 11.4.2.2.1 (INM 
    			 procedure)"
    ::= { xdsl2ExtPMLineHist15MinEntry 8 }         
    
    xdsl2PMLHist15MSnrmAvgUsDs  OBJECT-TYPE
    SYNTAX      Counter32
    MAX-ACCESS  read-only
    STATUS      current
    DESCRIPTION
       "Count of margin during this interval that there was average SNR margin."
    ::= { xdsl2ExtPMLineHist15MinEntry 9 } 
                                              
    xdsl2PMLHist15MSnrmU0D1  OBJECT-TYPE
    SYNTAX      Counter32
    MAX-ACCESS  read-only
    STATUS      current
    DESCRIPTION
       "Count of margin during this interval that there was SNR margin of U0/D1 band.
       Values range from -640 to 630 in units of 0.1 dB (physical
	   values are -64 to 63 dB).
	   A special value of 0x7FFFFFFF (2147483647) indicates the SNR
	   Margin is out of range to be represented.
	   A special value of 0x7FFFFFFE (2147483646) indicates the SNR
	   Margin measurement is currently unavailable.
	   "
       
       ::= { xdsl2ExtPMLineHist15MinEntry 10 }     
    
    xdsl2PMLHist15MSnrmU1D2  OBJECT-TYPE
    SYNTAX      Counter32
    MAX-ACCESS  read-only
    STATUS      current
    DESCRIPTION
       "Count of margin during this interval that there was SNR margin of U1/D2 band.
       Values range from -640 to 630 in units of 0.1 dB (physical
	   values are -64 to 63 dB).
	   A special value of 0x7FFFFFFF (2147483647) indicates the SNR
	   Margin is out of range to be represented.
	   A special value of 0x7FFFFFFE (2147483646) indicates the SNR
	   Margin measurement is currently unavailable.
	   "
    ::= { xdsl2ExtPMLineHist15MinEntry 11 } 

    xdsl2PMLHist15MSnrmU2D3  OBJECT-TYPE
    SYNTAX      Counter32
    MAX-ACCESS  read-only
    STATUS      current
    DESCRIPTION
       "Count of margin during this interval that there was SNR margin of U2/D3 band.
       Values range from -640 to 630 in units of 0.1 dB (physical
	   values are -64 to 63 dB).
	   A special value of 0x7FFFFFFF (2147483647) indicates the SNR
	   Margin is out of range to be represented.
	   A special value of 0x7FFFFFFE (2147483646) indicates the SNR
	   Margin measurement is currently unavailable.
	   "
       
    ::= { xdsl2ExtPMLineHist15MinEntry 12 } 
    
    xdsl2PMLHist15MSnrmU3D4  OBJECT-TYPE
    SYNTAX      Counter32
    MAX-ACCESS  read-only
    STATUS      current
    DESCRIPTION
       "Count of margin during this interval that there was SNR margin of U3/D4 band.
       Values range from -640 to 630 in units of 0.1 dB (physical
	   values are -64 to 63 dB).
	   A special value of 0x7FFFFFFF (2147483647) indicates the SNR
	   Margin is out of range to be represented.
	   A special value of 0x7FFFFFFE (2147483646) indicates the SNR
	   Margin measurement is currently unavailable.
	   "
       
    ::= { xdsl2ExtPMLineHist15MinEntry 13 } 

---------------------------------------
--  Extended  PM line history 1 Day  --
---------------------------------------
    xdsl2ExtPMLineHist1DayTable     OBJECT-TYPE
    SYNTAX      SEQUENCE  OF  Xdsl2ExtPMLineHist1DayEntry
    MAX-ACCESS  not-accessible
    STATUS      current
    DESCRIPTION
       "The table xdsl2ExtPMLineHist1DayTable extends xdsl2PMLineHist1DayTable."
    ::= { xdsl2ExtPMLine 4 }

    xdsl2ExtPMLineHist1DayEntry  OBJECT-TYPE
    SYNTAX      Xdsl2ExtPMLineHist1DayEntry
    MAX-ACCESS  not-accessible
    STATUS      current
    DESCRIPTION
       "The table xdsl2ExtPMLineHist1DayTable extends xdsl2PMLineHist1DayTable."
    INDEX  { ifIndex,
             xdsl2PMLHist1DUnit,
             xdsl2PMLHist1DInterval }
    ::= { xdsl2ExtPMLineHist1DayTable 1 }

    Xdsl2ExtPMLineHist1DayEntry  ::=
    SEQUENCE {
       xdsl2PMLHist1DLofs             Counter32,
       xdsl2PMLHist1DLol              Counter32,
       xdsl2PMLHist1DLols             Counter32,
       xdsl2PMLHist1DLpr              Counter32,
       xdsl2PMLHist1DLprs             Counter32,
       xdsl2PMLHist1DInmEqInp         Counter32,
       xdsl2PMLHist1DInmIAT           Counter32,
       xdsl2PMLHist1DInmME            Counter32
    }

    xdsl2PMLHist1DLofs  OBJECT-TYPE
    SYNTAX      Counter32
    UNITS       "seconds"
    MAX-ACCESS  read-only
    STATUS      current
    DESCRIPTION
       "Count of seconds during this interval that there was LOF."
    ::= { xdsl2ExtPMLineHist1DayEntry 1 }

    xdsl2PMLHist1DLol  OBJECT-TYPE
    SYNTAX      Counter32
    MAX-ACCESS  read-only
    STATUS      current
    DESCRIPTION
       "Count of times during this interval that the line Loss of Link."
    ::= { xdsl2ExtPMLineHist1DayEntry 2 }

    xdsl2PMLHist1DLols  OBJECT-TYPE
    SYNTAX      Counter32
    UNITS       "seconds"
    MAX-ACCESS  read-only
    STATUS      current
    DESCRIPTION
       "Count of seconds during this interval that the line Loss of Link."
    ::= { xdsl2ExtPMLineHist1DayEntry 3 }

    xdsl2PMLHist1DLpr  OBJECT-TYPE
    SYNTAX      Counter32
    MAX-ACCESS  read-only
    STATUS      current
    DESCRIPTION
       "Count of times during this interval that the line Loss of Power."
    ::= { xdsl2ExtPMLineHist1DayEntry 4 }

    xdsl2PMLHist1DLprs  OBJECT-TYPE
    SYNTAX      Counter32
    UNITS       "seconds"
    MAX-ACCESS  read-only
    STATUS      current
    DESCRIPTION
       "Count of seconds during this interval that the line Loss of Power."
    ::= { xdsl2ExtPMLineHist1DayEntry 5 }

    
    xdsl2PMLHist1DInmEqInp  OBJECT-TYPE
    SYNTAX      Counter32
    MAX-ACCESS  read-only
    STATUS      current
    DESCRIPTION
       "The INM Equivalent Inp histogram during 1Day interval. 
    An array of 68 octets (each 4 octets means amount of a bin of 
    histogram), designed for supporting from 1 to 17 bins of the 
    histogram. 
       The particular index of the bin incremented by an impulse
    noise event is equal to the computed value of equivalent INP,
    except the 17th of anomaly INPEQ, which logs all equivalent 
    INPs greater than 16.
       Each bin has a value in the range 0x0 to 0xFFFFFFFF"
    REFERENCE    "ITU-T G.993.2 Amd2, paragraph 11.4.2.2.1 (INM 
    			 procedure)"
    ::= { xdsl2ExtPMLineHist1DayEntry 6 }    
    
    xdsl2PMLHist1DInmIAT  OBJECT-TYPE
    SYNTAX      Counter32
    MAX-ACCESS  read-only
    STATUS      current
    DESCRIPTION
       "The INM Inter Arrival Time histogram during 1Day 
    interval. An array of 32 octets (each 4 octets means amount of 
    a bin of histogram), designed for supporting from 0 to 7 bins 
    of the histogram. 
       The index of the particular bin incremented by an complete 
    impulse noise event is determained from the following 
    INMControl parameters.
       Each bin has a value in the range 0x0 to 0xFFFFFFFF"
    REFERENCE    "ITU-T G.993.2 Amd2, paragraph 11.4.2.2.1 (INM 
    			 procedure)"
    ::= { xdsl2ExtPMLineHist1DayEntry 7 }    
    
    xdsl2PMLHist1DInmME  OBJECT-TYPE
    SYNTAX      Counter32
    MAX-ACCESS  read-only
    STATUS      current
    DESCRIPTION
       "The INM total measurement during this 1Day interval. 
    This indication occurs every time a data symbol is processed 
    by the Impulse Noise Sensor.
       The range of the value is from 0x0 to 0xFFFFFFFF"
    REFERENCE    "ITU-T G.993.2 Amd2, paragraph 11.4.2.2.1 (INM 
    			 procedure)"
    ::= { xdsl2ExtPMLineHist1DayEntry 8 }    
    
    

---------------------------------------------------
--  xdsl2 extended PM channel current counters   --
---------------------------------------------------
    xdsl2ExtPMChCurrTable        OBJECT-TYPE
    SYNTAX      SEQUENCE  OF  Xdsl2ExtPMChCurrEntry
    MAX-ACCESS  not-accessible
    STATUS      current
    DESCRIPTION
       "The table xdsl2PMChCurrTable extends xdsl2PMChCurrTable."
    ::= { xdsl2ExtPMChannel 1 }

    xdsl2ExtPMChCurrEntry  OBJECT-TYPE
    SYNTAX      Xdsl2ExtPMChCurrEntry
    MAX-ACCESS  not-accessible
    STATUS      current
    DESCRIPTION
       "The table xdsl2PMChCurrTable extends xdsl2PMChCurrTable."
    INDEX  { ifIndex, xdsl2PMChCurrUnit }
    ::= { xdsl2ExtPMChCurrTable 1 }

    Xdsl2ExtPMChCurrEntry  ::=
    SEQUENCE {
       xdsl2PMChSinceLinkUncorrectedCWs   Unsigned32,
       xdsl2PMChCurr15MUncorrectedCWs     Unsigned32,
       xdsl2PMChCurr1DayUncorrectedCWs    Unsigned32,
       xdsl2PMChSinceLinkCodingViolations Unsigned32,
       xdsl2PMChSinceLinkCorrectedBlocks  Unsigned32,
       xdsl2PMChSinceLinkRtx              Unsigned32,
       xdsl2PMChCurr15MRtx                Unsigned32,
       xdsl2PMChCurr1DayRtx               Unsigned32,
       xdsl2PMChSinceLinkRtxCorrected     Unsigned32,
       xdsl2PMChCurr15MRtxCorrected       Unsigned32,
       xdsl2PMChCurr1DayRtxCorrected      Unsigned32,
       xdsl2PMChSinceLinkRtxUncorrected   Unsigned32,
       xdsl2PMChCurr15MRtxUncorrected     Unsigned32,
       xdsl2PMChCurr1DayRtxUncorrected    Unsigned32,
       xdsl2PMChSinceLinkLEFTRs           Unsigned32,
       xdsl2PMChCurr15MLEFTRs             Unsigned32,
       xdsl2PMChCurr1DayLEFTRs            Unsigned32,
       xdsl2PMChSinceLinkMinEFTR          Unsigned32,
       xdsl2PMChCurr15MMinEFTR            Unsigned32,
       xdsl2PMChCurr1DayMinEFTR           Unsigned32,
       xdsl2PMChSinceLinkErrFreeBits      Unsigned32,
       xdsl2PMChCurr15MErrFreeBits        Unsigned32,
       xdsl2PMChCurr1DayErrFreeBits       Unsigned32
    }

    xdsl2PMChSinceLinkUncorrectedCWs  OBJECT-TYPE
    SYNTAX      Unsigned32
    MAX-ACCESS  read-only
    STATUS      current
    DESCRIPTION
       "Count of codewords that could not be corrected since last link up."
   ::= { xdsl2ExtPMChCurrEntry 1 }

    xdsl2PMChCurr15MUncorrectedCWs  OBJECT-TYPE
    SYNTAX      Unsigned32
    MAX-ACCESS  read-only
    STATUS      current
    DESCRIPTION
       "Count of codewords that could not be corrected since during this interval."
   ::= { xdsl2ExtPMChCurrEntry 2 }

    xdsl2PMChCurr1DayUncorrectedCWs  OBJECT-TYPE
    SYNTAX      Unsigned32
    MAX-ACCESS  read-only
    STATUS      current
    DESCRIPTION
       "Count of codewords that could not be corrected since during this interval."
   ::= { xdsl2ExtPMChCurrEntry 3 }

    xdsl2PMChSinceLinkCodingViolations  OBJECT-TYPE
    SYNTAX      Unsigned32
    MAX-ACCESS  read-only
    STATUS      current
    DESCRIPTION
       "Count of CRC-8 (FEBE for xTU-R) anomalies occurring in the channel 
        since last link up."
   ::= { xdsl2ExtPMChCurrEntry 4 }

    xdsl2PMChSinceLinkCorrectedBlocks  OBJECT-TYPE
    SYNTAX      Unsigned32
    MAX-ACCESS  read-only
    STATUS      current
    DESCRIPTION
       "Count of FEC (FFEC for xTU-R) anomalies (corrected code words) 
        occurring in the channel since last link up."
   ::= { xdsl2ExtPMChCurrEntry 5 }


    xdsl2PMChSinceLinkRtx  OBJECT-TYPE
    SYNTAX      Unsigned32
    MAX-ACCESS  read-only
    STATUS      current
    DESCRIPTION
       "Number of codewords retransmitted since last link up."
   ::= { xdsl2ExtPMChCurrEntry 6 }

    xdsl2PMChCurr15MRtx  OBJECT-TYPE
    SYNTAX      Unsigned32
    MAX-ACCESS  read-only
    STATUS      current
    DESCRIPTION
       "Number of codewords retransmitted during this interval."
   ::= { xdsl2ExtPMChCurrEntry 7 }

    xdsl2PMChCurr1DayRtx  OBJECT-TYPE
    SYNTAX      Unsigned32
    MAX-ACCESS  read-only
    STATUS      current
    DESCRIPTION
       "Number of codewords retransmitted during this interval."
   ::= { xdsl2ExtPMChCurrEntry 8 }

    xdsl2PMChSinceLinkRtxCorrected  OBJECT-TYPE
    SYNTAX      Unsigned32
    MAX-ACCESS  read-only
    STATUS      current
    DESCRIPTION
       "Number of codewords corrected through retransmission since last link up."
   ::= { xdsl2ExtPMChCurrEntry 9 }

    xdsl2PMChCurr15MRtxCorrected  OBJECT-TYPE
    SYNTAX      Unsigned32
    MAX-ACCESS  read-only
    STATUS      current
    DESCRIPTION
       "Number of codewords corrected through retransmission during this interval."
   ::= { xdsl2ExtPMChCurrEntry 10 }

    xdsl2PMChCurr1DayRtxCorrected  OBJECT-TYPE
    SYNTAX      Unsigned32
    MAX-ACCESS  read-only
    STATUS      current
    DESCRIPTION
       "Number of codewords corrected through retransmission during this interval."
   ::= { xdsl2ExtPMChCurrEntry 11 }

    xdsl2PMChSinceLinkRtxUncorrected  OBJECT-TYPE
    SYNTAX      Unsigned32
    MAX-ACCESS  read-only
    STATUS      current
    DESCRIPTION
       "Number of codewords left uncorrected after retransmission since last link up."
   ::= { xdsl2ExtPMChCurrEntry 12 }

    xdsl2PMChCurr15MRtxUncorrected  OBJECT-TYPE
    SYNTAX      Unsigned32
    MAX-ACCESS  read-only
    STATUS      current
    DESCRIPTION
       "Number of codewords left uncorrected after retransmission during this interval."
   ::= { xdsl2ExtPMChCurrEntry 13 }

    xdsl2PMChCurr1DayRtxUncorrected  OBJECT-TYPE
    SYNTAX      Unsigned32
    MAX-ACCESS  read-only
    STATUS      current
    DESCRIPTION
       "Number of codewords left uncorrected after retransmission during this interval."
   ::= { xdsl2ExtPMChCurrEntry 14 }

    xdsl2PMChSinceLinkLEFTRs  OBJECT-TYPE
    SYNTAX      Unsigned32
    MAX-ACCESS  read-only
    STATUS      current
    DESCRIPTION
       "Low Error-Free Throughput Rate Seconds since last link up."
   ::= { xdsl2ExtPMChCurrEntry 15 }

    xdsl2PMChCurr15MLEFTRs  OBJECT-TYPE
    SYNTAX      Unsigned32
    MAX-ACCESS  read-only
    STATUS      current
    DESCRIPTION
       "Low Error-Free Throughput Rate Seconds during this interval."
   ::= { xdsl2ExtPMChCurrEntry 16 }

    xdsl2PMChCurr1DayLEFTRs  OBJECT-TYPE
    SYNTAX      Unsigned32
    MAX-ACCESS  read-only
    STATUS      current
    DESCRIPTION
       "Low Error-Free Throughput Rate Seconds during this interval."
   ::= { xdsl2ExtPMChCurrEntry 17 }

    xdsl2PMChSinceLinkMinEFTR  OBJECT-TYPE
    SYNTAX      Unsigned32
    MAX-ACCESS  read-only
    STATUS      current
    DESCRIPTION
       "Lowest EFTR observed since last link up."
   ::= { xdsl2ExtPMChCurrEntry 18 }

    xdsl2PMChCurr15MMinEFTR  OBJECT-TYPE
    SYNTAX      Unsigned32
    MAX-ACCESS  read-only
    STATUS      current
    DESCRIPTION
       "Lowest EFTR observed in the current interval."
   ::= { xdsl2ExtPMChCurrEntry 19 }

    xdsl2PMChCurr1DayMinEFTR  OBJECT-TYPE
    SYNTAX      Unsigned32
    MAX-ACCESS  read-only
    STATUS      current
    DESCRIPTION
       "Lowest EFTR observed in the current interval."
   ::= { xdsl2ExtPMChCurrEntry 20 }

    xdsl2PMChSinceLinkErrFreeBits  OBJECT-TYPE
    SYNTAX      Unsigned32
    MAX-ACCESS  read-only
    STATUS      current
    DESCRIPTION
       "The number of bits belonging to correct DTUs leaving the Rx PMS-TC ¡Ñ 2(¡V16) since last link up."
   ::= { xdsl2ExtPMChCurrEntry 21 }

    xdsl2PMChCurr15MErrFreeBits  OBJECT-TYPE
    SYNTAX      Unsigned32
    MAX-ACCESS  read-only
    STATUS      current
    DESCRIPTION
       "The number of bits belonging to correct DTUs leaving the Rx PMS-TC ¡Ñ 2(¡V16) during this interval."
   ::= { xdsl2ExtPMChCurrEntry 22 }

    xdsl2PMChCurr1DayErrFreeBits  OBJECT-TYPE
    SYNTAX      Unsigned32
    MAX-ACCESS  read-only
    STATUS      current
    DESCRIPTION
       "The number of bits belonging to correct DTUs leaving the Rx PMS-TC ¡Ñ 2(¡V16) during this interval."
   ::= { xdsl2ExtPMChCurrEntry 23 }

--------------------------------------------------
-- xdsl2 entended PM channel history 15 Minutes --
--------------------------------------------------
    xdsl2ExtPMChHist15MinTable         OBJECT-TYPE
    SYNTAX      SEQUENCE  OF  Xdsl2ExtPMChHist15MinEntry
    MAX-ACCESS  not-accessible
    STATUS      current
    DESCRIPTION
       "The table xdsl2ExtPMChHist15MinTable extends xdsl2PMChHist15MinTable."
    ::= { xdsl2ExtPMChannel 2 }

    xdsl2ExtPMChHist15MinEntry  OBJECT-TYPE
    SYNTAX      Xdsl2ExtPMChHist15MinEntry
    MAX-ACCESS  not-accessible
    STATUS      current
    DESCRIPTION
       "The table xdsl2ExtPMChHist15MinTable extends xdsl2PMChHist15MinTable."
    INDEX  { ifIndex,
             xdsl2PMChHist15MUnit,
             xdsl2PMChHist15MInterval }
    ::= { xdsl2ExtPMChHist15MinTable 1 }

    Xdsl2ExtPMChHist15MinEntry  ::=
    SEQUENCE {
       xdsl2PMChHist15MUncorrectedCWs          Unsigned32,
       xdsl2PMChHist15MRtx                     Unsigned32,
       xdsl2PMChHist15MRtxCorrected            Unsigned32,
       xdsl2PMChHist15MRtxUncorrected          Unsigned32,
       xdsl2PMChHist15MLEFTRs                  Unsigned32,
       xdsl2PMChHist15MMinEFTR                 Unsigned32,
       xdsl2PMChHist15MErrFreeBits             Unsigned32
    }

    xdsl2PMChHist15MUncorrectedCWs  OBJECT-TYPE
    SYNTAX      Unsigned32
    MAX-ACCESS  read-only
    STATUS      current
    DESCRIPTION
       "Count of codewords that could not be corrected since during this interval."
    ::= { xdsl2ExtPMChHist15MinEntry 1 }

    xdsl2PMChHist15MRtx  OBJECT-TYPE
    SYNTAX      Unsigned32
    MAX-ACCESS  read-only
    STATUS      current
    DESCRIPTION
       "Number of codewords retransmitted during this interval."
    ::= { xdsl2ExtPMChHist15MinEntry 2 }
    
    xdsl2PMChHist15MRtxCorrected  OBJECT-TYPE
    SYNTAX      Unsigned32
    MAX-ACCESS  read-only
    STATUS      current
    DESCRIPTION
       "Number of codewords corrected through retransmission during this interval."
    ::= { xdsl2ExtPMChHist15MinEntry 3 }
    
    xdsl2PMChHist15MRtxUncorrected  OBJECT-TYPE
    SYNTAX      Unsigned32
    MAX-ACCESS  read-only
    STATUS      current
    DESCRIPTION
       "Number of codewords left uncorrected after retransmission during this interval."
    ::= { xdsl2ExtPMChHist15MinEntry 4 }
    
    xdsl2PMChHist15MLEFTRs  OBJECT-TYPE
    SYNTAX      Unsigned32
    MAX-ACCESS  read-only
    STATUS      current
    DESCRIPTION
       "Low Error-Free Throughput Rate Seconds during this interval."
    ::= { xdsl2ExtPMChHist15MinEntry 5 }
    
    xdsl2PMChHist15MMinEFTR  OBJECT-TYPE
    SYNTAX      Unsigned32
    MAX-ACCESS  read-only
    STATUS      current
    DESCRIPTION
       "Lowest EFTR observed in the current interval."
    ::= { xdsl2ExtPMChHist15MinEntry 6 }
    
    xdsl2PMChHist15MErrFreeBits  OBJECT-TYPE
    SYNTAX      Unsigned32
    MAX-ACCESS  read-only
    STATUS      current
    DESCRIPTION
       "The number of bits belonging to correct DTUs leaving the Rx PMS-TC ¡Ñ 2(¡V16) during this interval."
    ::= { xdsl2ExtPMChHist15MinEntry 7 }

------------------------------------------
--        PM channel history 1 Day      --
------------------------------------------
    xdsl2ExtPMChHist1DTable         OBJECT-TYPE
    SYNTAX      SEQUENCE  OF  Xdsl2ExtPMChHist1DEntry
    MAX-ACCESS  not-accessible
    STATUS      current
    DESCRIPTION
       "The table xdsl2ExtPMChHist1DTable extends xdsl2PMChHist1DTable."
    ::= { xdsl2ExtPMChannel 3 }

    xdsl2ExtPMChHist1DEntry  OBJECT-TYPE
    SYNTAX      Xdsl2ExtPMChHist1DEntry
    MAX-ACCESS  not-accessible
    STATUS      current
    DESCRIPTION
       "The table xdsl2ExtPMChHist1DTable extends xdsl2PMChHist1DTable."
    INDEX  { ifIndex,
             xdsl2PMChHist1DUnit,
             xdsl2PMChHist1DInterval }
    ::= { xdsl2ExtPMChHist1DTable 1 }

    Xdsl2ExtPMChHist1DEntry  ::=
    SEQUENCE {
       xdsl2PMChHist1DayUncorrectedCWs          Unsigned32,
       xdsl2PMChHist1DayRtx                     Unsigned32,
       xdsl2PMChHist1DayRtxCorrected            Unsigned32,
       xdsl2PMChHist1DayRtxUncorrected          Unsigned32,
       xdsl2PMChHist1DayLEFTRs                  Unsigned32,
       xdsl2PMChHist1DayMinEFTR                 Unsigned32,
       xdsl2PMChHist1DayErrFreeBits             Unsigned32
    }

    xdsl2PMChHist1DayUncorrectedCWs  OBJECT-TYPE
    SYNTAX      Unsigned32
    MAX-ACCESS  read-only
    STATUS      current
    DESCRIPTION
       "Count of codewords that could not be corrected since during this interval."
    ::= { xdsl2ExtPMChHist1DEntry 1 }

    xdsl2PMChHist1DayRtx  OBJECT-TYPE
    SYNTAX      Unsigned32
    MAX-ACCESS  read-only
    STATUS      current
    DESCRIPTION
       "Number of codewords retransmitted during this interval."
    ::= { xdsl2ExtPMChHist1DEntry 2 }
    
    xdsl2PMChHist1DayRtxCorrected  OBJECT-TYPE
    SYNTAX      Unsigned32
    MAX-ACCESS  read-only
    STATUS      current
    DESCRIPTION
       "Number of codewords corrected through retransmission during this interval."
    ::= { xdsl2ExtPMChHist1DEntry 3 }
    
    xdsl2PMChHist1DayRtxUncorrected  OBJECT-TYPE
    SYNTAX      Unsigned32
    MAX-ACCESS  read-only
    STATUS      current
    DESCRIPTION
       "Number of codewords left uncorrected after retransmission during this interval."
    ::= { xdsl2ExtPMChHist1DEntry 4 }
    
    xdsl2PMChHist1DayLEFTRs  OBJECT-TYPE
    SYNTAX      Unsigned32
    MAX-ACCESS  read-only
    STATUS      current
    DESCRIPTION
       "Low Error-Free Throughput Rate Seconds during this interval."
    ::= { xdsl2ExtPMChHist1DEntry 5 }
    
    xdsl2PMChHist1DayMinEFTR  OBJECT-TYPE
    SYNTAX      Unsigned32
    MAX-ACCESS  read-only
    STATUS      current
    DESCRIPTION
       "Lowest EFTR observed in the current interval."
    ::= { xdsl2ExtPMChHist1DEntry 6 }
    
    xdsl2PMChHist1DayErrFreeBits  OBJECT-TYPE
    SYNTAX      Unsigned32
    MAX-ACCESS  read-only
    STATUS      current
    DESCRIPTION
       "The number of bits belonging to correct DTUs leaving the Rx PMS-TC ¡Ñ 2(¡V16) during this interval."
    ::= { xdsl2ExtPMChHist1DEntry 7 }

------------------------------------------------
--     xdsl2ExtLineConfTemplateTable          --
------------------------------------------------
    xdsl2ExtLineConfTemplateTable  OBJECT-TYPE
    SYNTAX      SEQUENCE  OF  Xdsl2ExtLineConfTemplateEntry
    MAX-ACCESS  not-accessible
    STATUS      current
    DESCRIPTION
       "The table xdsl2ExtLineConfTemplateTable extends xdsl2LineConfTemplateTable."
    ::= { xdsl2ExtProfileLine 1 }

    xdsl2ExtLineConfTemplateEntry  OBJECT-TYPE
    SYNTAX      Xdsl2ExtLineConfTemplateEntry
    MAX-ACCESS  not-accessible
    STATUS      current
    DESCRIPTION
       "TThe table xdsl2ExtLineConfTemplateTable extends xdsl2LineConfTemplateTable."
    INDEX  { xdsl2LConfTempTemplateName }
    ::= { xdsl2ExtLineConfTemplateTable 1 }

    Xdsl2ExtLineConfTemplateEntry  ::=
    SEQUENCE {
       xdsl2LConfTempPortList      PortList,
       xdsl2LConfTempInmConfProfile  SnmpAdminString
    }

    xdsl2LConfTempPortList  OBJECT-TYPE
    SYNTAX      PortList
    MAX-ACCESS      read-only
    STATUS      current
    DESCRIPTION
       "A port list that indicates which ports this template applys for."
    REFERENCE    ""
    ::= { xdsl2ExtLineConfTemplateEntry 1 }

    xdsl2LConfTempInmConfProfile  OBJECT-TYPE
	SYNTAX      SnmpAdminString (SIZE(1..32))
	MAX-ACCESS  read-create
	STATUS      current
	DESCRIPTION   
	  "The value of this object identifies the row in the
       VDSL2/ADSL/ADSL2 and ADSL2+ INM configuration Profile Table,
       (xdsl2ExtInmConfProfTable) that applies for this DSL line."
	DEFVAL       { "DEFVAL" }
	::= { xdsl2ExtLineConfTemplateEntry 2 }


------------------------------------------
--      xdsl2ExtLineConfProfTable       --
------------------------------------------
    xdsl2ExtLineConfProfTable  OBJECT-TYPE
    SYNTAX      SEQUENCE  OF  Xdsl2ExtLineConfProfEntry
    MAX-ACCESS  not-accessible
    STATUS      current
    DESCRIPTION
       "The table xdsl2ExtLineConfProfTable extends xdsl2LineConfProfTable."
    ::= { xdsl2ExtProfileLine 2 }

    xdsl2ExtLineConfProfEntry  OBJECT-TYPE
    SYNTAX      Xdsl2ExtLineConfProfEntry
    MAX-ACCESS  not-accessible
    STATUS      current
    DESCRIPTION
       "The table xdsl2ExtLineConfProfTable extends xdsl2LineConfProfTable."
    INDEX  { xdsl2LConfProfProfileName }
    ::= { xdsl2ExtLineConfProfTable 1 }

    Xdsl2ExtLineConfProfEntry  ::=
    SEQUENCE {
       xdsl2LConfProfBitSwapDs     Unsigned32,
       xdsl2LConfProfBitSwapUs     Unsigned32,
       xdsl2LConfProfPortList      PortList,
       xdsl2LConfProfSosTimeDs     Unsigned32,
       xdsl2LConfProfSosTimeUs     Unsigned32,
       xdsl2LConfProfSosCrcDs      Unsigned32,
       xdsl2LConfProfSosCrcUs      Unsigned32,
       xdsl2LConfProfSosNToneDs    Unsigned32,   
       xdsl2LConfProfSosNToneUs    Unsigned32,
       xdsl2LConfProfSosMaxDs      Unsigned32,
       xdsl2LConfProfSosMaxUs      Unsigned32,
       xdsl2LConfProfSosMultiStepDs	BITS,
       xdsl2LConfProfSosMultiStepUs BITS,
       xdsl2LConfProfRocEnableDs   Unsigned32,
       xdsl2LConfProfRocEnableUs   Unsigned32,
       xdsl2LConfProfRocSnrmDs     Unsigned32,
       xdsl2LConfProfRocSnrmUs     Unsigned32,
       xdsl2LConfProfRocMinInpDs   Unsigned32,
       xdsl2LConfProfRocMinInpUs   Unsigned32,
       xdsl2LConfProfDynamicDepthDs     Unsigned32,
       xdsl2LConfProfDynamicDepthUs     Unsigned32
    }

    xdsl2LConfProfBitSwapDs OBJECT-TYPE
    SYNTAX Unsigned32 
    MAX-ACCESS  read-write
    STATUS  current
    DESCRIPTION
       "This configuration parameter indicates if the use of bitswap is
        disabled on downstream direction.
        The possible values are:
        disable(0),
        enable(1)"
    ::= { xdsl2ExtLineConfProfEntry 1 }

    xdsl2LConfProfBitSwapUs OBJECT-TYPE
    SYNTAX Unsigned32 
    MAX-ACCESS  read-write
    STATUS  current
    DESCRIPTION
       "This configuration parameter indicates if the use of bitswap is
        disabled on upstream direction.
        The possible values are:
        disable(0),
        enable(1)"
    ::= { xdsl2ExtLineConfProfEntry 2 }

    xdsl2LConfProfPortList  OBJECT-TYPE
    SYNTAX      PortList
    MAX-ACCESS      read-only
    STATUS      current
    DESCRIPTION
       "A port list that indicates which ports this profile applys for."
    REFERENCE    ""
    ::= { xdsl2ExtLineConfProfEntry 3 }

    xdsl2LConfProfSosTimeDs OBJECT-TYPE
    SYNTAX Unsigned32 
    MAX-ACCESS  read-write
    STATUS  current
    DESCRIPTION
       "The parameter SOS-TIME-ds is used in the specification of the receiver initiated SOS 
       (see 13.4.3/G.993.2). If the value of this parameter is not zero, the standard SOS 
       triggering criteria are enabled, and the value corresponds with duration of the time 
       window used in the standard SOS triggering criteria in the downstream direction. 
       See G.993.2 for detailed usage rules.
		
	   The special value zero indicates that the standard SOS triggering criteria are disabled, 
	   i.e., vendor-discretionary values may be used instead of the values configured in the MIB 
	   for the following parameters: SOS-NTONES-ds, SOS-CRC-ds, SOS-TIME-ds.
	   
	   This parameter applies in the downstream direction. The valid range of non-zero values 
	   is from 64 ms to 16320 ms in steps of 64 ms.
       "
    ::= { xdsl2ExtLineConfProfEntry 4 }

    xdsl2LConfProfSosTimeUs OBJECT-TYPE
    SYNTAX Unsigned32 
    MAX-ACCESS  read-write
    STATUS  current
    DESCRIPTION
       "The parameter SOS-TIME-u	s is used in the specification of the receiver initiated SOS 
       (see 13.4.3/G.993.2). If the value of this parameter is not zero, the standard SOS 
       triggering criteria are enabled, and the value corresponds with duration of the time 
       window used in the standard SOS triggering criteria in the downstream direction. 
       See G.993.2 for detailed usage rules.
		
	   The special value zero indicates that the standard SOS triggering criteria are disabled, 
	   i.e., vendor-discretionary values may be used instead of the values configured in the MIB 
	   for the following parameters: SOS-NTONES-ds, SOS-CRC-ds, SOS-TIME-ds.
	   
	   This parameter applies in the downstream direction. The valid range of non-zero values 
	   is from 64 ms to 16320 ms in steps of 64 ms.
       "
    ::= { xdsl2ExtLineConfProfEntry 5 }
   
    xdsl2LConfProfSosCrcDs OBJECT-TYPE
    SYNTAX Unsigned32 
    MAX-ACCESS  read-write
    STATUS  current
    DESCRIPTION
       "This parameter is defined as the minimum number of normalized CRC anomalies received 
       in SOS-TIME-ds seconds in order to arm the second sub condition of the standard SOS 
       triggering criteria (see 13.4.3.2/G.993.2) in the downstream direction. See G.993.2 
       for detailed usage rules. The valid range of SOS-CRC values is 0.02 to ((2^16)-1)*0.02, 
       in steps of 0.02."
    ::= { xdsl2ExtLineConfProfEntry 6 }

    xdsl2LConfProfSosCrcUs OBJECT-TYPE
    SYNTAX Unsigned32 
    MAX-ACCESS  read-write
    STATUS  current
    DESCRIPTION
       "This parameter is defined as the minimum number of normalized CRC anomalies received 
       in SOS-TIME-ds seconds in order to arm the second sub condition of the standard SOS 
       triggering criteria (see 13.4.3.2/G.993.2) in the downstream direction. See G.993.2 
       for detailed usage rules. The valid range of SOS-CRC values is 0.02 to ((2^16)-1)*0.02, 
       in steps of 0.02."
    ::= { xdsl2ExtLineConfProfEntry 7 }

    xdsl2LConfProfSosNToneDs OBJECT-TYPE
    SYNTAX Unsigned32 
    MAX-ACCESS  read-write
    STATUS  current
    DESCRIPTION
       "This parameter is defined as the minimum percentage of tones in the downstream 
       MEDLEY SET that must be degraded in order to arm the first sub-condition of the 
       standard SOS triggering criteria (see 13.4.3.2/G.993.2) in the downstream direction. 
       The parameter SOS-NTONES-ds is defined as a percentage of tones. See G.993.2 for 
       detailed usage rules. The valid range of values is from 1 to 100 in steps of 1. 
       Use of the special value 0 is described in 13.4.3.2/G.993.2."
    ::= { xdsl2ExtLineConfProfEntry 8 }

    xdsl2LConfProfSosNToneUs OBJECT-TYPE
    SYNTAX Unsigned32 
    MAX-ACCESS  read-write
    STATUS  current
    DESCRIPTION
       "This parameter is defined as the minimum percentage of tones in the downstream 
       MEDLEY SET that must be degraded in order to arm the first sub-condition of the 
       standard SOS triggering criteria (see 13.4.3.2/G.993.2) in the downstream direction. 
       The parameter SOS-NTONES-ds is defined as a percentage of tones. See G.993.2 for 
       detailed usage rules. The valid range of values is from 1 to 100 in steps of 1. 
       Use of the special value 0 is described in 13.4.3.2/G.993.2."
    ::= { xdsl2ExtLineConfProfEntry 9 }

    xdsl2LConfProfSosMaxDs OBJECT-TYPE
    SYNTAX Unsigned32 
    MAX-ACCESS  read-write
    STATUS  current
    DESCRIPTION
       "This parameter is used in G.993.2 de-activation (see 12.1.4/G.993.2). If the number 
       of successful SOS procedures in the downstream direction performed within a 120-second 
       interval exceeds MAX-SOS-ds, the modem shall transition to the L3 state. See G.993.2 
       for detailed usage rules (see 12.1.4/G.993.2). The valid range of values is 1 to 15. 
       Use of the special value 0 is described in 12.1/G.993.2."
    ::= { xdsl2ExtLineConfProfEntry 10 }

    xdsl2LConfProfSosMaxUs OBJECT-TYPE
    SYNTAX Unsigned32 
    MAX-ACCESS  read-write
    STATUS  current
    DESCRIPTION
       "This parameter is used in G.993.2 de-activation (see 12.1.4/G.993.2). If the number 
       of successful SOS procedures in the downstream direction performed within a 120-second 
       interval exceeds MAX-SOS-ds, the modem shall transition to the L3 state. See G.993.2 
       for detailed usage rules (see 12.1.4/G.993.2). The valid range of values is 1 to 15. 
       Use of the special value 0 is described in 12.1/G.993.2."
    ::= { xdsl2ExtLineConfProfEntry 11 }

    xdsl2LConfProfSosMultiStepDs OBJECT-TYPE
    SYNTAX BITS 
    MAX-ACCESS  read-write
    STATUS  current
    DESCRIPTION
       "Indicates the capabilities of the VTU-R to execute the SOS request in one step or in
		multiple steps in the downstream direction. The field is formatted as [gggg 0000]. 
		The first four MSBs [gggg] indicate the maximum number of tones (GSOS) that can be 
		executed in a single step (GSOS)in the downstream direction. The valid values are:
		- [0000]: No limitation
		- [0010]: GSOS = 256 tones
		- [0011]: GSOS = 512 tones
		- [0100]: GSOS = 1024 tones"
    ::= { xdsl2ExtLineConfProfEntry 12 }

    xdsl2LConfProfSosMultiStepUs OBJECT-TYPE
    SYNTAX BITS 
    MAX-ACCESS  read-write
    STATUS  current
    DESCRIPTION
       "Indicates the capabilities of the VTU-R to execute the SOS request in one step or in
		multiple steps in the downstream direction. The field is formatted as [gggg 0000]. 
		The first four MSBs [gggg] indicate the maximum number of tones (GSOS) that can be 
		executed in a single step (GSOS)in the downstream direction. The valid values are:
		- [0000]: No limitation
		- [0010]: GSOS = 256 tones
		- [0011]: GSOS = 512 tones
		- [0100]: GSOS = 1024 tones"
    ::= { xdsl2ExtLineConfProfEntry 13 }

    xdsl2LConfProfRocEnableDs OBJECT-TYPE
    SYNTAX Unsigned32 
    MAX-ACCESS  read-write
    STATUS  current
    DESCRIPTION
       "Enable the robust overhead channel.
        disable(0),
        enable(1)"
    ::= { xdsl2ExtLineConfProfEntry 14 }

    xdsl2LConfProfRocEnableUs OBJECT-TYPE
    SYNTAX Unsigned32 
    MAX-ACCESS  read-write
    STATUS  current
    DESCRIPTION
       "Enable the robust overhead channel.
        disable(0),
        enable(1)"
    ::= { xdsl2ExtLineConfProfEntry 15 }

    xdsl2LConfProfRocSnrmDs OBJECT-TYPE
    SYNTAX Unsigned32 
    MAX-ACCESS  read-write
    STATUS  current
    DESCRIPTION
       "The parameter is defined as the SNR margin offset for the ROC channel in the downstream 
       	direction. The parameter is used in the specification of the channel initialization 
       	policy (see 12.3.7.1/G.993.2).
		The valid range of SNR margin offset values is from 0 to 31 dB with 0.1 dB steps."
    ::= { xdsl2ExtLineConfProfEntry 16 }

    xdsl2LConfProfRocSnrmUs OBJECT-TYPE
    SYNTAX Unsigned32 
    MAX-ACCESS  read-write
    STATUS  current
    DESCRIPTION
       "The parameter is defined as the SNR margin offset for the ROC channel in the downstream 
       	direction. The parameter is used in the specification of the channel initialization 
       	policy (see 12.3.7.1/G.993.2).
		The valid range of SNR margin offset values is from 0 to 31 dB with 0.1 dB steps."
    ::= { xdsl2ExtLineConfProfEntry 17 }
 
    xdsl2LConfProfRocMinInpDs OBJECT-TYPE
    SYNTAX Unsigned32 
    MAX-ACCESS  read-write
    STATUS  current
    DESCRIPTION
       "This parameter contains the minimum impulse noise protection to apply on the ROC in the 
       downstream direction. The minimum impulse noise protection is an integer ranging from 
       0 to 16."
    ::= { xdsl2ExtLineConfProfEntry 18 }

    xdsl2LConfProfRocMinInpUs OBJECT-TYPE
    SYNTAX Unsigned32 
    MAX-ACCESS  read-write
    STATUS  current
    DESCRIPTION
       "This parameter contains the minimum impulse noise protection to apply on the ROC in the 
       downstream direction. The minimum impulse noise protection is an integer ranging from 
       0 to 16."
    ::= { xdsl2ExtLineConfProfEntry 19 }
   
    xdsl2LConfProfDynamicDepthDs OBJECT-TYPE
    SYNTAX Unsigned32 
    MAX-ACCESS  read-write
    STATUS  current
    DESCRIPTION
       "This configuration parameter indicates if the use of Dynamic Depth is
        disabled on downstream direction.
        The possible values are:
        disable(0),
        enable(1)"
    ::= { xdsl2ExtLineConfProfEntry 20 }

    xdsl2LConfProfDynamicDepthUs OBJECT-TYPE
    SYNTAX Unsigned32 
    MAX-ACCESS  read-write
    STATUS  current
    DESCRIPTION
       "This configuration parameter indicates if the use of Dynamic Depth is
        disabled on upstream direction.
        The possible values are:
        disable(0),
        enable(1)"
    ::= { xdsl2ExtLineConfProfEntry 21 }
    xdsl2MaxNumLineConfTemplate OBJECT-TYPE
    SYNTAX  Unsigned32
    MAX-ACCESS  read-only
    STATUS  current
    DESCRIPTION
        "The maximum number of VDSL line template."
    ::= { xdsl2ExtProfileLine 5 }

    xdsl2MaxNumLineConfProfile OBJECT-TYPE
    SYNTAX  Unsigned32
    MAX-ACCESS  read-only
    STATUS  current
    DESCRIPTION
        "The maximum number of VDSL line profile."
    ::= { xdsl2ExtProfileLine 6 }

------------------------------------------
--        xdsl2ExtInmConfProfTable      --
------------------------------------------
	xdsl2ExtInmConfProfTable  OBJECT-TYPE
    SYNTAX      SEQUENCE  OF  Xdsl2ExtInmConfProfEntry
    MAX-ACCESS  not-accessible
    STATUS      current
    DESCRIPTION
       "xdsl2ExtInmConfProfTable."
    REFERENCE    "ITU-T G.993.2 Amd2, paragraph 11.4.2.2.1 (INM 
    			 procedure)"   
    ::= { xdsl2ExtProfileLine 7 }

    xdsl2ExtInmConfProfEntry  OBJECT-TYPE
    SYNTAX      Xdsl2ExtInmConfProfEntry
    MAX-ACCESS  not-accessible
    STATUS      current
    DESCRIPTION
       "xdsl2ExtInmConfProfTable." 
    REFERENCE    "ITU-T G.993.2 Amd2, paragraph 11.4.2.2.1 (INM 
    			 procedure)"
    INDEX  { xdsl2ExtInmConfProfProfileName }
    ::= { xdsl2ExtInmConfProfTable 1 }

    Xdsl2ExtInmConfProfEntry  ::=
	SEQUENCE {
      xdsl2ExtInmConfProfProfileName		SnmpAdminString,
      xdsl2ExtInmConfProfVtucInpEq			Unsigned32,
      xdsl2ExtInmConfProfVturInpEq			Unsigned32,
      xdsl2ExtInmConfProfVtucCC            	Unsigned32,
      xdsl2ExtInmConfProfVturCC            	Unsigned32,
      xdsl2ExtInmConfProfVtucIATO			Unsigned32,
      xdsl2ExtInmConfProfVturIATO			Unsigned32,
      xdsl2ExtInmConfProfVtucIATS			Unsigned32,
      xdsl2ExtInmConfProfVturIATS			Unsigned32, 
      xdsl2ExtInmConfProfRowStatus          RowStatus,
      xdsl2ExtInmConfProfPortList			PortList
	}

	xdsl2ExtInmConfProfProfileName  OBJECT-TYPE
	SYNTAX      SnmpAdminString (SIZE(1..32))
	MAX-ACCESS  not-accessible
	STATUS      current
	DESCRIPTION
      "This object identifies a row in this table."
    REFERENCE    "ITU-T G.993.2 Amd2, paragraph 11.4.2.2.1 (INM 
    			 procedure)"
     ::= { xdsl2ExtInmConfProfEntry 1 }

    xdsl2ExtInmConfProfVtucInpEq OBJECT-TYPE
    SYNTAX Unsigned32 (0..3)
    MAX-ACCESS  read-write
    STATUS  current
    DESCRIPTION
       "The INM Inmpulse Noise Protection Equivalent Mode. 
    Configuration parameter INM_INPEQ_MODE defines the way of 
    computation of Equivalent INP, as defined in ITU-T G.993.2 Amd2 
    11.4.2.2.1
       This takes a value in the range from 0 to 3."
    REFERENCE    "ITU-T G.993.2 Amd2, paragraph 11.4.2.2.1 (INM 
    			 procedure)"
    DEFVAL       { 0 }
    ::= { xdsl2ExtInmConfProfEntry 2 }

    xdsl2ExtInmConfProfVturInpEq OBJECT-TYPE
    SYNTAX Unsigned32 (0..3)
    MAX-ACCESS  read-write
    STATUS  current
    DESCRIPTION
       "The INM Inmpulse Noise Protection Equivalent Mode. 
    Configuration parameter INM_INPEQ_MODE defines the way of 
    computation of Equivalent INP, as defined in ITU-T G.993.2 Amd2 
    11.4.2.2.1
       This takes a value in the range from 0 to 3."
    REFERENCE    "ITU-T G.993.2 Amd2, paragraph 11.4.2.2.1 (INM 
    			 procedure)"
    DEFVAL       { 0 }
    ::= { xdsl2ExtInmConfProfEntry 3 }

    xdsl2ExtInmConfProfVtucCC OBJECT-TYPE
    SYNTAX Unsigned32 
    MAX-ACCESS  read-write
    STATUS  current
    DESCRIPTION
       "The INM Cluster Continuation. The valid values for INMCC range 
    from 0 from 64 DMT symbols in steps of 1 DMT symbol.
       Up to and including INMCC nondegraded symbols will be allowed before
    a cluster is deemed to be complete and the impulse noise event over."
    REFERENCE    "ITU-T G.993.2 Amd2, paragraph 11.4.2.2.1 (INM 
    			 procedure)"  
    DEFVAL       { 0 }
    ::= { xdsl2ExtInmConfProfEntry 4 } 
    
    xdsl2ExtInmConfProfVturCC OBJECT-TYPE
    SYNTAX Unsigned32 
    MAX-ACCESS  read-write
    STATUS  current
    DESCRIPTION
       "The INM Cluster Continuation. The valid values for INMCC range 
    from 0 from 64 DMT symbols in steps of 1 DMT symbol.
       Up to and including INMCC nondegraded symbols will be allowed before
    a cluster is deemed to be complete and the impulse noise event over."
    REFERENCE    "ITU-T G.993.2 Amd2, paragraph 11.4.2.2.1 (INM 
    			 procedure)"  
    DEFVAL       { 0 }
    ::= { xdsl2ExtInmConfProfEntry 5 }
    
    xdsl2ExtInmConfProfVtucIATO OBJECT-TYPE
    SYNTAX Unsigned32 
    MAX-ACCESS  read-write
    STATUS  current
    DESCRIPTION
       "The INM Inter Arrival Time Offset for the IAT anomaly generation. 
    The valid values for INMIATO range from 3 from 511 DMT symbols in steps
    of 1 DMT symbol."
    REFERENCE    "ITU-T G.993.2 Amd2, paragraph 11.4.2.2.1 (INM 
    			 procedure)"     
    DEFVAL       { 3 }    
    ::= { xdsl2ExtInmConfProfEntry 6 }
    
    xdsl2ExtInmConfProfVturIATO OBJECT-TYPE
    SYNTAX Unsigned32 
    MAX-ACCESS  read-write
    STATUS  current
    DESCRIPTION
       "The INM Inter Arrival Time Offset for the IAT anomaly generation. 
    The valid values for INMIATO range from 3 from 511 DMT symbols in steps
    of 1 DMT symbol."
    REFERENCE    "ITU-T G.993.2 Amd2, paragraph 11.4.2.2.1 (INM 
    			 procedure)"     
    DEFVAL       { 3 }    
    ::= { xdsl2ExtInmConfProfEntry 7 }    

    xdsl2ExtInmConfProfVtucIATS OBJECT-TYPE
    SYNTAX Unsigned32 
    MAX-ACCESS  read-write
    STATUS  current
    DESCRIPTION
       "The INM Inter Arrival Time Step for the IAT anomaly generation. 
    The valid values for INMIATS range from 0 from 7 in steps. The range of 
    values of inter-arrival times recorded in a single bin is 2^(INMIATS).
    All inter-arrival times greater than or equal to INMIATO+6*(2^INMIATS)
    are recorded in the 7th bin of INMAIAT."
    REFERENCE    "ITU-T G.993.2 Amd2, paragraph 11.4.2.2.1 (INM 
    			 procedure)"     
    DEFVAL       { 0 }    
    ::= { xdsl2ExtInmConfProfEntry 8 }

    xdsl2ExtInmConfProfVturIATS OBJECT-TYPE
    SYNTAX Unsigned32 
    MAX-ACCESS  read-write
    STATUS  current
    DESCRIPTION
       "The INM Inter Arrival Time Step for the IAT anomaly generation. 
    The valid values for INMIATS range from 0 from 7 in steps. The range of 
    values of inter-arrival times recorded in a single bin is 2^(INMIATS).
    All inter-arrival times greater than or equal to INMIATO+6*(2^INMIATS)
    are recorded in the 7th bin of INMAIAT."
    REFERENCE    "ITU-T G.993.2 Amd2, paragraph 11.4.2.2.1 (INM 
    			 procedure)"     
    DEFVAL       { 0 }    
    ::= { xdsl2ExtInmConfProfEntry 9 }

    xdsl2ExtInmConfProfRowStatus  OBJECT-TYPE
    SYNTAX      RowStatus
    MAX-ACCESS  read-create
    STATUS      current
    DESCRIPTION
      "This object is used to create a new row or to modify or
 	delete an existing row in this table."
    ::= { xdsl2ExtInmConfProfEntry 14 }
    
    xdsl2ExtInmConfProfPortList  OBJECT-TYPE
    SYNTAX      PortList
    MAX-ACCESS      read-only
    STATUS      current
    DESCRIPTION
       "A port list that indicates which ports this profile applys for."
    REFERENCE    ""
    ::= { xdsl2ExtInmConfProfEntry 15 }
    
    xdsl2MaxNumInmConfProfile OBJECT-TYPE
    SYNTAX  Unsigned32
    MAX-ACCESS  read-only
    STATUS  current
    DESCRIPTION
        "The maximum number of VDSL Inm profile."
    ::= { xdsl2ExtProfileLine 8 }         

------------------------------------------------
--        xdsl2ExtChConfProfileTable          --
------------------------------------------------
    xdsl2ExtChConfProfileTable  OBJECT-TYPE
    SYNTAX      SEQUENCE  OF  Xdsl2ExtChConfProfileEntry
    MAX-ACCESS  not-accessible
    STATUS      current
    DESCRIPTION
       "The table xdsl2ExtChConfProfileTable extends xdsl2ExtChConfProfileTable."
    ::= { xdsl2ExtProfileChannel 1 }

    Xdsl2ConfigRtxMode ::= TEXTUAL-CONVENTION
    STATUS      current
    DESCRIPTION
       "forbidden(0) - Support for G998.4 is disabled.
        preferred(1) - If G998.4 is supported by the far-end, it is enabled.
        forced(2)    - The line will only train if G998.4 can be enabled.
        test(3)      - G998.4 is enabled in test mode (refer to G998.4, Clause 10.4)."
    SYNTAX      INTEGER {
    	forbidden(0),
        preferred(1),
        forced(2),
        test(3)
    }

    xdsl2ExtChConfProfileEntry  OBJECT-TYPE
    SYNTAX      Xdsl2ExtChConfProfileEntry
    MAX-ACCESS  not-accessible
    STATUS      current
    DESCRIPTION
       "The table xdsl2ExtChConfProfileTable extends xdsl2ExtChConfProfileTable."
    INDEX  { xdsl2ChConfProfProfileName }
    ::= { xdsl2ExtChConfProfileTable 1 }

    Xdsl2ExtChConfProfileEntry  ::=
    SEQUENCE {
       xdsl2ChConfProfPhyRDs        Unsigned32,
       xdsl2ChConfProfPhyRUs        Unsigned32,
       xdsl2ChConfProfPortList      OCTET STRING,
       xdsl2ChConfProfGinpRtxModeDs        Xdsl2ConfigRtxMode,
       xdsl2ChConfProfGinpRtxModeUs        Xdsl2ConfigRtxMode,
       xdsl2ChConfProfGinpEtrMaxDs        Unsigned32,
       xdsl2ChConfProfGinpEtrMaxUs        Unsigned32,
       xdsl2ChConfProfGinpEtrMinDs        Unsigned32,
       xdsl2ChConfProfGinpEtrMinUs        Unsigned32,
       xdsl2ChConfProfGinpNdrMaxDs        Unsigned32,
       xdsl2ChConfProfGinpNdrMaxUs        Unsigned32,
       xdsl2ChConfProfGinpShineRatioDs        Unsigned32,
       xdsl2ChConfProfGinpShineRatioUs        Unsigned32,
       xdsl2ChConfProfGinpLeftrThresholdDs        Unsigned32,
       xdsl2ChConfProfGinpLeftrThresholdUs        Unsigned32,
       xdsl2ChConfProfGinpMaxDelayDs        Unsigned32,
       xdsl2ChConfProfGinpMaxDelayUs        Unsigned32,
       xdsl2ChConfProfGinpMinDelayDs        Unsigned32,
       xdsl2ChConfProfGinpMinDelayUs        Unsigned32,
       xdsl2ChConfProfGinpInpMinDs        Unsigned32,
       xdsl2ChConfProfGinpInpMinUs        Unsigned32,
       xdsl2ChConfProfGinpReinCfgInpDs        Unsigned32,
       xdsl2ChConfProfGinpReinCfgInpUs        Unsigned32,
       xdsl2ChConfProfGinpReinCfgFreqDs        Unsigned32,
       xdsl2ChConfProfGinpReinCfgFreqUs        Unsigned32,
       xdsl2ChConfProfSosMinRateB0Ds	Unsigned32,
       xdsl2ChConfProfSosMinRateB0Us	Unsigned32
    }

    xdsl2ChConfProfPhyRDs OBJECT-TYPE
    SYNTAX Unsigned32 
    MAX-ACCESS  read-create
    STATUS  current
    DESCRIPTION
       "This configuration parameter defines phy retransmission 
        mode on downstream direction. If auto mode is selected,
        PhyR will be disabled if the net data rate in PhyR mode 
        will be lower than in non-PhyR mode under current loop 
        condition and framing paramters.
        The possible values are:
        disable(0),
        enable(1),
        auto(2)"
    ::= { xdsl2ExtChConfProfileEntry 1 }

    xdsl2ChConfProfPhyRUs OBJECT-TYPE
    SYNTAX Unsigned32 
    MAX-ACCESS  read-create
    STATUS  current
    DESCRIPTION
       "This configuration parameter defines phy retransmission 
        mode on upstream direction. If auto mode is selected,
        PhyR will be disabled if the net data rate in PhyR mode 
        will be lower than in non-PhyR mode under current loop 
        condition and framing paramters.
        The possible values are:
        disable(0),
        enable(1),
        auto(2)"
    ::= { xdsl2ExtChConfProfileEntry 2 }

    xdsl2ChConfProfPortList  OBJECT-TYPE
    SYNTAX      PortList
    MAX-ACCESS      read-only
    STATUS      current
    DESCRIPTION
       "A port list that indicates which ports this profile applys for."
    REFERENCE    ""
    ::= { xdsl2ExtChConfProfileEntry 3 }

    xdsl2ChConfProfGinpRtxModeDs OBJECT-TYPE
    SYNTAX Xdsl2ConfigRtxMode 
    MAX-ACCESS  read-create
    STATUS  current
    DESCRIPTION
       "G.inp(G.998.4) support setting on downstream direction.
        The possible values are:
         forbidden(0) - Support for G998.4 is disabled.
         preferred(1) - If G998.4 is supported by the far-end, it is enabled.
         forced(2)    - The line will only train if G998.4 can be enabled.
         test(3)      - G998.4 is enabled in test mode (refer to G998.4, Clause 10.4)."
    ::= { xdsl2ExtChConfProfileEntry 4 }

    xdsl2ChConfProfGinpRtxModeUs OBJECT-TYPE
    SYNTAX Xdsl2ConfigRtxMode 
    MAX-ACCESS  read-create
    STATUS  current
    DESCRIPTION
       "G.inp(G.998.4) support setting on upstream direction.
        The possible values are:
         forbidden(0) - Support for G998.4 is disabled.
         preferred(1) - If G998.4 is supported by the far-end, it is enabled.
         forced(2)    - The line will only train if G998.4 can be enabled.
         test(3)      - G998.4 is enabled in test mode (refer to G998.4, Clause 10.4)."
    ::= { xdsl2ExtChConfProfileEntry 5 }
    
    xdsl2ChConfProfGinpEtrMaxDs OBJECT-TYPE
    SYNTAX Unsigned32 
    UNITS "kbps"
    MAX-ACCESS  read-create
    STATUS  current
    DESCRIPTION
       "Defines the maximum allowed value for the ETR (Effective Throughput Rate)."
    ::= { xdsl2ExtChConfProfileEntry 6 }

    xdsl2ChConfProfGinpEtrMaxUs OBJECT-TYPE
    SYNTAX Unsigned32 
    UNITS "kbps"
    MAX-ACCESS  read-create
    STATUS  current
    DESCRIPTION
       "Defines the maximum allowed value for the ETR (Effective Throughput Rate)."
    ::= { xdsl2ExtChConfProfileEntry 7 }
    
    xdsl2ChConfProfGinpEtrMinDs OBJECT-TYPE
    SYNTAX Unsigned32 
    UNITS "kbps"
    MAX-ACCESS  read-create
    STATUS  current
    DESCRIPTION
       "Defines the minimum value for the ETR (Effective Throughput Rate)."
    ::= { xdsl2ExtChConfProfileEntry 8 }

    xdsl2ChConfProfGinpEtrMinUs OBJECT-TYPE
    SYNTAX Unsigned32 
    UNITS "kbps"
    MAX-ACCESS  read-create
    STATUS  current
    DESCRIPTION
       "Defines the minimum value for the ETR (Effective Throughput Rate)."
    ::= { xdsl2ExtChConfProfileEntry 9 }
    
    xdsl2ChConfProfGinpNdrMaxDs OBJECT-TYPE
    SYNTAX Unsigned32 
    UNITS "kbps"
    MAX-ACCESS  read-create
    STATUS  current
    DESCRIPTION
       "Overrules the wanted maximum data rate provided in the SetLineTrafficConfiguration"
    ::= { xdsl2ExtChConfProfileEntry 10 }

    xdsl2ChConfProfGinpNdrMaxUs OBJECT-TYPE
    SYNTAX Unsigned32 
    UNITS "kbps"
    MAX-ACCESS  read-create
    STATUS  current
    DESCRIPTION
       "Overrules the wanted maximum data rate provided in the SetLineTrafficConfiguration"
    ::= { xdsl2ExtChConfProfileEntry 11 }
    
    xdsl2ChConfProfGinpShineRatioDs OBJECT-TYPE
    SYNTAX Unsigned32 
    UNITS "0.001"
    MAX-ACCESS  read-create
    STATUS  current
    DESCRIPTION
       "The loss of rate in a 1 second interval expressed as a fraction of NDR due 
        to a SHINE impulse noise environment expected by the operator to occur 
        at a probability acceptable for the services.
        The valid values are all multiples of 0.001 from 0 to 0.1."
    ::= { xdsl2ExtChConfProfileEntry 12 }

    xdsl2ChConfProfGinpShineRatioUs OBJECT-TYPE
    SYNTAX Unsigned32 
    UNITS "0.001"
    MAX-ACCESS  read-create
    STATUS  current
    DESCRIPTION
       "The loss of rate in a 1 second interval expressed as a fraction of NDR due 
        to a SHINE impulse noise environment expected by the operator to occur 
        at a probability acceptable for the services.
        The valid values are all multiples of 0.001 from 0 to 0.1."
    ::= { xdsl2ExtChConfProfileEntry 13 }
    
    xdsl2ChConfProfGinpLeftrThresholdDs OBJECT-TYPE
    SYNTAX Unsigned32 
    UNITS "0.01"
    MAX-ACCESS  read-create
    STATUS  current
    DESCRIPTION
       "The threshold used to declare leftr defects (see clause 11.3.3) expressed in 
        fraction of the NDR. The value 0 is a special value to indicate that the 
        receiver shall use a special value for declaring leftr defect . The minimum 
        valid threshold to declare leftr is ETR/2. The receiver shall ignore 
        threshold values that are less than the minimum and shall use ETR/2 for 
        declaring leftr defect instead (see clause 11.3.3).
        The valid values are all multiples of 0.01 from 0 to 0.99."
    ::= { xdsl2ExtChConfProfileEntry 14 }

    xdsl2ChConfProfGinpLeftrThresholdUs OBJECT-TYPE
    SYNTAX Unsigned32 
    UNITS "0.01"
    MAX-ACCESS  read-create
    STATUS  current
    DESCRIPTION
       "The threshold used to declare leftr defects (see clause 11.3.3) expressed in 
        fraction of the NDR. The value 0 is a special value to indicate that the 
        receiver shall use a special value for declaring leftr defect . The minimum 
        valid threshold to declare leftr is ETR/2. The receiver shall ignore 
        threshold values that are less than the minimum and shall use ETR/2 for 
        declaring leftr defect instead (see clause 11.3.3).
        The valid values are all multiples of 0.01 from 0 to 0.99."
    ::= { xdsl2ExtChConfProfileEntry 15 }
    
    xdsl2ChConfProfGinpMaxDelayDs OBJECT-TYPE
    SYNTAX Unsigned32 
    UNITS "ms"
    MAX-ACCESS  read-create
    STATUS  current
    DESCRIPTION
       "The maximum allowed delay for retransmission."
    ::= { xdsl2ExtChConfProfileEntry 16 }

    xdsl2ChConfProfGinpMaxDelayUs OBJECT-TYPE
    SYNTAX Unsigned32 
    UNITS "ms"
    MAX-ACCESS  read-create
    STATUS  current
    DESCRIPTION
       "The maximum allowed delay for retransmission."
    ::= { xdsl2ExtChConfProfileEntry 17 }
    
    xdsl2ChConfProfGinpMinDelayDs OBJECT-TYPE
    SYNTAX Unsigned32 
    UNITS "ms"
    MAX-ACCESS  read-create
    STATUS  current
    DESCRIPTION
       "The minimum allowed delay for retransmission."
    ::= { xdsl2ExtChConfProfileEntry 18 }

    xdsl2ChConfProfGinpMinDelayUs OBJECT-TYPE
    SYNTAX Unsigned32 
    UNITS "ms"
    MAX-ACCESS  read-create
    STATUS  current
    DESCRIPTION
       "The minimum allowed delay for retransmission."
    ::= { xdsl2ExtChConfProfileEntry 19 }
    
    xdsl2ChConfProfGinpInpMinDs OBJECT-TYPE
    SYNTAX Unsigned32 
    UNITS "symbols"
    MAX-ACCESS  read-create
    STATUS  current
    DESCRIPTION
       "Minimum impulse noise protection (INP) against SHINE in DMT symbols.
        The possible values are: 0-31"
    ::= { xdsl2ExtChConfProfileEntry 20 }

    xdsl2ChConfProfGinpInpMinUs OBJECT-TYPE
    SYNTAX Unsigned32 
    UNITS "symbols"
    MAX-ACCESS  read-create
    STATUS  current
    DESCRIPTION
       "Minimum impulse noise protection (INP) against SHINE in DMT symbols.
        The possible values are: 0-31"
    ::= { xdsl2ExtChConfProfileEntry 21 }
    
    xdsl2ChConfProfGinpReinCfgInpDs OBJECT-TYPE
    SYNTAX Unsigned32 
    UNITS "symbols"
    MAX-ACCESS  read-create
    STATUS  current
    DESCRIPTION
       "Minimum impulse protection against electrical repetitive impulse noise 
        (REIN) in DMT symbols.
        The possible values are: 0-7"
    ::= { xdsl2ExtChConfProfileEntry 22 }

    xdsl2ChConfProfGinpReinCfgInpUs OBJECT-TYPE
    SYNTAX Unsigned32 
    UNITS "symbols"
    MAX-ACCESS  read-create
    STATUS  current
    DESCRIPTION
       "Minimum impulse protection against electrical repetitive impulse noise 
        (REIN) in DMT symbols.
        The possible values are: 0-7"
    ::= { xdsl2ExtChConfProfileEntry 23 }
    
    xdsl2ChConfProfGinpReinCfgFreqDs OBJECT-TYPE
    SYNTAX Unsigned32 
    UNITS "Hz"
    MAX-ACCESS  read-create
    STATUS  current
    DESCRIPTION
       "Configuration indicating the frequency of REIN.
        The possible values are:
        100 - 100Hz
        120 - 120Hz"
    ::= { xdsl2ExtChConfProfileEntry 24 }

    xdsl2ChConfProfGinpReinCfgFreqUs OBJECT-TYPE
    SYNTAX Unsigned32 
    UNITS "Hz"
    MAX-ACCESS  read-create
    STATUS  current
    DESCRIPTION
       "Configuration indicating the frequency of REIN.
        The possible values are:
        100 - 100Hz
        120 - 120Hz"
    ::= { xdsl2ExtChConfProfileEntry 25 }

    xdsl2ChConfProfSosMinRateB0Ds OBJECT-TYPE
    SYNTAX Unsigned32 
    MAX-ACCESS  read-create
    STATUS  current
    DESCRIPTION
       "This parameter specifies the minimum net data rate required for a valid SOS request 
       in the downstream direction. The value shall be coded as an unsigned integer representing 
       the data rate as a multiple of 8 kbit/s."
    ::= { xdsl2ExtChConfProfileEntry 26 }
    
    xdsl2ChConfProfSosMinRateB0Us OBJECT-TYPE
    SYNTAX Unsigned32 
    MAX-ACCESS  read-create
    STATUS  current
    DESCRIPTION
       "This parameter specifies the minimum net data rate required for a valid SOS request 
       in the downstream direction. The value shall be coded as an unsigned integer representing 
       the data rate as a multiple of 8 kbit/s."
    ::= { xdsl2ExtChConfProfileEntry 27 }

    xdsl2MaxNumChConfProfile OBJECT-TYPE
    SYNTAX  Unsigned32
    MAX-ACCESS  read-only
    STATUS  current
    DESCRIPTION
        "The maximum number of VDSL channel profile."
    ::= { xdsl2ExtProfileChannel 2 }

------------------------------------------------
--    xdsl2ExtLineAlarmConfTemplateTable      --
------------------------------------------------
    xdsl2ExtLineAlarmConfTemplateTable  OBJECT-TYPE
    SYNTAX      SEQUENCE  OF  Xdsl2ExtLineAlarmConfTemplateEntry
    MAX-ACCESS  not-accessible
    STATUS      current
    DESCRIPTION
       "The table xdsl2ExtLineAlarConfTemplateTable extends 
       xdsl2ExtLineAlarConfTemplateTable."
    ::= { xdsl2ExtProfileAlarmConf 1 }

    xdsl2ExtLineAlarmConfTemplateEntry  OBJECT-TYPE
    SYNTAX      Xdsl2ExtLineAlarmConfTemplateEntry
    MAX-ACCESS  not-accessible
    STATUS      current
    DESCRIPTION
       "The table xdsl2ExtLineAlarConfTemplateTable extends 
       xdsl2ExtLineAlarConfTemplateTable."
   INDEX  { xdsl2LAlarmConfTempTemplateName }
   ::= { xdsl2ExtLineAlarmConfTemplateTable 1 }

    Xdsl2ExtLineAlarmConfTemplateEntry  ::=
    SEQUENCE {
       xdsl2LAlarmConfTempPortList      PortList
    }

    xdsl2LAlarmConfTempPortList  OBJECT-TYPE
    SYNTAX      PortList
    MAX-ACCESS      read-only
    STATUS      current
    DESCRIPTION
       "A port list that indicates which ports this template applys for."
    REFERENCE    ""
    ::= { xdsl2ExtLineAlarmConfTemplateEntry 3 }

------------------------------------------------
--   xdsl2ExtLineAlarmConfProfileTable        --
------------------------------------------------

    xdsl2ExtLineAlarmConfProfileTable  OBJECT-TYPE
    SYNTAX      SEQUENCE  OF  Xdsl2ExtLineAlarmConfProfileEntry
    MAX-ACCESS  not-accessible
    STATUS      current
    DESCRIPTION
      "The table xdsl2ExtLineAlarmConfProfileTable extends 
       xdsl2LineAlarmConfProfileTable."
     ::= { xdsl2ExtProfileAlarmConf 2 }

    xdsl2ExtLineAlarmConfProfileEntry  OBJECT-TYPE
    SYNTAX      Xdsl2ExtLineAlarmConfProfileEntry
    MAX-ACCESS  not-accessible
    STATUS      current
    DESCRIPTION
      "The table xdsl2ExtLineAlarmConfProfileTable extends 
       xdsl2LineAlarmConfProfileTable."
    INDEX  { xdsl2LineAlarmConfProfileName }
    ::= { xdsl2ExtLineAlarmConfProfileTable 1 }

    Xdsl2ExtLineAlarmConfProfileEntry ::=
    SEQUENCE {
       xdsl2LineAlarmConfProfileXtucThresh15MinLofs   HCPerfIntervalThreshold,
       xdsl2LineAlarmConfProfileXturThresh15MinLofs   HCPerfIntervalThreshold,
       xdsl2LAlarmConfProfilePortList 				  PortList,
       xdsl2LineAlarmConfProfileXturThresh15MinLprs   HCPerfIntervalThreshold
    }

    xdsl2LineAlarmConfProfileXtucThresh15MinLofs  OBJECT-TYPE
    SYNTAX      HCPerfIntervalThreshold
    UNITS       "seconds"
    MAX-ACCESS  read-create
    STATUS      current
    DESCRIPTION
       "A threshold for the xdsl2PMLCurr15MLofs counter, when
        xdsl2PMLCurrUnit is xtuc {1}.
        The value 0 means that no threshold is specified for the
        associated counter."
    DEFVAL       { 0 }
    ::= { xdsl2ExtLineAlarmConfProfileEntry 1 }

    xdsl2LineAlarmConfProfileXturThresh15MinLofs  OBJECT-TYPE
    SYNTAX      HCPerfIntervalThreshold
    UNITS       "seconds"
    MAX-ACCESS  read-create
    STATUS      current
    DESCRIPTION
       "A threshold for the xdsl2PMLCurr15MLofs counter, when
        xdsl2PMLCurrUnit is xtur {2}.
        The value 0 means that no threshold is specified for the
        associated counter."
    DEFVAL       { 0 }
    ::= { xdsl2ExtLineAlarmConfProfileEntry 2 }

    xdsl2LAlarmConfProfilePortList  OBJECT-TYPE
    SYNTAX      PortList
    MAX-ACCESS      read-only
    STATUS      current
    DESCRIPTION
       "A port list that indicates which ports this profile applys for."
    ::= { xdsl2ExtLineAlarmConfProfileEntry 3 }

    xdsl2LineAlarmConfProfileXturThresh15MinLprs  OBJECT-TYPE
    SYNTAX      HCPerfIntervalThreshold
    UNITS       "seconds"
    MAX-ACCESS  read-create
    STATUS      current
    DESCRIPTION
       "A threshold for the xdsl2PMLCurr15MLprs counter, when
        xdsl2PMLCurrUnit is xtur {2}.
        The value 0 means that no threshold is specified for the
        associated counter."
    DEFVAL       { 0 }
    ::= { xdsl2ExtLineAlarmConfProfileEntry 4 }


------------------------------------------------
--    xdsl2ExtChAlarmConfProfileTable         --
------------------------------------------------

    xdsl2ExtChAlarmConfProfileTable  OBJECT-TYPE
    SYNTAX      SEQUENCE  OF  Xdsl2ExtChAlarmConfProfileEntry
    MAX-ACCESS  not-accessible
    STATUS      current
    DESCRIPTION
      "The table xdsl2ExtChAlarmConfProfileTable extends 
       xdsl2ExtChAlarmConfProfileTable."
    ::= { xdsl2ExtProfileAlarmConf 3 }

    xdsl2ExtChAlarmConfProfileEntry  OBJECT-TYPE
    SYNTAX      Xdsl2ExtChAlarmConfProfileEntry
    MAX-ACCESS  not-accessible
    STATUS      current
    DESCRIPTION
      "The table xdsl2ExtChAlarmConfProfileTable extends 
       xdsl2ExtChAlarmConfProfileTable."
    INDEX  { xdsl2ChAlarmConfProfileName }
    ::= { xdsl2ExtChAlarmConfProfileTable 1 }

    Xdsl2ExtChAlarmConfProfileEntry ::=
    SEQUENCE {
       xdsl2ChAlarmConfProfilePortList PortList
    }

    xdsl2ChAlarmConfProfilePortList  OBJECT-TYPE
    SYNTAX      PortList
    MAX-ACCESS      read-only
    STATUS      current
    DESCRIPTION
       "A port list that indicates which ports this profileapplys for."
    ::= { xdsl2ExtChAlarmConfProfileEntry 3 }

    xdsl2MaxNumLineAlarmConfTemplate OBJECT-TYPE
    SYNTAX  Unsigned32
    MAX-ACCESS  read-only
    STATUS  current
    DESCRIPTION
        "The maximum number of VDSL alarm template."
    ::= { xdsl2ExtProfileAlarmConf 4 }

    xdsl2MaxNumLineAlarmConfProfile OBJECT-TYPE
    SYNTAX  Unsigned32
    MAX-ACCESS  read-only
    STATUS  current
    DESCRIPTION
        "The maximum number of VDSL line alarm profile."
    ::= { xdsl2ExtProfileAlarmConf 5 }

    xdsl2MaxNumChAlarmConfProfile OBJECT-TYPE
    SYNTAX  Unsigned32
    MAX-ACCESS  read-only
    STATUS  current
    DESCRIPTION
        "The maximum number of VDSL channel alarm profile."
    ::= { xdsl2ExtProfileAlarmConf 6 }
            
-------------------------------------------
--          Notifications Group          --
-------------------------------------------
	xdsl2LinePerfLOFSThreshXtuc NOTIFICATION-TYPE
    OBJECTS
    {
    xdsl2PMLCurr15MLofs,
    xdsl2LineAlarmConfProfileXtucThresh15MinLofs
    }
    STATUS     current
    DESCRIPTION
      "This notification indicates that the LOF seconds threshold
       has been reached/exceeded for the referred xTU-C."
    ::= { xdsl2ExtNotifications 1 }

	xdsl2LinePerfLOFSThreshXtur NOTIFICATION-TYPE
    OBJECTS
    {
    xdsl2PMLCurr15MLofs,
    xdsl2LineAlarmConfProfileXturThresh15MinLofs
    }
    STATUS     current
    DESCRIPTION
      "This notification indicates that the LOF seconds threshold
       has been reached/exceeded for the referred xTU-R."
    ::= { xdsl2ExtNotifications 2 }
    
	xdsl2LinePerfLPRSThreshXtur NOTIFICATION-TYPE
    OBJECTS
    {
    xdsl2PMLCurr15MLprs,
    xdsl2LineAlarmConfProfileXturThresh15MinLprs
    }
    STATUS     current
    DESCRIPTION
      "This notification indicates that the LPR seconds threshold
       has been reached/exceeded for the referred xTU-R."
    ::= { xdsl2ExtNotifications 3 }

--  macBasedVlanSetup
	macBasedVlanSetup     	OBJECT IDENTIFIER ::= { ves1724-56fanless 61 }

        macBasedVlanTable	OBJECT-TYPE
        SYNTAX	SEQUENCE OF MacBasedVlanEntry
        MAX-ACCESS  not-accessible
        STATUS  current
        DESCRIPTION
                 	""
        ::= { macBasedVlanSetup 1 }

		macBasedVlanEntry OBJECT-TYPE
        SYNTAX	MacBasedVlanEntry
        MAX-ACCESS	not-accessible
        STATUS	current
        DESCRIPTION    	"An entry in macBasedVlanTable."
        INDEX          	{macBasedVlanMAC }
        ::= { macBasedVlanTable 1 }

      	MacBasedVlanEntry ::=
		SEQUENCE {
        	macBasedVlanName		DisplayString,
        	macBasedVlanMAC 	MacAddress,      
        	macBasedVlanVlanId 	INTEGER,
        	macBasedVlan8021pPriority INTEGER,
        	macBasedVlanRowstatus RowStatus        	
           }                                             
                        
        macBasedVlanName OBJECT-TYPE
        SYNTAX  DisplayString
        MAX-ACCESS  read-write
        STATUS  current
        DESCRIPTION
                      	"Name of Mac-Based Vlan."
        ::= { macBasedVlanEntry 1 }                        
                        
        macBasedVlanMAC OBJECT-TYPE
        SYNTAX  MacAddress
        MAX-ACCESS  read-only
        STATUS  current
        DESCRIPTION
                      	"Mac address for Mac-Based Vlan"
        ::= { macBasedVlanEntry 2 }
                                             
   		macBasedVlanVlanId OBJECT-TYPE
        SYNTAX  INTEGER
        MAX-ACCESS  read-write
        STATUS  current
        DESCRIPTION
                      	"Vlan id for Mac-Based Vlan, 1~4094."
        ::= { macBasedVlanEntry 3 }
        
			macBasedVlan8021pPriority OBJECT-TYPE
        SYNTAX  INTEGER
        MAX-ACCESS  read-write
        STATUS  current
        DESCRIPTION
                      	"802.1p priority for Mac-Based Vlan, 0~7."
        ::= { macBasedVlanEntry 4 } 
        
      macBasedVlanRowstatus OBJECT-TYPE
        SYNTAX  RowStatus
        MAX-ACCESS  read-create
        STATUS  current
        DESCRIPTION
                      	"Row Status for Mac-Based Vlan"
        ::= { macBasedVlanEntry 5 } 

--  vlanProfileSetup
	vlanProfileSetup     	OBJECT IDENTIFIER ::= { ves1724-56fanless 62 }

        vlanProfileTable	OBJECT-TYPE
        SYNTAX	SEQUENCE OF VlanProfileEntry
        MAX-ACCESS  not-accessible
        STATUS  current
        DESCRIPTION
                 	""
        ::= { vlanProfileSetup 1 }

		vlanProfileEntry OBJECT-TYPE
        SYNTAX	VlanProfileEntry
        MAX-ACCESS	not-accessible
        STATUS	current
        DESCRIPTION    	"An entry in vlanProfileTable."
        INDEX          	{vlanProfileName }
        ::= { vlanProfileTable 1 }

      	VlanProfileEntry ::=
		SEQUENCE {
        	vlanProfileName		DisplayString,
        	vlanProfileMacLearning 	INTEGER,      
        	vlanProfileUnknownMulticast		INTEGER, 
        	vlanProfileRowStatus 	RowStatus      	
           }                                             
                        
        vlanProfileName OBJECT-TYPE
        SYNTAX  DisplayString
        MAX-ACCESS  read-only
        STATUS  current
        DESCRIPTION
                      	"Name of vlan Profile."
        ::= { vlanProfileEntry 1 }                        
                        
        vlanProfileMacLearning OBJECT-TYPE
        SYNTAX  INTEGER{
                enable(1),
                disable(0)
        }
        MAX-ACCESS  read-write
        STATUS  current
        DESCRIPTION
                      	"Mac learning for vlan profile"
        ::= { vlanProfileEntry 2 }
                   
        vlanProfileUnknownMulticast OBJECT-TYPE
        SYNTAX  INTEGER{
        	none(1),
        	flooding(3)
        }
        MAX-ACCESS  read-write
        STATUS  current
        DESCRIPTION
                      	"Set unknown multicast packets behavior.
			None means normally forwarding.
			Flooding means force forwarding even unknown multicast setting on multicast is drop."
        ::= { vlanProfileEntry 3 }
                   
        vlanProfileRowStatus OBJECT-TYPE
        SYNTAX  RowStatus
        MAX-ACCESS  read-create
        STATUS  current
        DESCRIPTION
                      	"Row status for vlan profile"
        ::= { vlanProfileEntry 4 } 

        vlanTable	OBJECT-TYPE
        SYNTAX	SEQUENCE OF VlanEntry
        MAX-ACCESS  not-accessible
        STATUS  current
        DESCRIPTION
                 	""
        ::= { vlanProfileSetup 2 }

	vlanEntry OBJECT-TYPE
        SYNTAX	VlanEntry
        MAX-ACCESS	not-accessible
        STATUS	current
        DESCRIPTION    	"An entry in vlanTable."
        INDEX          	{dot1qVlanIndex }
        ::= { vlanTable 1 }

      	VlanEntry ::=
		SEQUENCE {
        	profileName	DisplayString	
           }                                             
                        
        profileName OBJECT-TYPE
        SYNTAX  DisplayString
        MAX-ACCESS  read-write
        STATUS  current
        DESCRIPTION
                      	"Name of vlan Profile."
        ::= { vlanEntry 1 }                        

--  DoSPreventionSetup
	dosPreventionSetup     	OBJECT IDENTIFIER ::= { ves1724-56fanless 63 }                                        
                        
        dosPreventionActive OBJECT-TYPE
        SYNTAX  INTEGER{
                enable(1),
                disable(0)
        }
        MAX-ACCESS  read-write
        STATUS  current
        DESCRIPTION
                      	"DoS prevention enabled/disabled for the switch."
        ::= { dosPreventionSetup 1 }                        
                        
--        dosPreventionTCPHeaderSize OBJECT-TYPE
--        SYNTAX  INTEGER
--        MAX-ACCESS  read-write
--        STATUS  current
--        DESCRIPTION
--                      	"Minimum TCP header size."
--        ::= { dosPreventionSetup 2 }
                   
--        dosPreventionICMPPacketSize OBJECT-TYPE
--        SYNTAX  INTEGER
--        MAX-ACCESS  read-write
--        STATUS  current
--        DESCRIPTION
--                      	"Maximum ICMP packet size."
--        ::= { dosPreventionSetup 3 } 
             
        dosPreventionMacChecking OBJECT-TYPE
        SYNTAX  INTEGER{
                enable(1),
                disable(0)
        }
        MAX-ACCESS  read-write
        STATUS  current
        DESCRIPTION
                      	"Checking MAC enabled/disabled for the switch."
        ::= { dosPreventionSetup 4 }     
             
        dosPreventionIPChecking OBJECT-TYPE
        SYNTAX  INTEGER{
                enable(1),
                disable(0)
        }
        MAX-ACCESS  read-write
        STATUS  current
        DESCRIPTION
                      	"Checking IP enabled/disabled for the switch."
        ::= { dosPreventionSetup 5 }    
             
--        dosPreventionDoSIPAttack OBJECT-TYPE
--        SYNTAX  INTEGER{
--                enable(1),
--                disable(0)
--        }
--        MAX-ACCESS  read-write
--        STATUS  current
--        DESCRIPTION
--                      	"DoS IP attack enabled/disabled for the switch."
--        ::= { dosPreventionSetup 6 }  
             
--        dosPreventionICMPSize OBJECT-TYPE
--        SYNTAX  INTEGER{
--                enable(1),
--                disable(0)
--        }
--        MAX-ACCESS  read-write
--        STATUS  current
--        DESCRIPTION
--                      	"Checking ICMP packet size enabled/disabled for the switch."
--        ::= { dosPreventionSetup 7 }  
             
--        dosPreventionDoSICMPAttack OBJECT-TYPE
--        SYNTAX  INTEGER{
--                enable(1),
--                disable(0)
--        }
--        MAX-ACCESS  read-write
--        STATUS  current
--        DESCRIPTION
--                      	"DoS ICMP attack enabled/disabled for the switch."
--        ::= { dosPreventionSetup 8 }     
             
        dosPreventionICMPFragment OBJECT-TYPE
        SYNTAX  INTEGER{
                enable(1),
                disable(0)
        }
        MAX-ACCESS  read-write
        STATUS  current
        DESCRIPTION
                      	"Dropping fragmented ICMP packets enabled/disabled for the switch."
        ::= { dosPreventionSetup 9 }  
             
--        dosPreventionTCPSize OBJECT-TYPE
--        SYNTAX  INTEGER{
--                enable(1),
--                disable(0)
--        }
--        MAX-ACCESS  read-write
--        STATUS  current
--        DESCRIPTION
--                      	"Checking TCP header size enabled/disabled for the switch."
--        ::= { dosPreventionSetup 10 }      
             
        dosPreventionTCPSYN OBJECT-TYPE
        SYNTAX  INTEGER{
                enable(1),
                disable(0)
        }
        MAX-ACCESS  read-write
        STATUS  current
        DESCRIPTION
                      	"Checking TCP SYN packets enabled/disabled for the switch."
        ::= { dosPreventionSetup 11 }     
             
--        dosPreventionDoSTCPAttack OBJECT-TYPE
--        SYNTAX  INTEGER{
--                enable(1),
--                disable(0)
--        }
--        MAX-ACCESS  read-write
--        STATUS  current
--        DESCRIPTION
--                      	"DoS TCP attack enabled/disabled for the switch."
--        ::= { dosPreventionSetup 12 }     
             
        dosPreventionTCPFragment OBJECT-TYPE
        SYNTAX  INTEGER{
                enable(1),
                disable(0)
        }
        MAX-ACCESS  read-write
        STATUS  current
        DESCRIPTION
                      	"Dropping fragmented TCP packets with offset value of 1 enabled/disabled for the switch."
        ::= { dosPreventionSetup 13 }     
             
        dosPreventionTCPControlSN OBJECT-TYPE
        SYNTAX  INTEGER{
                enable(1),
                disable(0)
        }
        MAX-ACCESS  read-write
        STATUS  current
        DESCRIPTION
                      	"Dropping TCP packets with control flag of 0 and sequence number of 0 enabled/disabled for the switch."
        ::= { dosPreventionSetup 14 }    
             
        dosPreventionTCPPort OBJECT-TYPE
        SYNTAX  INTEGER{
                enable(1),
                disable(0)
        }
        MAX-ACCESS  read-write
        STATUS  current
        DESCRIPTION
                      	"Checking TCP port enabled/disabled for the switch."
        ::= { dosPreventionSetup 15 }  
             
        dosPreventionTCPSF OBJECT-TYPE
        SYNTAX  INTEGER{
                enable(1),
                disable(0)
        }
        MAX-ACCESS  read-write
        STATUS  current
        DESCRIPTION
                      	"Checking TCP packets with SYN and FIN bits enabled/disabled for the switch."
        ::= { dosPreventionSetup 16 }      
             
        dosPreventionTCPFUP OBJECT-TYPE
        SYNTAX  INTEGER{
                enable(1),
                disable(0)
        }
        MAX-ACCESS  read-write
        STATUS  current
        DESCRIPTION
                      	"Checking TCP packets with FIN, URG, PSH bits and sequence number enabled/disabled for the switch."
        ::= { dosPreventionSetup 17 }      
             
        dosPreventionUDPPort OBJECT-TYPE
        SYNTAX  INTEGER{
                enable(1),
                disable(0)
        }
        MAX-ACCESS  read-write
        STATUS  current
        DESCRIPTION
                      	"Checking UDP port enabled/disabled for the switch."
        ::= { dosPreventionSetup 18 }      
             
--        dosPreventionTCPUDPPort OBJECT-TYPE
--        SYNTAX  INTEGER{
--                enable(1),
--                disable(0)
--        }
--        MAX-ACCESS  read-write
--        STATUS  current
--        DESCRIPTION
--                      	"Checking TCP/UDP port enabled/disabled for the switch."
--        ::= { dosPreventionSetup 19 }    
   
--  ipv6Setup
	ipv6Setup     	OBJECT IDENTIFIER ::= { ves1724-56fanless 65 }

--        dnsIpv6Address OBJECT-TYPE
--        SYNTAX  Ipv6Address
--        MAX-ACCESS  read-write
--        STATUS  current
--        DESCRIPTION
--                      ""
--        ::= { ipv6Setup 1 }

        ipv6DefaultMgmt OBJECT-TYPE
        SYNTAX  INTEGER {
        	in_band(0),
        	out_of_band(1)
        }
        MAX-ACCESS  read-write
        STATUS  current
        DESCRIPTION
                      ""
        ::= { ipv6Setup 2 }

	inbandIpv6Setup     	OBJECT IDENTIFIER ::= { ipv6Setup 3 }

--        inbandIpType OBJECT-TYPE
--        SYNTAX  INTEGER {
--        	dhcp_client(0),
--        	static_ip(1)
--        }
--        MAX-ACCESS  read-write
--        STATUS  current
--        DESCRIPTION
--                      ""
--        ::= { inbandIpv6Setup 1 }

        inbandIpv6Vid OBJECT-TYPE
        SYNTAX  INTEGER
        MAX-ACCESS  read-write
        STATUS  current
        DESCRIPTION
                      ""
        ::= { inbandIpv6Setup 2 }

        inbandIpv6StaticIp OBJECT-TYPE
        SYNTAX  Ipv6Address
        MAX-ACCESS  read-write
        STATUS  current
        DESCRIPTION
                      ""
        ::= { inbandIpv6Setup 3 }

        inbandIpv6StaticSubnetMask OBJECT-TYPE
        SYNTAX  Ipv6Address
        MAX-ACCESS  read-write
        STATUS  current
        DESCRIPTION
                      ""
        ::= { inbandIpv6Setup 4 }

        inbandIpv6StaticGateway OBJECT-TYPE
        SYNTAX  Ipv6Address
        MAX-ACCESS  read-write
        STATUS  current
        DESCRIPTION
                      ""
        ::= { inbandIpv6Setup 5 }

	outOfBandIpv6Setup     	OBJECT IDENTIFIER ::= { ipv6Setup 4 }

        outOfBandIpv6Ip OBJECT-TYPE
        SYNTAX  Ipv6Address
        MAX-ACCESS  read-write
        STATUS  current
        DESCRIPTION
                      ""
        ::= { outOfBandIpv6Setup 1 }

        outOfBandIpv6SubnetMask OBJECT-TYPE
        SYNTAX  Ipv6Address
        MAX-ACCESS  read-write
        STATUS  current
        DESCRIPTION
                      ""
        ::= { outOfBandIpv6Setup 2 }

        outOfBandIpv6Gateway OBJECT-TYPE
        SYNTAX  Ipv6Address
        MAX-ACCESS  read-write
        STATUS  current
        DESCRIPTION
                      ""
        ::= { outOfBandIpv6Setup 3 }
       
        
---------------------------------------------------
--
--  Layer 2 Protocol Tunneling
--
---------------------------------------------------
 l2ptSetup      OBJECT IDENTIFIER ::= { ves1724-56fanless 115 }
 
--  l2ptState                               
        l2ptState OBJECT-TYPE
        SYNTAX  EnabledStatus
        MAX-ACCESS  read-write
        STATUS  current
        DESCRIPTION
                       "L2PT feature enabled/disabled for the switch"
        ::= { l2ptSetup 1 }
                                
        l2ptMacAddr OBJECT-TYPE
        SYNTAX  MacAddress
        MAX-ACCESS  read-write
        STATUS  current
        DESCRIPTION
                       "L2PT destination mac address"
        ::= { l2ptSetup 2 }
                                
-- l2ptTable
 
        l2ptTable OBJECT-TYPE
        SYNTAX SEQUENCE OF L2ptEntry
        MAX-ACCESS  not-accessible
        STATUS  current
        DESCRIPTION
                  ""
        ::= { l2ptSetup 3 }
        
 l2ptEntry OBJECT-TYPE
        SYNTAX L2ptEntry
        MAX-ACCESS not-accessible
        STATUS current
        DESCRIPTION     "An entry in l2ptTable."
        INDEX           { dot1dBasePort }
        ::= { l2ptTable 1 }
 
        L2ptEntry ::=
           SEQUENCE {
         l2ptProtocolGroup  BITS,
         l2ptPointToPointProtocolGroup BITS,
         l2ptMode   INTEGER
           }
 
     l2ptProtocolGroup OBJECT-TYPE
        SYNTAX BITS {
		  cDP(0),
		  sTP(1),
		  vTP(2)
		 }
        MAX-ACCESS  read-write
        STATUS  current
        DESCRIPTION
                       "L2PT protocols enabled/disabled on the port"
        ::= { l2ptEntry 1 }
 
     l2ptPointToPointProtocolGroup OBJECT-TYPE
        SYNTAX BITS {
		  pAGP(0),
		  lACP(1),
		  uDLD(2)
		 }
        MAX-ACCESS  read-write
        STATUS  current
        DESCRIPTION
                       "L2PT point-to-point protocols enabled/disabled on the port"
        ::= { l2ptEntry 2 }
                
        l2ptMode OBJECT-TYPE
        SYNTAX  INTEGER {
         access(1),
         tunnel(2)
        }
        MAX-ACCESS  read-write
        STATUS  current
        DESCRIPTION
                       "L2PT port role on the port"
        ::= { l2ptEntry 3 }   


---------------------------------------------------
--
--  vlan mapping
--
---------------------------------------------------

-- vlanMappingSetup
	vlanMappingSetup     	OBJECT IDENTIFIER ::= { ves1724-56fanless 116 }
                               
        vlanMappingState OBJECT-TYPE
        SYNTAX  EnabledStatus
        MAX-ACCESS  read-write
        STATUS  current
        DESCRIPTION
                      	""
        ::= { vlanMappingSetup 1 }

                                               
-- vlanMappingPortTable

        vlanMappingPortTable OBJECT-TYPE
        SYNTAX	SEQUENCE OF VlanMappingPortEntry
        MAX-ACCESS  not-accessible
        STATUS  current
        DESCRIPTION
                 	""
        ::= { vlanMappingSetup 2 }
        
	vlanMappingPortEntry OBJECT-TYPE
        SYNTAX	VlanMappingPortEntry
        MAX-ACCESS	not-accessible
        STATUS	current
        DESCRIPTION    	"An entry in vlanMappingPortTable."
        INDEX          	{ dot1dBasePort }
        ::= { vlanMappingPortTable 1 }

        VlanMappingPortEntry ::=
           SEQUENCE {
        	vlanMappingPortState	EnabledStatus,
        	vlanMappingPortDropMiss	EnabledStatus
           }

        vlanMappingPortState OBJECT-TYPE
        SYNTAX  EnabledStatus
        MAX-ACCESS  read-write
        STATUS  current
        DESCRIPTION
                      	""
        ::= { vlanMappingPortEntry 1 }


        vlanMappingPortDropMiss OBJECT-TYPE
        SYNTAX  EnabledStatus
        MAX-ACCESS  read-write
        STATUS  current
        DESCRIPTION
                      	""
        ::= { vlanMappingPortEntry 2 }

-- vlanMappingRuleTable
        vlanMappingRuleTable OBJECT-TYPE
        SYNTAX	SEQUENCE OF VlanMappingRuleEntry
        MAX-ACCESS  not-accessible
        STATUS  current
        DESCRIPTION
                 	""
        ::= { vlanMappingSetup 3 }
        
	vlanMappingRuleEntry OBJECT-TYPE
        SYNTAX	VlanMappingRuleEntry
        MAX-ACCESS	not-accessible
        STATUS	current
        DESCRIPTION    	"An entry in vlan-mapping rule table"
        INDEX          	{ vlanMappingRulePort, vlanMappingRuleVid }
        ::= { vlanMappingRuleTable 1 }

        VlanMappingRuleEntry ::=
           SEQUENCE {
           	vlanMappingRuleName		DisplayString,
        	vlanMappingRulePort		INTEGER,
        	vlanMappingRuleVid		INTEGER,
        	vlanMappingRuleTransVid	INTEGER,
        	vlanMappingRulePriority	INTEGER,
        	vlanMappingRuleRowStatus	RowStatus,
        	vlanMappingRuleReplacePrio	EnabledStatus
           }

        vlanMappingRuleName OBJECT-TYPE
        SYNTAX  DisplayString
        MAX-ACCESS  read-write
        STATUS  current
        DESCRIPTION
                      	"The name of vlan-mapping entry"
        ::= { vlanMappingRuleEntry 1 }

        vlanMappingRulePort OBJECT-TYPE
        SYNTAX  INTEGER
        MAX-ACCESS  read-only
        STATUS  current
        DESCRIPTION
                     	"interface port id"
        ::= { vlanMappingRuleEntry 2 }

        vlanMappingRuleVid OBJECT-TYPE
        SYNTAX  INTEGER
        MAX-ACCESS  read-only
        STATUS  current
        DESCRIPTION
                     	"inner vid"
        ::= { vlanMappingRuleEntry 3 }
        
        vlanMappingRuleTransVid OBJECT-TYPE
        SYNTAX  INTEGER
        MAX-ACCESS  read-write
        STATUS  current
        DESCRIPTION
                     	"translated vid"
        ::= { vlanMappingRuleEntry 4 }
        
        vlanMappingRulePriority OBJECT-TYPE
        SYNTAX  INTEGER {
        		priority_0(0),
        		priority_1(1),
        		priority_2(2),
        		priority_3(3),
        		priority_4(4),
        		priority_5(5),
        		priority_6(6),
        		priority_7(7)
        }

        MAX-ACCESS  read-write
        STATUS  current
        DESCRIPTION
                     	"priority"
        ::= { vlanMappingRuleEntry 5 }

        vlanMappingRuleRowStatus OBJECT-TYPE
        SYNTAX  RowStatus
        MAX-ACCESS  read-create
        STATUS  current
        DESCRIPTION
                     	""
        ::= { vlanMappingRuleEntry 6 }

        vlanMappingRuleReplacePrio OBJECT-TYPE
        SYNTAX  EnabledStatus
        MAX-ACCESS  read-write
        STATUS  current
        DESCRIPTION
                     	"Replace Original Priority"
        ::= { vlanMappingRuleEntry 7 }

-- transceiverInfoTable
	transceiverInfo OBJECT IDENTIFIER ::= { ves1724-56fanless 117 }

-- transceiverSerialInfoTable
	
        transceiverSerialInfoTable	OBJECT-TYPE
        SYNTAX	SEQUENCE OF TransceiverSerialInfoEntry
        MAX-ACCESS  not-accessible
        STATUS  current
        DESCRIPTION
                 	""
        ::= { transceiverInfo 1 }
        
	transceiverSerialInfoEntry OBJECT-TYPE
        SYNTAX	TransceiverSerialInfoEntry
        MAX-ACCESS	not-accessible
        STATUS	current
        DESCRIPTION    	"An entry in transceiverSerialInfoTable."
        INDEX          	{ transceiverSerialInfoEntryPort }
        ::= { transceiverSerialInfoTable 1 }

        TransceiverSerialInfoEntry ::=
           SEQUENCE {
        	transceiverSerialInfoEntryPort			INTEGER,
        	transceiverSerialInfoEntryStatus		INTEGER,
        	transceiverSerialInfoEntryVendor		DisplayString,
        	transceiverSerialInfoEntryPartNo		DisplayString,
        	transceiverSerialInfoEntrySerialNo		DisplayString,
        	transceiverSerialInfoEntryRevision		DisplayString,
        	transceiverSerialInfoEntryDateCode		DisplayString,
        	transceiverSerialInfoEntryTransceiver	DisplayString
           }

        transceiverSerialInfoEntryPort OBJECT-TYPE
        SYNTAX  INTEGER
        MAX-ACCESS  read-only
        STATUS  current
        DESCRIPTION
                      	"Index of transceiverSerialInfo. It is referred to dot1dBasePort"
        ::= { transceiverSerialInfoEntry 1 }
        
        transceiverSerialInfoEntryStatus OBJECT-TYPE
        SYNTAX  INTEGER {
        		ok_with_DDM(1),
        		ok_without_DDM(2),
        		nonoperational(3)
        }
        MAX-ACCESS  read-only
        STATUS  current
        DESCRIPTION
                      	"Transceiver module status."
        ::= { transceiverSerialInfoEntry 2 }


        transceiverSerialInfoEntryVendor OBJECT-TYPE
        SYNTAX  DisplayString
        MAX-ACCESS  read-only
        STATUS  current
        DESCRIPTION
                      	"Transceiver module vendor name."
        ::= { transceiverSerialInfoEntry 3 }

        transceiverSerialInfoEntryPartNo OBJECT-TYPE
        SYNTAX  DisplayString
        MAX-ACCESS  read-only
        STATUS  current
        DESCRIPTION
                      	"Part number provided by transceiver module vendor."
        ::= { transceiverSerialInfoEntry 4 }
        
        transceiverSerialInfoEntrySerialNo OBJECT-TYPE
        SYNTAX  DisplayString
        MAX-ACCESS  read-only
        STATUS  current
        DESCRIPTION
                      	"Serial number provided by transceiver module vendor."
        ::= { transceiverSerialInfoEntry 5 }

        transceiverSerialInfoEntryRevision OBJECT-TYPE
        SYNTAX  DisplayString
        MAX-ACCESS  read-only
        STATUS  current
        DESCRIPTION
                      	"Revision level for part number provided by transceiver module vendor."
        ::= { transceiverSerialInfoEntry 6 }

        transceiverSerialInfoEntryDateCode OBJECT-TYPE
        SYNTAX  DisplayString
        MAX-ACCESS  read-only
        STATUS  current
        DESCRIPTION
                      	"Transceiver module vendor's manufacturing date code"
        ::= { transceiverSerialInfoEntry 7 }
        
        transceiverSerialInfoEntryTransceiver OBJECT-TYPE
        SYNTAX  DisplayString
        MAX-ACCESS  read-only
        STATUS  current
        DESCRIPTION
                      	"Transceiver module type names"
        ::= { transceiverSerialInfoEntry 8 }

-- transceiverDdmInfoTable
	
        transceiverDdmInfoTable	OBJECT-TYPE
        SYNTAX	SEQUENCE OF TransceiverDdmInfoEntry
        MAX-ACCESS  not-accessible
        STATUS  current
        DESCRIPTION
                 	""
        ::= { transceiverInfo 2 }
        
		transceiverDdmInfoEntry OBJECT-TYPE
        SYNTAX	TransceiverDdmInfoEntry
        MAX-ACCESS	not-accessible
        STATUS	current
        DESCRIPTION    	"An entry in transceiverDdmInfoTable."
        INDEX          	{ transceiverDdmInfoEntryPort, transceiverDdmInfoEntryType }
        ::= { transceiverDdmInfoTable 1 }

        TransceiverDdmInfoEntry ::=
           SEQUENCE {
        	transceiverDdmInfoEntryPort			INTEGER,
        	transceiverDdmInfoEntryType			INTEGER,
        	transceiverDdmInfoEntryAlarmMax		DisplayString,
        	transceiverDdmInfoEntryAlarmMin		DisplayString,
        	transceiverDdmInfoEntryWarnMax		DisplayString,
        	transceiverDdmInfoEntryWarnMin		DisplayString,
        	transceiverDdmInfoEntryCurrent		DisplayString,
        	transceiverDdmInfoEntryDescription	DisplayString
           }

        transceiverDdmInfoEntryPort OBJECT-TYPE
        SYNTAX  INTEGER
        MAX-ACCESS  read-only
        STATUS  current
        DESCRIPTION
                      	"Index of transceiverDdmInfo. This will be referred to dot1dBasePort"
        ::= { transceiverDdmInfoEntry 1 }
        
        transceiverDdmInfoEntryType OBJECT-TYPE
        SYNTAX  INTEGER {
        		temperature(1),
        		voltage(2),
        		txbias(3),
                txPower(4),
                rxPower(5)
        }
        MAX-ACCESS  read-only
        STATUS  current
        DESCRIPTION
                      	"Transceiver module status."
        ::= { transceiverDdmInfoEntry 2 }


        transceiverDdmInfoEntryAlarmMax OBJECT-TYPE
        SYNTAX  DisplayString
        MAX-ACCESS  read-only
        STATUS  current
        DESCRIPTION
                      	"Default Transceiver high alarm threshold."
        ::= { transceiverDdmInfoEntry 3 }

        transceiverDdmInfoEntryAlarmMin OBJECT-TYPE
        SYNTAX  DisplayString
        MAX-ACCESS  read-only
        STATUS  current
        DESCRIPTION
                      	"Default Transceiver low alarm threshold."
        ::= { transceiverDdmInfoEntry 4 }
        
        transceiverDdmInfoEntryWarnMax OBJECT-TYPE
        SYNTAX  DisplayString      
        MAX-ACCESS  read-only
        STATUS  current
        DESCRIPTION
                      	"Default Transceiver high warning threshold."
        ::= { transceiverDdmInfoEntry 5 }

        transceiverDdmInfoEntryWarnMin OBJECT-TYPE
        SYNTAX  DisplayString        
        MAX-ACCESS  read-only
        STATUS  current
        DESCRIPTION
                      	"Default Transceiver low warning threshold."
        ::= { transceiverDdmInfoEntry 6 }

        transceiverDdmInfoEntryCurrent OBJECT-TYPE
        SYNTAX  DisplayString    
        MAX-ACCESS  read-only
        STATUS  current
        DESCRIPTION
                      	"Transceiver current value."
        ::= { transceiverDdmInfoEntry 7 }
        
        transceiverDdmInfoEntryDescription OBJECT-TYPE
        SYNTAX  DisplayString
        MAX-ACCESS  read-only
        STATUS  current
        DESCRIPTION
                      	"Transceiver module type names"
        ::= { transceiverDdmInfoEntry 8 }  

-- vturSwitchStatus
	vturSwitchStatus     	OBJECT IDENTIFIER ::= { ves1724-56fanless 118 }

-- vturLayer2Status
		vturLayer2Status     	OBJECT IDENTIFIER ::= { vturSwitchStatus 1 }

	layer2StatusTable OBJECT-TYPE
       	SYNTAX	SEQUENCE OF Layer2StatusEntry
       	MAX-ACCESS  not-accessible
       	STATUS  current
       	DESCRIPTION
      	      	""
       	::= { vturLayer2Status 1 }

	layer2StatusEntry OBJECT-TYPE
       	SYNTAX	Layer2StatusEntry
       	MAX-ACCESS	not-accessible
       	STATUS	current
       	DESCRIPTION    	"An entry in layer2Table."
       	INDEX          	{ dot1dBasePort}
       	::= { layer2StatusTable 1 }

        Layer2StatusEntry ::=
       	SEQUENCE {
	       	vturIgmpSnoopingStatus	INTEGER,
	       	vturUnknownMulticastStatus	INTEGER
        }

        vturIgmpSnoopingStatus OBJECT-TYPE
        SYNTAX  INTEGER {
         		enabled(1),
         		disabled(2)
        }
        MAX-ACCESS  read-only
        STATUS  current
        DESCRIPTION
                      ""
        ::= { layer2StatusEntry 2 }

		vturUnknownMulticastStatus OBJECT-TYPE
		SYNTAX INTEGER {
				block(1),
				forward(2)
		}
		MAX-ACCESS	read-only
		STATUS	current
		DESCRIPTION
		              ""
		::= { layer2StatusEntry 4 }
       
-- vturPortStatus
		vturPortStatus     	OBJECT IDENTIFIER ::= { vturSwitchStatus 2 }

-- PortTable
    portStatusTable OBJECT-TYPE
       	SYNTAX	SEQUENCE OF PortStatusEntry
       	MAX-ACCESS  not-accessible
       	STATUS  current
       	DESCRIPTION
      	      	""
       	::= { vturPortStatus 1 }

	portStatusEntry OBJECT-TYPE
       	SYNTAX	PortStatusEntry
       	MAX-ACCESS	not-accessible
       	STATUS	current
       	DESCRIPTION    	"An entry in portTable."
       	INDEX          	{ dot1dBasePort, portStatusNumber }
       	::= { portStatusTable 1 }

    PortStatusEntry ::=
       	SEQUENCE {
       	portStatusNumber	INTEGER,
        portStatusOperStatus	INTEGER,
        portStatusOperSpeed	INTEGER  
        }

    portStatusNumber OBJECT-TYPE
       	SYNTAX  INTEGER
     	MAX-ACCESS  read-only
       	STATUS  current
       	DESCRIPTION
                    	"Display all ports we got in CPE side"
        ::= { portStatusEntry 1 }

    portStatusOperStatus OBJECT-TYPE
       	SYNTAX  INTEGER {
       	enable(1),
       	disable(2)
       	}
     	MAX-ACCESS  read-only
       	STATUS  current
       	DESCRIPTION
                    	"CPE port's current status."
        ::= { portStatusEntry 3 }


    portStatusOperSpeed OBJECT-TYPE
       	SYNTAX  INTEGER {
       	linkdown(0),
       	autoneg(1),
       	half_10M(2),
       	full_10M(3),
       	half_100M(4),
       	full_100M(5)
       	}
       	MAX-ACCESS  read-only
       	STATUS  current
       	DESCRIPTION
                     	"CPE port's current speed."
        ::= { portStatusEntry 8 }




-- vturWanStatus
		vturWanStatus     	OBJECT IDENTIFIER ::= { vturSwitchStatus 4 }


-- vturWanTable
	vturWanInfo OBJECT IDENTIFIER ::= { vturWanStatus 1 }
	
	vturWanStatusTable OBJECT-TYPE
       	SYNTAX	SEQUENCE OF VturWanStatusEntry
       	MAX-ACCESS  not-accessible
       	STATUS  current
       	DESCRIPTION
      	      	""
       	::= { vturWanInfo 1 }

     vturWanStatusEntry OBJECT-TYPE
       	SYNTAX	VturWanStatusEntry
       	MAX-ACCESS	not-accessible
       	STATUS	current
       	DESCRIPTION    	"An entry in vturWanTable."
       	INDEX          	{ dot1dBasePort, vturWanStatusIndex }
       	::= { vturWanStatusTable 1 }

     VturWanStatusEntry ::=
       	SEQUENCE {
	    	vturWanStatusIndex	INTEGER,
			vturWanStatusVlanTagging	INTEGER,
			vturWanStatusVlanID	INTEGER,
			vturWanStatus8021p	INTEGER,
			vturWanStatusPPPUsername	OCTET STRING,
			vturWanStatusPPPPassword	OCTET STRING,
			vturWanStatusProtocol INTEGER,
			vturWanStatusProtocolSetting BITS,
			vturWanStatusIP IpAddress,
			vturWanStatusSubnetMask IpAddress,
			vturWanStatusService	EnabledStatus,
			vturWanStatusMAC	MacAddress
        }

     vturWanStatusIndex OBJECT-TYPE
       	SYNTAX  INTEGER
       	MAX-ACCESS  read-only
       	STATUS  current
       	DESCRIPTION
                   	"Display the wan index range from 1 to 4 we got in CPE side"
       	::= { vturWanStatusEntry 1 }

     vturWanStatusVlanTagging OBJECT-TYPE
       	SYNTAX  INTEGER
       	{
       	disable(1),
       	vlan_mux(2),
       	auto_vlan(3)
       	}
       	MAX-ACCESS  read-only
       	STATUS  current
       	DESCRIPTION
                   	"Display the vlan tagging we got in CPE side"
       	::= { vturWanStatusEntry 2 }

     vturWanStatusVlanID OBJECT-TYPE
       	SYNTAX  INTEGER
       	MAX-ACCESS  read-only
       	STATUS  current
       	DESCRIPTION
                   	"Display the vlan id range from 1 to 4094 we got in CPE side"
       	::= { vturWanStatusEntry 3 }       	

     vturWanStatus8021p OBJECT-TYPE
       	SYNTAX  INTEGER
       	MAX-ACCESS  read-only
       	STATUS  current
       	DESCRIPTION
                   	"Display the 802.1p value range from 0 to 7 we got in CPE side"
       	::= { vturWanStatusEntry 4 }

     vturWanStatusPPPUsername OBJECT-TYPE
       	SYNTAX  OCTET STRING
       	MAX-ACCESS  read-only
       	STATUS  current
       	DESCRIPTION
                   	"Display the PPP username we got in CPE side"
       	::= { vturWanStatusEntry 5 }
       	
     vturWanStatusPPPPassword OBJECT-TYPE
       	SYNTAX  OCTET STRING
       	MAX-ACCESS  read-only
       	STATUS  current
       	DESCRIPTION
                   	"Display the PPP password we got in CPE side"
       	::= { vturWanStatusEntry 6 }
       	
     vturWanStatusProtocol OBJECT-TYPE
       	SYNTAX  INTEGER
       	{
       	pppoe(1),
       	mer(2),
       	bridge(3)
       	}
       	MAX-ACCESS  read-only
       	STATUS  current
       	DESCRIPTION
                   	"Display the wan protocol info we got in CPE side"
       	::= { vturWanStatusEntry 7 }

     vturWanStatusProtocolSetting OBJECT-TYPE
       	SYNTAX  BITS
       	{
		dhcp_client_(0),
		nat(1),
		firewall(2),
		igmp(3)
	}       	
       	MAX-ACCESS  read-only
       	STATUS  current
       	DESCRIPTION
                   	"Display the wan service enable/disable status we got in CPE side"
       	::= { vturWanStatusEntry 8 }       	       	       	       	      
          
      vturWanStatusIP OBJECT-TYPE
        SYNTAX  IpAddress
        MAX-ACCESS  read-only
        STATUS  current
        DESCRIPTION
                      	"Display the wan IP setting we got in CPE side"
        ::= { vturWanStatusEntry 9 }

      vturWanStatusSubnetMask OBJECT-TYPE
        SYNTAX  IpAddress
        MAX-ACCESS  read-only
        STATUS  current
        DESCRIPTION
                      	"Display the wan subnet mask we got in CPE side"
        ::= { vturWanStatusEntry 10 }

     vturWanStatusService OBJECT-TYPE
       	SYNTAX  EnabledStatus
       	MAX-ACCESS  read-only
       	STATUS  current
       	DESCRIPTION
                   	"Display the wan service enable/disable status we got in CPE side"
       	::= { vturWanStatusEntry 11 }       	       	       	       	           

    vturWanStatusMAC OBJECT-TYPE
       	SYNTAX  MacAddress
       	MAX-ACCESS  read-only
       	STATUS  current
       	DESCRIPTION
                   	"Display the wan MAC we got in CPE side"
       	::= { vturWanStatusEntry 12 }       	       	       	       	           

	vturWanStatusCommon OBJECT IDENTIFIER ::= { vturWanStatus 2 }

        vturWanStatusCommonTable  OBJECT-TYPE
        SYNTAX	SEQUENCE OF VturWanStatusCommonEntry
       	MAX-ACCESS  not-accessible
       	STATUS  current
       	DESCRIPTION
      	      	""
        ::= { vturWanStatusCommon 1 }

	vturWanStatusCommonEntry OBJECT-TYPE
       	SYNTAX	VturWanStatusCommonEntry
       	MAX-ACCESS	not-accessible
       	STATUS	current
       	DESCRIPTION    	"An entry in vturWanCommonTable."
       	INDEX          	{ dot1dBasePort}
       	::= { vturWanStatusCommonTable 1 }

        VturWanStatusCommonEntry ::=
       	SEQUENCE {
	       	vturWanStatusCommonQoS							EnabledStatus,
	       	vturWanStatusCommonEnableAutoDefaultGateway		EnabledStatus,
	        vturWanStatusCommonDefaultGatewayIP				IpAddress,
	        vturWanStatusCommonVitualPortEnable				EnabledStatus
        }


        vturWanStatusCommonQoS OBJECT-TYPE
        SYNTAX  EnabledStatus
        MAX-ACCESS  read-only
        STATUS  current
        DESCRIPTION
                      ""
        ::= { vturWanStatusCommonEntry 1 }

        vturWanStatusCommonEnableAutoDefaultGateway OBJECT-TYPE
        SYNTAX  EnabledStatus 
        MAX-ACCESS  read-only
        STATUS  current
        DESCRIPTION
                      "Display the enable auto default gateay setting we get from CPE side"
        ::= { vturWanStatusCommonEntry 2 }

        vturWanStatusCommonDefaultGatewayIP OBJECT-TYPE
       	SYNTAX  IpAddress 
     	MAX-ACCESS  read-only
       	STATUS  current
       	DESCRIPTION
       		"Display the default gateway setting we get from CPE side"
        ::= { vturWanStatusCommonEntry 3 }

        vturWanStatusCommonVitualPortEnable OBJECT-TYPE
        SYNTAX  EnabledStatus
        MAX-ACCESS  read-only
        STATUS  current
        DESCRIPTION
                      "Display Enable/Disable virtual port on eth1 setting we get on CPE side"
        ::= { vturWanStatusCommonEntry 4 }


-- vturClassificationStatus
		vturClassificationStatus     	OBJECT IDENTIFIER ::= { vturSwitchStatus 5 }


-- vturClassificationTable
    vturClassificationStatusTable OBJECT-TYPE
       	SYNTAX	SEQUENCE OF VturClassificationStatusEntry
       	MAX-ACCESS  not-accessible
       	STATUS  current
       	DESCRIPTION
      	      	""
       	::= { vturClassificationStatus 1 }

     vturClassificationStatusEntry OBJECT-TYPE
       	SYNTAX	VturClassificationStatusEntry
       	MAX-ACCESS	not-accessible
       	STATUS	current
       	DESCRIPTION    	"An entry in vturClassificationTable."
       	INDEX          	{ dot1dBasePort, vturClassificationStatusIndex }
       	::= { vturClassificationStatusTable 1 }

     VturClassificationStatusEntry ::=
       	SEQUENCE {
        	vturClassificationStatusIndex	INTEGER,
			vturClassificationStatusRuleEnable	EnabledStatus,
			vturClassificationStatusWanInterface		INTEGER,
			vturClassificationStatusQueue		INTEGER,
			vturClassificationStatus8021p		INTEGER,
			vturClassificationStatusVid		INTEGER,
			vturClassificationStatusFilterPhysicalPort		INTEGER,
			vturClassificationStatusFilterProtocol		INTEGER,
			vturClassificationStatusFilterSourceIP		IpAddress,
			vturClassificationStatusFilterSourceSubnetMask	IpAddress,
			vturClassificationStatusFilterDestinationIP		IpAddress,
			vturClassificationStatusFilterDestinationSubnetMask	IpAddress,
			vturClassificationStatusFilterSourcePortStart	INTEGER,
			vturClassificationStatusFilterSourcePortEnd		INTEGER,
			vturClassificationStatusFilterDestinationPortStart	INTEGER,
			vturClassificationStatusFilterDestinationPortEnd	INTEGER,
			vturClassificationStatusFilterSourceMACAddr		OCTET STRING,
			vturClassificationStatusFilterSourceMACMask		OCTET STRING,
			vturClassificationStatusFilterDestinationMACAddr	OCTET STRING,
			vturClassificationStatusFilterDestinationMACMask	OCTET STRING,
			vturClassificationStatusFilter8021p			INTEGER,
			vturClassificationStatusFilterProtocolType		INTEGER,
			vturClassificationStatusPolicyGatewayIP		IpAddress
        }

     vturClassificationStatusIndex OBJECT-TYPE
       	SYNTAX  INTEGER
       	MAX-ACCESS  read-only
       	STATUS  current
       	DESCRIPTION
                   	"Display the classification index range from 1 to 8 we got in CPE side"
       	::= { vturClassificationStatusEntry 1 }

     vturClassificationStatusRuleEnable OBJECT-TYPE
       	SYNTAX  EnabledStatus
       	MAX-ACCESS  read-only
       	STATUS  current
       	DESCRIPTION
                   	"Display the classification enable/disable status we got in CPE side"
       	::= { vturClassificationStatusEntry 2 }

     vturClassificationStatusWanInterface OBJECT-TYPE
       	SYNTAX  INTEGER
       	MAX-ACCESS  read-only
       	STATUS  current
       	DESCRIPTION
                   	"Display the wan interface index range from 1 to 4 we got in CPE side"
       	::= { vturClassificationStatusEntry 3 }       	

     vturClassificationStatusQueue OBJECT-TYPE
       	SYNTAX  INTEGER
       	MAX-ACCESS  read-only
       	STATUS  current
       	DESCRIPTION
                   	"Display the assigned queue (1-4)802.1p value we got in CPE side"
       	::= { vturClassificationStatusEntry 4 }
      
     vturClassificationStatus8021p OBJECT-TYPE
       	SYNTAX  INTEGER
       	MAX-ACCESS  read-only
       	STATUS  current
       	DESCRIPTION
                   	"Mark 802.1p if 802.1q is enabled [0-7]"
       	::= { vturClassificationStatusEntry 5 }

     vturClassificationStatusVid OBJECT-TYPE
       	SYNTAX  INTEGER
       	MAX-ACCESS  read-only
       	STATUS  current
       	DESCRIPTION
                   	"Display the 802.1Q VLAN ID: [1-4094]"
       	::= { vturClassificationStatusEntry 6 }
       	
     vturClassificationStatusFilterPhysicalPort OBJECT-TYPE
       	SYNTAX  INTEGER
       	MAX-ACCESS  read-only
       	STATUS  current
       	DESCRIPTION
                   	" Physical LAN Port number"
       	::= { vturClassificationStatusEntry 7 }

     vturClassificationStatusFilterProtocol OBJECT-TYPE
                SYNTAX  INTEGER{
		tcp_udp(1),
       	tcp(2),
       	udp(3),
       	icmp(4)
       	}
       	MAX-ACCESS  read-only
       	STATUS  current
       	DESCRIPTION
                   	"Protocol: [TCP/UDP, TCP, UDP, ICMP]  1-4"
       	::= { vturClassificationStatusEntry 8 }       	       	       	       	      

     vturClassificationStatusFilterSourceIP OBJECT-TYPE
       	SYNTAX  IpAddress
       	MAX-ACCESS  read-only
       	STATUS  current
       	DESCRIPTION
                   	"Display the filtering source IP we got in CPE side"
       	::= { vturClassificationStatusEntry 9 }

     vturClassificationStatusFilterSourceSubnetMask OBJECT-TYPE
       	SYNTAX  IpAddress
       	MAX-ACCESS  read-only
       	STATUS  current
       	DESCRIPTION
                   	"Display the filtering source subnet mask we got in CPE side"
       	::= { vturClassificationStatusEntry 10 }

     vturClassificationStatusFilterDestinationIP OBJECT-TYPE
       	SYNTAX  IpAddress
       	MAX-ACCESS  read-only
       	STATUS  current
       	DESCRIPTION
                   	"Display the filtering destination IP we got in CPE side"
       	::= { vturClassificationStatusEntry 11 }       	

     vturClassificationStatusFilterDestinationSubnetMask OBJECT-TYPE
       	SYNTAX  IpAddress
       	MAX-ACCESS  read-only
       	STATUS  current
       	DESCRIPTION
                   	"Display the filtering destination subnet mask we got in CPE side"
       	::= { vturClassificationStatusEntry 12 }
       	
     vturClassificationStatusFilterSourcePortStart OBJECT-TYPE
       	SYNTAX  INTEGER
       	MAX-ACCESS  read-only
       	STATUS  current
       	DESCRIPTION
                   	"Display the filtering source port start we got in CPE side"
       	::= { vturClassificationStatusEntry 13 }
       	
     vturClassificationStatusFilterSourcePortEnd OBJECT-TYPE
       	SYNTAX  INTEGER
       	MAX-ACCESS  read-only
       	STATUS  current
       	DESCRIPTION
                   	"Display the filtering source port end we got in CPE side"
       	::= { vturClassificationStatusEntry 14 }

     vturClassificationStatusFilterDestinationPortStart OBJECT-TYPE
       	SYNTAX  INTEGER
       	MAX-ACCESS  read-only
       	STATUS  current
       	DESCRIPTION
                   	"Display the filtering destination port start we got in CPE side"
       	::= { vturClassificationStatusEntry 15 }
       	
     vturClassificationStatusFilterDestinationPortEnd OBJECT-TYPE
       	SYNTAX  INTEGER
       	MAX-ACCESS  read-only
       	STATUS  current
       	DESCRIPTION
                   	"Display the filtering destination end port we got in CPE side"
       	::= { vturClassificationStatusEntry 16 }       	

     vturClassificationStatusFilterSourceMACAddr OBJECT-TYPE
       	SYNTAX  OCTET STRING
       	MAX-ACCESS  read-only
       	STATUS  current
       	DESCRIPTION
                   	"Display the filtering source MAC addr we got in CPE side"
       	::= { vturClassificationStatusEntry 17 }
       	
     vturClassificationStatusFilterSourceMACMask OBJECT-TYPE
       	SYNTAX  OCTET STRING
       	MAX-ACCESS  read-only
       	STATUS  current
       	DESCRIPTION
                   	"Display the filtering source MAC mask we got in CPE side"
       	::= { vturClassificationStatusEntry 18 }      

     vturClassificationStatusFilterDestinationMACAddr OBJECT-TYPE
       	SYNTAX  OCTET STRING
       	MAX-ACCESS  read-only
       	STATUS  current
       	DESCRIPTION
                   	"Display the filtering destination MAC addr we got in CPE side"
       	::= { vturClassificationStatusEntry 19 }
       	
     vturClassificationStatusFilterDestinationMACMask OBJECT-TYPE
       	SYNTAX  OCTET STRING
       	MAX-ACCESS  read-only
       	STATUS  current
       	DESCRIPTION
                   	"Display the filtering destination MAC mask we got in CPE side"
       	::= { vturClassificationStatusEntry 20 }  

     vturClassificationStatusFilter8021p OBJECT-TYPE
       	SYNTAX  INTEGER
       	MAX-ACCESS  read-only
       	STATUS  current
       	DESCRIPTION
                   	"Display the filtering 802.1p value we got in CPE side"
       	::= { vturClassificationStatusEntry 21 }
       	
     vturClassificationStatusFilterProtocolType OBJECT-TYPE
       	SYNTAX  INTEGER
       	MAX-ACCESS  read-only
       	STATUS  current
       	DESCRIPTION
                   	"Display the filtering protocol type we got in CPE side"
       	::= { vturClassificationStatusEntry 22 } 

     vturClassificationStatusPolicyGatewayIP OBJECT-TYPE
       	SYNTAX  IpAddress
       	MAX-ACCESS  read-only
       	STATUS  current
       	DESCRIPTION
                   	"Display the filtering protocol type we got in CPE side"
       	::= { vturClassificationStatusEntry 23 } 

      
-- vturMiscStatus
--		vturMiscStatus     	OBJECT IDENTIFIER ::= { vturSwitchStatus 6 }


-- vturMntTable
--    vturMntTable OBJECT-TYPE
--       	SYNTAX	SEQUENCE OF VturMntEntry
--       	MAX-ACCESS  not-accessible
--       	STATUS  current
--       	DESCRIPTION
--      	      	""
--       	::= { vturMiscStatus 1 }

--	vturMntEntry OBJECT-TYPE
--       	SYNTAX	VturMntEntry
--       	MAX-ACCESS	not-accessible
--       	STATUS	current
--       	DESCRIPTION    	"An entry in VTUR Misc Table."
--       	INDEX          	{ dot1dBasePort }
--       	::= { vturMntTable 1 }

--    VturMntEntry ::=
--       	SEQUENCE {
--        mntOperation	INTEGER,    
--        mntCommit		INTEGER,
--        mntStatus		INTEGER
--        }

--    mntOperation OBJECT-TYPE
--       	SYNTAX  INTEGER {
--       	layer2Setup(1),
--       	portSetup(2),
--       	priorityQueueSetup(3),
--       	dot1qVlanSetup(4),
--       	portBasedVlanSetup(5),
--       	loadFactoryDefault(6),
--       	resetSW(7),
--        apBasicSetup(8),
--        apSecuritySetup(9),
--        apRadiusSetup(10),
--        apMacFilterSetup(11),
--        apMacFilterAddrSetup(12),
--        reinit(13),
--        consoleSetup(14),
--        remoteFunctionSetup(15),         
--        regetstatue(16),         
--        protocolBasedVlanSetup(17),
--        vturWanSetup(18),
--        vturClassificationSetup(19),
--        vturLanSetup(20),
--        vturResetCounter(21),
--        loadDefaultWithoutIP(22)
--       	}
--       	MAX-ACCESS  read-write
--       	STATUS  current
--       	DESCRIPTION
--                   	"Specify the operation of VTUR"
--       	::= { vturMntEntry 1 }
    
--    mntCommit OBJECT-TYPE
--       	SYNTAX  INTEGER {
--       	idle(0),
--       	commit(1)
--       	}
--       	MAX-ACCESS  read-write
--       	STATUS  current
--       	DESCRIPTION
--                    	"Apply maintenance setting to vtur"
--        ::= { vturMntEntry 2 }
    
--    mntStatus OBJECT-TYPE
--       	SYNTAX  INTEGER {
--       	in-progress(0),
--       	success(1),
--       	fail(2)
--       	}
--       	MAX-ACCESS  read-only
--       	STATUS  current
--       	DESCRIPTION
--                    	"Display the current status regarding to the operation."
--        ::= { vturMntEntry 3 }

-- vturAPStatus
	vturAPStatus     	OBJECT IDENTIFIER ::= { vturSwitchStatus 7 }
	
-- vturAPGeneral
        vturAPGeneralStatus OBJECT IDENTIFIER ::= { vturAPStatus 1 }

-- vturAPGeneralStatisticsTable

        vturAPGeneralStatusTable  OBJECT-TYPE
        SYNTAX	SEQUENCE OF VturAPGeneralStatusEntry
        MAX-ACCESS  not-accessible
        STATUS  current
        DESCRIPTION
                 	""
        ::= { vturAPGeneralStatus 1 }

		vturAPGeneralStatusEntry OBJECT-TYPE
       		SYNTAX	VturAPGeneralStatusEntry
       		MAX-ACCESS	not-accessible
       		STATUS	current
	       	DESCRIPTION    	"An entry in VTUR AP General Statistics Table."
	       	INDEX          	{ dot1dBasePort }
	       	::= { vturAPGeneralStatusTable 1 }

		VturAPGeneralStatusEntry ::=
	       	SEQUENCE {
	        	vturLanRxBytes	Counter32,
	        	vturLanRxPkts	Counter32,
	        	vturLanTxBytes	Counter32,
	        	vturLanTxPkts	Counter32,
	        	vturVdslRxBytes	Counter32,
	        	vturVdslRxPkts	Counter32,
	        	vturVdslTxBytes	Counter32,
	        	vturVdslTxPkts	Counter32,
	        	vturWlanRxBytes	Counter32,
	        	vturWlanRxPkts	Counter32,
	        	vturWlanRxErrs	Counter32,
	        	vturWlanRxDrops	Counter32,
	        	vturWlanTxBytes	Counter32,
	        	vturWlanTxPkts	Counter32,
	        	vturWlanTxErrs	Counter32,
	        	vturWlanTxDrops	Counter32
	        }


		        vturLanRxBytes OBJECT-TYPE
        		SYNTAX  Counter32
        		MAX-ACCESS  read-only
        		STATUS  current
        		DESCRIPTION
                      		"Received bytes on LAN"
        		::= { vturAPGeneralStatusEntry 1 }

		        vturLanRxPkts OBJECT-TYPE
        		SYNTAX  Counter32
        		MAX-ACCESS  read-only
        		STATUS  current
        		DESCRIPTION
                      		"Received frames on LAN"
        		::= { vturAPGeneralStatusEntry 2 }


		        vturLanTxBytes OBJECT-TYPE
        		SYNTAX  Counter32
        		MAX-ACCESS  read-only
        		STATUS  current
        		DESCRIPTION
                      		"Transmitted bytes on LAN"
        		::= { vturAPGeneralStatusEntry 3 }

		        vturLanTxPkts OBJECT-TYPE
        		SYNTAX  Counter32
        		MAX-ACCESS  read-only
        		STATUS  current
        		DESCRIPTION
                      		"Transmitted frames on LAN"
        		::= { vturAPGeneralStatusEntry 4 }

		        vturVdslRxBytes OBJECT-TYPE
        		SYNTAX  Counter32
        		MAX-ACCESS  read-only
        		STATUS  current
        		DESCRIPTION
                      		"Received bytes on VDSL"
        		::= { vturAPGeneralStatusEntry 5 }

		        vturVdslRxPkts OBJECT-TYPE
        		SYNTAX  Counter32
        		MAX-ACCESS  read-only
        		STATUS  current
        		DESCRIPTION
                      		"Received frames on VDSL"
        		::= { vturAPGeneralStatusEntry 6 }

		        vturVdslTxBytes OBJECT-TYPE
        		SYNTAX  Counter32
        		MAX-ACCESS  read-only
        		STATUS  current
        		DESCRIPTION
                      		"Transmitted bytes on VDSL"
        		::= { vturAPGeneralStatusEntry 7 }

		        vturVdslTxPkts OBJECT-TYPE
        		SYNTAX  Counter32
        		MAX-ACCESS  read-only
        		STATUS  current
        		DESCRIPTION
                      		"Transmitted frames on VDSL"
        		::= { vturAPGeneralStatusEntry 8 }

		        vturWlanRxBytes OBJECT-TYPE
        		SYNTAX  Counter32
        		MAX-ACCESS  read-only
        		STATUS  current
        		DESCRIPTION
                      		"Received bytes on WLAN"
        		::= { vturAPGeneralStatusEntry 9 }

		        vturWlanRxPkts OBJECT-TYPE
        		SYNTAX  Counter32
        		MAX-ACCESS  read-only
        		STATUS  current
        		DESCRIPTION
                      		"Received frames on WLAN "
        		::= { vturAPGeneralStatusEntry 10 }

		        vturWlanRxErrs OBJECT-TYPE
        		SYNTAX  Counter32
        		MAX-ACCESS  read-only
        		STATUS  current
        		DESCRIPTION
                      		"Received error frames on WLAN "
        		::= { vturAPGeneralStatusEntry 11 }

		        vturWlanRxDrops OBJECT-TYPE
        		SYNTAX  Counter32
        		MAX-ACCESS  read-only
        		STATUS  current
        		DESCRIPTION
                      		"Received drop frames on WLAN "
        		::= { vturAPGeneralStatusEntry 12 }

		        vturWlanTxBytes OBJECT-TYPE
        		SYNTAX  Counter32
        		MAX-ACCESS  read-only
        		STATUS  current
        		DESCRIPTION
                      		"Transmitted bytes on WLAN "
        		::= { vturAPGeneralStatusEntry 13 }

		        vturWlanTxPkts OBJECT-TYPE
        		SYNTAX  Counter32
        		MAX-ACCESS  read-only
        		STATUS  current
        		DESCRIPTION
                      		"Transmitted frames on WLAN "
        		::= { vturAPGeneralStatusEntry 14 }

		        vturWlanTxErrs OBJECT-TYPE
        		SYNTAX  Counter32
        		MAX-ACCESS  read-only
        		STATUS  current
        		DESCRIPTION
                      		"Transmitted error frames on WLAN "
        		::= { vturAPGeneralStatusEntry 15 }

		        vturWlanTxDrops OBJECT-TYPE
        		SYNTAX  Counter32
        		MAX-ACCESS  read-only
        		STATUS  current
        		DESCRIPTION
                      		"Transmitted drop frames on WLAN "
        		::= { vturAPGeneralStatusEntry 16 }

-- vturAPPerSSIDStatisticsTable

        vturAPPerSSIDStatusTable  OBJECT-TYPE
        SYNTAX	SEQUENCE OF VturAPPerSSIDStatusEntry
        MAX-ACCESS  not-accessible
        STATUS  current
        DESCRIPTION
                 	""
        ::= { vturAPGeneralStatus 2 }

		vturAPPerSSIDStatusEntry OBJECT-TYPE
       		SYNTAX	VturAPPerSSIDStatusEntry
       		MAX-ACCESS	not-accessible
       		STATUS	current
	       	DESCRIPTION    	"An entry in VTUR AP Per-SSID Statistics Table."
	       	INDEX          	{ dot1dBasePort, vturWlanPerSSIDStatusIndex }
	       	::= { vturAPPerSSIDStatusTable 1 }

		VturAPPerSSIDStatusEntry ::=
	       	SEQUENCE {
	       		vturWlanPerSSIDStatusIndex	INTEGER,
                vturWlanPerSSIDStatusSSID	DisplayString,
	        	vturWlanPerSSIDRxBytes		Counter32,
	        	vturWlanPerSSIDRxPkts		Counter32,
	        	vturWlanPerSSIDRxErrs		Counter32,
	        	vturWlanPerSSIDRxDrops		Counter32,
	        	vturWlanPerSSIDTxBytes		Counter32,
	        	vturWlanPerSSIDTxPkts		Counter32,
	        	vturWlanPerSSIDTxErrs		Counter32,
	        	vturWlanPerSSIDTxDrops		Counter32
	        }

		        vturWlanPerSSIDStatusIndex OBJECT-TYPE
        		SYNTAX  INTEGER
        		MAX-ACCESS  read-only
        		STATUS  current
        		DESCRIPTION
                      		"Index of vturAPPerSSIDStatusTable"
        		::= { vturAPPerSSIDStatusEntry 1 }

		        vturWlanPerSSIDStatusSSID OBJECT-TYPE
        		SYNTAX  DisplayString
        		MAX-ACCESS  read-only
        		STATUS  current
        		DESCRIPTION
                      		"WLAN SSID"
        		::= { vturAPPerSSIDStatusEntry 2 }

		        vturWlanPerSSIDRxBytes OBJECT-TYPE
        		SYNTAX  Counter32
        		MAX-ACCESS  read-only
        		STATUS  current
        		DESCRIPTION
                      		"Received bytes on WLAN"
        		::= { vturAPPerSSIDStatusEntry 3 }

		        vturWlanPerSSIDRxPkts OBJECT-TYPE
        		SYNTAX  Counter32
        		MAX-ACCESS  read-only
        		STATUS  current
        		DESCRIPTION
                      		"Received frames on WLAN "
        		::= { vturAPPerSSIDStatusEntry 4 }

		        vturWlanPerSSIDRxErrs OBJECT-TYPE
        		SYNTAX  Counter32
        		MAX-ACCESS  read-only
        		STATUS  current
        		DESCRIPTION
                      		"Received error frames on WLAN "
        		::= { vturAPPerSSIDStatusEntry 5 }

		        vturWlanPerSSIDRxDrops OBJECT-TYPE
        		SYNTAX  Counter32
        		MAX-ACCESS  read-only
        		STATUS  current
        		DESCRIPTION
                      		"Received drop frames on WLAN "
        		::= { vturAPPerSSIDStatusEntry 6 }

		        vturWlanPerSSIDTxBytes OBJECT-TYPE
        		SYNTAX  Counter32
        		MAX-ACCESS  read-only
        		STATUS  current
        		DESCRIPTION
                      		"Transmitted bytes on WLAN "
        		::= { vturAPPerSSIDStatusEntry 7 }

		        vturWlanPerSSIDTxPkts OBJECT-TYPE
        		SYNTAX  Counter32
        		MAX-ACCESS  read-only
        		STATUS  current
        		DESCRIPTION
                      		"Transmitted frames on WLAN "
        		::= { vturAPPerSSIDStatusEntry 8 }

		        vturWlanPerSSIDTxErrs OBJECT-TYPE
        		SYNTAX  Counter32
        		MAX-ACCESS  read-only
        		STATUS  current
        		DESCRIPTION
                      		"Transmitted error frames on WLAN "
        		::= { vturAPPerSSIDStatusEntry 9 }

		        vturWlanPerSSIDTxDrops OBJECT-TYPE
        		SYNTAX  Counter32
        		MAX-ACCESS  read-only
        		STATUS  current
        		DESCRIPTION
                      		"Transmitted drop frames on WLAN "
        		::= { vturAPPerSSIDStatusEntry 10 }

		vturAPPortLinkUpTimeTable  OBJECT-TYPE
        SYNTAX	SEQUENCE OF VturAPPortLinkUpTimeEntry
        MAX-ACCESS  not-accessible
        STATUS  current
        DESCRIPTION
                 	""
        ::= { vturAPGeneralStatus 3 }

		vturAPPortLinkUpTimeEntry OBJECT-TYPE
       		SYNTAX	VturAPPortLinkUpTimeEntry
       		MAX-ACCESS	not-accessible
       		STATUS	current
	       	DESCRIPTION    	"An entry in VTUR AP General Statistics Table."
	       	INDEX          	{ dot1dBasePort, vturPortIndex}
	       	::= { vturAPPortLinkUpTimeTable 1 }

		VturAPPortLinkUpTimeEntry ::=
	       	SEQUENCE {
	        	vturPortIndex		INTEGER,
	        	vturLinkUpTime		Counter32
	        }

		        vturPortIndex OBJECT-TYPE
        		SYNTAX  INTEGER
        		MAX-ACCESS  read-only
        		STATUS  current
        		DESCRIPTION
                      		"Port index of vtur"
        		::= { vturAPPortLinkUpTimeEntry 1 }

		        vturLinkUpTime OBJECT-TYPE
        		SYNTAX  Counter32
        		MAX-ACCESS  read-only
        		STATUS  current
        		DESCRIPTION
                      		"Port link up time"
        		::= { vturAPPortLinkUpTimeEntry 2 }



-- vturAPWlanStatus
        vturAPWlanStatus OBJECT IDENTIFIER ::= { vturAPStatus 2 }

-- vturAPWlanBasicTable

        vturAPWlanStatusBasicTable  OBJECT-TYPE
        SYNTAX	SEQUENCE OF VturAPWlanStatusBasicEntry
        MAX-ACCESS  not-accessible
        STATUS  current
        DESCRIPTION
                 	""
        ::= { vturAPWlanStatus 1 }

		vturAPWlanStatusBasicEntry OBJECT-TYPE
       		SYNTAX	VturAPWlanStatusBasicEntry
       		MAX-ACCESS	not-accessible
       		STATUS	current
	       	DESCRIPTION    	"An entry in VTUR AP Wlan Basic Table."
	       	INDEX          	{ dot1dBasePort }
	       	::= { vturAPWlanStatusBasicTable 1 }

		VturAPWlanStatusBasicEntry ::=
	       	SEQUENCE {
		        vturWlanEnable	INTEGER,
		        vturWlanSsid	DisplayString,
		        vturWlanBssid	MacAddress,
		        vturWlanHidden	INTEGER,
		        vturWlanChannel	INTEGER,
		        vturWlanMode	INTEGER,
		        vturWlanTxPower	INTEGER,
		        vturWlanMulticastRate	INTEGER
	        }


		        vturWlanEnable OBJECT-TYPE
        		SYNTAX  INTEGER
        		MAX-ACCESS  read-only
        		STATUS  current
        		DESCRIPTION
                      		"Display the current WLAN status
                      		 0:Disable WLAN
                      		 1:Enable WLAN"
        		::= { vturAPWlanStatusBasicEntry 1 }

		        vturWlanSsid OBJECT-TYPE
        		SYNTAX  DisplayString
        		MAX-ACCESS  read-only
        		STATUS  current
        		DESCRIPTION
                      		"SSID of the AP"
        		::= { vturAPWlanStatusBasicEntry 2 }

		        vturWlanBssid OBJECT-TYPE
        		SYNTAX  MacAddress
        		MAX-ACCESS  read-only
        		STATUS  current
        		DESCRIPTION
                      		"Mac address of AP"
        		::= { vturAPWlanStatusBasicEntry 3 }

		        vturWlanHidden OBJECT-TYPE
        		SYNTAX  INTEGER
        		MAX-ACCESS  read-only
        		STATUS  current
        		DESCRIPTION
                      		"Display the current AP's SSID status
                      		 0: not hide AP's SSID
                      		 1: hide AP's SSID"
        		::= { vturAPWlanStatusBasicEntry 4 }

		        vturWlanChannel OBJECT-TYPE
        		SYNTAX  INTEGER
        		MAX-ACCESS  read-only
        		STATUS  current
        		DESCRIPTION
                      		"Channel number of the AP"
        		::= { vturAPWlanStatusBasicEntry 5 }

		        vturWlanMode OBJECT-TYPE
        		SYNTAX  INTEGER
        		MAX-ACCESS  read-only
        		STATUS  current
        		DESCRIPTION
                      		"Display the current AP's mode
                      		 1: B or G mix mode
                      		 2: Pure G mode
                      		 3: Pure B mode"
        		::= { vturAPWlanStatusBasicEntry 6 }

		        vturWlanTxPower OBJECT-TYPE
        		SYNTAX  INTEGER
        		MAX-ACCESS  read-only
        		STATUS  current
        		DESCRIPTION
                      		"Display the current Transmit power
                      		 1: 30 mW
                      		 2: 15 mW"
        		::= { vturAPWlanStatusBasicEntry 7 }

		        vturWlanMulticastRate OBJECT-TYPE
        		SYNTAX  INTEGER
        		MAX-ACCESS  read-only
        		STATUS  current
        		DESCRIPTION
                      		"Transmit rate of multicast packets. If the value not zero, transmit rate is value * 500kbps
                      		 0: auto
                      		 2, 4, 11, 22: Transmit rate = 1, 2, 5.5, 11 Mbps when mode = pure B mode
                      		 12, 18, 24, 36, 48, 96, 108: Transmit rate = 6, 9, 12, 18, 24, 36, 48, 54 Mbps when mode = pure G mode2, 4, 11, 12, 18, 22, 24, 36, 48, 96, 108: Transmit rate = 1, 2, 5.5, 6, 9, 11, 12, 18, 24, 36, 48, 54 Mbps when mode = B or G mix mode"
        		::= { vturAPWlanStatusBasicEntry 8 }

-- vturAPWlanSecurityTable

        vturAPWlanStatusSecurityTable  OBJECT-TYPE
        SYNTAX	SEQUENCE OF VturAPWlanStatusSecurityEntry
        MAX-ACCESS  not-accessible
        STATUS  current
        DESCRIPTION
                 	""
        ::= { vturAPWlanStatus 2 }

		vturAPWlanStatusSecurityEntry OBJECT-TYPE
       		SYNTAX	VturAPWlanStatusSecurityEntry
       		MAX-ACCESS	not-accessible
       		STATUS	current
	       	DESCRIPTION    	"An entry in VTUR AP Wlan Security Table."
	       	INDEX          	{ dot1dBasePort }
	       	::= { vturAPWlanStatusSecurityTable 1 }

		VturAPWlanStatusSecurityEntry ::=
	       	SEQUENCE {
		        vturWlanSecurityMode	INTEGER,
		        vturWlanWepEncryp	INTEGER,
		        vturWlanKeyId		INTEGER,
		        vturWlanKey1		DisplayString,
		        vturWlanKey2		DisplayString,
		        vturWlanKey3		DisplayString,
		        vturWlanKey4		DisplayString,
		        vturWlanPsk		DisplayString,
		        vturWlanWpaMix		INTEGER,
		        vturWlanReAuthTime	INTEGER,
		        vturWlanIdleTime	INTEGER,
		        vturWlanGtkTime		INTEGER
	        }

		        vturWlanSecurityMode OBJECT-TYPE
        		SYNTAX  INTEGER
        		MAX-ACCESS  read-only
        		STATUS  current
        		DESCRIPTION
                      		"Display the current Security Mode
                      		 1: No security
                      		 2: Static WEP
                      		 3: WPA-PSK
                      		 4: WPA
                      		 5: WPA2
                      		 6: WPA2-PSK"
        		::= { vturAPWlanStatusSecurityEntry 1 }

		        vturWlanWepEncryp OBJECT-TYPE
        		SYNTAX  INTEGER
        		MAX-ACCESS  read-only
        		STATUS  current
        		DESCRIPTION
                      		"This field is for SecurityMode = static WEP.
                      		 1: 64-Bit
                      		 2: 128-Bit"
        		::= { vturAPWlanStatusSecurityEntry 2 }

		        vturWlanKeyId OBJECT-TYPE
        		SYNTAX  INTEGER
        		MAX-ACCESS  read-only
        		STATUS  current
        		DESCRIPTION
                      		"This field is for SecurityMode = static WEP. It indicate which key will be used for encryption. 
                      		 If KeyId is equal to 1, AP will use Key1 to encrypt frame."
        		::= { vturAPWlanStatusSecurityEntry 3 }

		        vturWlanKey1 OBJECT-TYPE
        		SYNTAX  DisplayString
        		MAX-ACCESS  read-only
        		STATUS  current
        		DESCRIPTION
                      		"This field is for SecurityMode = static WEP.
                      		 If WEPEncryp is 64-Bit, key1 will be 10 heximal digits.
                      		 If WEPEncryp is 128-Bit, key1 will be 26 heximal digits."
        		::= { vturAPWlanStatusSecurityEntry 4 }

		        vturWlanKey2 OBJECT-TYPE
        		SYNTAX  DisplayString
        		MAX-ACCESS  read-only
        		STATUS  current
        		DESCRIPTION
                      		"This field is for SecurityMode = static WEP.
                      		 If WEPEncryp is 64-Bit, key2 will be 10 heximal digits.
                      		 If WEPEncryp is 128-Bit, key2 will be 26 heximal digits."
        		::= { vturAPWlanStatusSecurityEntry 5 }

		        vturWlanKey3 OBJECT-TYPE
        		SYNTAX  DisplayString
        		MAX-ACCESS  read-only
        		STATUS  current
        		DESCRIPTION
                      		"This field is for SecurityMode = static WEP.
                      		 If WEPEncryp is 64-Bit, key3 will be 10 heximal digits.
                      		 If WEPEncryp is 128-Bit, key3 will be 26 heximal digits."
        		::= { vturAPWlanStatusSecurityEntry 6 }

		        vturWlanKey4 OBJECT-TYPE
        		SYNTAX  DisplayString
        		MAX-ACCESS  read-only
        		STATUS  current
        		DESCRIPTION
                      		"This field is for SecurityMode = static WEP.
                      		 If WEPEncryp is 64-Bit, key4 will be 10 heximal digits.
                      		 If WEPEncryp is 128-Bit, key4 will be 26 heximal digits."
        		::= { vturAPWlanStatusSecurityEntry 7 }

		        vturWlanPsk OBJECT-TYPE
        		SYNTAX  DisplayString
        		MAX-ACCESS  read-only
        		STATUS  current
        		DESCRIPTION
                      		"This field is for SecurityMode = WPA-PSK or WPA2-PSK. It means Pre-Shared Key"
        		::= { vturAPWlanStatusSecurityEntry 8 }

		        vturWlanWpaMix OBJECT-TYPE
        		SYNTAX  INTEGER
        		MAX-ACCESS  read-only
        		STATUS  current
        		DESCRIPTION
                      		"This field is for SecurityMode = WPA2 or WPA2-PSK. 
                      		 When WPAMix is enable on WPA2, stations with WPA2-AES or WPA-TKIP could connect to AP.
                      		 When WPAMix is enable on WPA2-PSK, stations with WPA2-PSK-AES or WPA-PSK-TKIP could connect to AP.
                      		 0: disable
                      		 1: enable"
        		::= { vturAPWlanStatusSecurityEntry 9 }

		        vturWlanReAuthTime OBJECT-TYPE
        		SYNTAX  INTEGER
        		MAX-ACCESS  read-only
        		STATUS  current
        		DESCRIPTION
                      		"This field is for SecurityMode = WPA-PSK, WPA2-PSK, WPA or WPA2. 
                      		 AP will trigger re-authentication with station every [ReAuthTime] seconds."
        		::= { vturAPWlanStatusSecurityEntry 10 }

		        vturWlanIdleTime OBJECT-TYPE
        		SYNTAX  INTEGER
        		MAX-ACCESS  read-only
        		STATUS  current
        		DESCRIPTION
                      		"This field is for SecurityMode = WPA-PSK, WPA2-PSK, WPA or WPA2. 
                      		 AP will flush station¡¦s information if there are no packets from station for [idleTime] seconds."
        		::= { vturAPWlanStatusSecurityEntry 11 }

		        vturWlanGtkTime OBJECT-TYPE
        		SYNTAX  INTEGER
        		MAX-ACCESS  read-only
        		STATUS  current
        		DESCRIPTION
                      		"This field is for SecurityMode = WPA-PSK, WPA2-PSK, WPA or WPA2. 
                      		 AP will trigger the update of group key with station every [GTKTime] seconds."
        		::= { vturAPWlanStatusSecurityEntry 12 }

-- vturAPWlanStatusRadiusEntry

        vturAPWlanStatusRadiusTable  OBJECT-TYPE
        SYNTAX	SEQUENCE OF VturAPWlanStatusRadiusEntry
        MAX-ACCESS  not-accessible
        STATUS  current
        DESCRIPTION
                 	""
        ::= { vturAPWlanStatus 3 }

		vturAPWlanStatusRadiusEntry OBJECT-TYPE
       		SYNTAX	VturAPWlanStatusRadiusEntry
       		MAX-ACCESS	not-accessible
       		STATUS	current
	       	DESCRIPTION    	"An entry in VTUR AP Wlan Security Table."
	       	INDEX          	{ dot1dBasePort }
	       	::= { vturAPWlanStatusRadiusTable 1 }

		VturAPWlanStatusRadiusEntry ::=
	       	SEQUENCE {
		        vturWlanAuthServIP	InetAddress,
		        vturWlanAuthServPort	INTEGER,
		        vturWlanAuthServSecret	DisplayString,
		        vturWlanAccServActive	INTEGER,
		        vturWlanAccServIP	InetAddress,
		        vturWlanAccServPort	INTEGER,
		        vturWlanAccServSecret	DisplayString
	        }


		        vturWlanAuthServIP OBJECT-TYPE
				SYNTAX      InetAddress
        		MAX-ACCESS  read-only
        		STATUS  current
        		DESCRIPTION
                      		"This field is the IP address of authentication server."
        		::= { vturAPWlanStatusRadiusEntry 1 }

		        vturWlanAuthServPort OBJECT-TYPE
        		SYNTAX  INTEGER
        		MAX-ACCESS  read-only
        		STATUS  current
        		DESCRIPTION
                      		"This field is the port number of authentication server."
        		::= { vturAPWlanStatusRadiusEntry 2 }

		        vturWlanAuthServSecret OBJECT-TYPE
        		SYNTAX  DisplayString
        		MAX-ACCESS  read-only
        		STATUS  current
        		DESCRIPTION
                      		"This field is the shared secret of authentication server."
        		::= { vturAPWlanStatusRadiusEntry 3 }

		        vturWlanAccServActive OBJECT-TYPE
        		SYNTAX  INTEGER
        		MAX-ACCESS  read-only
        		STATUS  current
        		DESCRIPTION
                      		"This field is for activating or inactivating accounting server.
                      		 0: inactivate accounting server.
                      		 1: activate accounting server"
        		::= { vturAPWlanStatusRadiusEntry 4 }


		        vturWlanAccServIP OBJECT-TYPE
        		SYNTAX      InetAddress
        		MAX-ACCESS  read-only
        		STATUS  current
        		DESCRIPTION
                      		"This field is the IP address of accounting server."
        		::= { vturAPWlanStatusRadiusEntry 5 }

		        vturWlanAccServPort OBJECT-TYPE
        		SYNTAX  INTEGER
        		MAX-ACCESS  read-only
        		STATUS  current
        		DESCRIPTION
                      		"This field is the port number of accounting server."
        		::= { vturAPWlanStatusRadiusEntry 6 }

		        vturWlanAccServSecret OBJECT-TYPE
        		SYNTAX  DisplayString
        		MAX-ACCESS  read-only
        		STATUS  current
        		DESCRIPTION
                      		"This field is the shared secret of accounting server."
        		::= { vturAPWlanStatusRadiusEntry 7 }



       	vturAPWlanStatusMacFilter OBJECT IDENTIFIER ::= { vturAPWlanStatus 4 }
-- vturAPWlanMacFilterTable

        vturAPWlanStatusMacFilterTable  OBJECT-TYPE
        SYNTAX	SEQUENCE OF VturAPWlanStatusMacFilterEntry
        MAX-ACCESS  not-accessible
        STATUS  current
        DESCRIPTION
                 	""
        ::= { vturAPWlanStatusMacFilter 1 }

		vturAPWlanStatusMacFilterEntry OBJECT-TYPE
       		SYNTAX	VturAPWlanStatusMacFilterEntry
       		MAX-ACCESS	not-accessible
       		STATUS	current
	       	DESCRIPTION    	"An entry in VTUR AP Wlan Mac Filter Table."
	       	INDEX          	{ dot1dBasePort }
	       	::= { vturAPWlanStatusMacFilterTable 1 }

		VturAPWlanStatusMacFilterEntry ::=
	       	SEQUENCE {
	        vturWlanMacFltActive	INTEGER,
	        vturWlanMacFltAction	INTEGER
	        }

		        vturWlanMacFltActive OBJECT-TYPE
        		SYNTAX  INTEGER
        		MAX-ACCESS  read-only
        		STATUS  current
        		DESCRIPTION
                      		"Activate or inactivate wlan MAC filter.
                      		 0: Inactive
                      		 1: Active"
        		::= { vturAPWlanStatusMacFilterEntry 1 }

		        vturWlanMacFltAction OBJECT-TYPE
        		SYNTAX  INTEGER
        		MAX-ACCESS  read-only
        		STATUS  current
        		DESCRIPTION
                      		"0: allow association for station which matches the address which is defined in MacFltAddr1~MacFltAddr8.
                      		 1: deny association for station which matches the address which is defined in MacFltAddr1~MacFltAddr8."
        		::= { vturAPWlanStatusMacFilterEntry 2 }


-- vturAPWlanStatusMacFltAddrTable

        vturAPWlanStatusMacFltAddrTable  OBJECT-TYPE
        SYNTAX	SEQUENCE OF VturAPWlanStatusMacFltAddrEntry
        MAX-ACCESS  not-accessible
        STATUS  current
        DESCRIPTION
                 	""
        ::= { vturAPWlanStatusMacFilter 2 }

		vturAPWlanStatusMacFltAddrEntry OBJECT-TYPE
       		SYNTAX	VturAPWlanStatusMacFltAddrEntry
       		MAX-ACCESS	not-accessible
       		STATUS	current
	       	DESCRIPTION    	"An entry in VTUR AP Wlan Security Table."
	       	INDEX          	{ dot1dBasePort, fltStaIndex }
	       	::= { vturAPWlanStatusMacFltAddrTable 1 }
	       	
		VturAPWlanStatusMacFltAddrEntry ::=
	       	SEQUENCE {
	        vturWlanFltStaIndex	INTEGER,
	        vturWlanMacFltAddr	MacAddress
	        }

		        vturWlanFltStaIndex  OBJECT-TYPE
        		SYNTAX  INTEGER
        		MAX-ACCESS  read-only
        		STATUS  current
        		DESCRIPTION
                      		"The index for Mac filter"
        		::= { vturAPWlanStatusMacFltAddrEntry 1 }

		        vturWlanMacFltAddr  OBJECT-TYPE
        		SYNTAX  MacAddress
        		MAX-ACCESS  read-only
        		STATUS  current
        		DESCRIPTION
                      		"The address for Mac filter"
        		::= { vturAPWlanStatusMacFltAddrEntry 2 }


-- vturAPWlanStatusStatisticsTable

	
	vturAPWlanStatusStatisticsTable  OBJECT-TYPE
        SYNTAX	SEQUENCE OF VturAPWlanStatusStatisticsEntry
        MAX-ACCESS  not-accessible
        STATUS  current
        DESCRIPTION
                 	""
        ::= { vturAPWlanStatus 5 }

		vturAPWlanStatusStatisticsEntry OBJECT-TYPE
       		SYNTAX	VturAPWlanStatusStatisticsEntry
       		MAX-ACCESS	not-accessible
       		STATUS	current
	       	DESCRIPTION    	"An entry in VTUR AP Wlan Security Table."
	       	INDEX          	{ dot1dBasePort }
	       	::= { vturAPWlanStatusStatisticsTable 1 }

		VturAPWlanStatusStatisticsEntry ::=
	       	SEQUENCE {
		        vturWlanInPkts		INTEGER,
		        vturWlanInOctets	INTEGER,
		        vturWlanInUCasts	INTEGER,
		        vturWlanInMCasts	INTEGER,
		        vturWlanRxFCSErrors	INTEGER,
		        vturWlanOutPkts		INTEGER,
		        vturWlanOutOctets	INTEGER,
		        vturWlanOutUCasts	INTEGER,
		        vturWlanOutMCasts	INTEGER
	        }

		        vturWlanInPkts  OBJECT-TYPE
        		SYNTAX  INTEGER
        		MAX-ACCESS  read-only
        		STATUS  current
        		DESCRIPTION
                      		"Same as WLANRxPkts in vturAPGeneral.vturAPGeneralStatistics MIB "
        		::= { vturAPWlanStatusStatisticsEntry 1 }

		        vturWlanInOctets  OBJECT-TYPE
        		SYNTAX  INTEGER
        		MAX-ACCESS  read-only
        		STATUS  current
        		DESCRIPTION
                      		"Same as WLANRxBytes in vturAPGeneral.vturAPGeneralStatistics MIB "
        		::= { vturAPWlanStatusStatisticsEntry 2 }

		        vturWlanInUCasts  OBJECT-TYPE
        		SYNTAX  INTEGER
        		MAX-ACCESS  read-only
        		STATUS  current
        		DESCRIPTION
                      		"Received unicast frames"
        		::= { vturAPWlanStatusStatisticsEntry 3 }

		        vturWlanInMCasts  OBJECT-TYPE
        		SYNTAX  INTEGER
        		MAX-ACCESS  read-only
        		STATUS  current
        		DESCRIPTION
                      		"Received multicast frames"
        		::= { vturAPWlanStatusStatisticsEntry 4 }

		        vturWlanRxFCSErrors  OBJECT-TYPE
        		SYNTAX  INTEGER
        		MAX-ACCESS  read-only
        		STATUS  current
        		DESCRIPTION
                      		"Same as WLANRxErrs in vturAPGeneral.vturAPGeneralStatistics MIB"
        		::= { vturAPWlanStatusStatisticsEntry 5 }

		        vturWlanOutPkts  OBJECT-TYPE
        		SYNTAX  INTEGER
        		MAX-ACCESS  read-only
        		STATUS  current
        		DESCRIPTION
                      		"Same as WLANTxPkts in vturAPGeneral.vturAPGeneralStatistics MIB"
        		::= { vturAPWlanStatusStatisticsEntry 6 }

		        vturWlanOutOctets  OBJECT-TYPE
        		SYNTAX  INTEGER
        		MAX-ACCESS  read-only
        		STATUS  current
        		DESCRIPTION
                      		"Same as WLANTxBytes in vturAPGeneral.vturAPGeneralStatistics MIB"
        		::= { vturAPWlanStatusStatisticsEntry 7 }

		        vturWlanOutUCasts  OBJECT-TYPE
        		SYNTAX  INTEGER
        		MAX-ACCESS  read-only
        		STATUS  current
        		DESCRIPTION
                      		"Transmitted unicast frames"
        		::= { vturAPWlanStatusStatisticsEntry 8 }

		        vturWlanOutMCasts  OBJECT-TYPE
        		SYNTAX  INTEGER
        		MAX-ACCESS  read-only
        		STATUS  current
        		DESCRIPTION
                      		"Transmitted multicast frames"
        		::= { vturAPWlanStatusStatisticsEntry 9 }


-- vturAPWlanStatusStaListTable


	vturAPWlanStatusStaListTable  OBJECT-TYPE
        SYNTAX	SEQUENCE OF VturAPWlanStatusStaListEntry
        MAX-ACCESS  not-accessible
        STATUS  current
        DESCRIPTION
                 	""
        ::= { vturAPWlanStatus 6 }

		vturAPWlanStatusStaListEntry OBJECT-TYPE
       		SYNTAX	VturAPWlanStatusStaListEntry
       		MAX-ACCESS	not-accessible
       		STATUS	current
	       	DESCRIPTION    	"An entry in VTUR AP Wlan Security Table."
	       	INDEX          	{ dot1dBasePort, staIndex }
	       	::= { vturAPWlanStatusStaListTable 1 }

		VturAPWlanStatusStaListEntry ::=
	       	SEQUENCE {
	        vturWlanStaIndex	INTEGER,
	        vturWlanStaMacAddr	MacAddress
	        }

		        vturWlanStaIndex  OBJECT-TYPE
        		SYNTAX  INTEGER
        		MAX-ACCESS  read-only
        		STATUS  current
        		DESCRIPTION
                      		"The index of associated WLAN STA. Max = 32, Min = 1"
        		::= { vturAPWlanStatusStaListEntry 1 }
        	
		        vturWlanStaMacAddr  OBJECT-TYPE
        		SYNTAX  MacAddress
        		MAX-ACCESS  read-only
        		STATUS  current
        		DESCRIPTION
                      		"The address of associated WLAN STA "
        		::= { vturAPWlanStatusStaListEntry 2 }


-- vturConsoleStatus
		vturConsoleStatus     	OBJECT IDENTIFIER ::= { vturSwitchStatus 8 }

		vturConsoleStatusTable OBJECT-TYPE
       	SYNTAX	SEQUENCE OF VturConsoleStatusEntry
       	MAX-ACCESS  not-accessible
       	STATUS  current
       	DESCRIPTION
      	      	""
       	::= { vturConsoleStatus 1 }

	vturConsoleStatusEntry OBJECT-TYPE
       	SYNTAX	VturConsoleStatusEntry
       	MAX-ACCESS	not-accessible
       	STATUS	current
       	DESCRIPTION    	"An entry in vturConsoleTable."
       	INDEX          	{ dot1dBasePort}
       	::= { vturConsoleStatusTable 1 }

        VturConsoleStatusEntry ::=
       	SEQUENCE {
       	vturConsoleStatusState			INTEGER,
       	vturConsoleStatusAdminPassword	OCTET STRING,
       	vturConsoleStatusUserPassword		OCTET STRING
        }


        vturConsoleStatusState OBJECT-TYPE
        SYNTAX  INTEGER {
         		enable(1),
         		disable(2)
        }
        MAX-ACCESS  read-only
        STATUS  current
        DESCRIPTION
                      "Display the current Console status
                       1: Enable console
                       2: Disable console"
        ::= { vturConsoleStatusEntry 1 }

	vturConsoleStatusAdminPassword OBJECT-TYPE
		SYNTAX  OCTET STRING
		MAX-ACCESS  read-only
		STATUS  current
		DESCRIPTION
			"The operation for vtur device admin password"
		::= { vturConsoleStatusEntry 2 }
		
	vturConsoleStatusUserPassword OBJECT-TYPE
		SYNTAX  OCTET STRING
		MAX-ACCESS  read-only
		STATUS  current
		DESCRIPTION
			"The operation for vtur device user password"
		::= { vturConsoleStatusEntry 3 }		

-- vturRemoteFunctionStatus
	vturRemoteFunctionStatus     	OBJECT IDENTIFIER ::= { vturSwitchStatus 9 }

	remoteFunctionStatusTable OBJECT-TYPE
       	SYNTAX	SEQUENCE OF RemoteFunctionStatusEntry
       	MAX-ACCESS  not-accessible
       	STATUS  current
       	DESCRIPTION
      	      	""
       	::= { vturRemoteFunctionStatus 1 }

	remoteFunctionStatusEntry OBJECT-TYPE
       	SYNTAX	RemoteFunctionStatusEntry
       	MAX-ACCESS	not-accessible
       	STATUS	current
       	DESCRIPTION    	"An entry in RemoteFunctionTable."
       	INDEX          	{ dot1dBasePort}
       	::= { remoteFunctionStatusTable 1 }

        RemoteFunctionStatusEntry ::=
       	SEQUENCE {
	       	telnetStatus  INTEGER,
	       	tftpStatus    INTEGER,
	       	webStatus     INTEGER,
	       	snmpStatus    INTEGER,
	       	sshStatus     INTEGER,
	       	wirelessStatus INTEGER
        }


        telnetStatus OBJECT-TYPE
        SYNTAX  INTEGER {
         		enable_all(1),
         		disable_all(2),
         		enable_lan_only(3),
         		enable_wan_only(4)
        }
        MAX-ACCESS  read-only
        STATUS  current
        DESCRIPTION
                      "Display the current Telnet status
                       1: Enable All
                       2: Disable All
                       3: Enable LAN only
                       4: Enable WAN only"
        ::= { remoteFunctionStatusEntry 3 }

        tftpStatus OBJECT-TYPE
        SYNTAX  INTEGER {
         		enable_all(1),
         		disable_all(2),
         		enable_lan_only(3),
         		enable_wan_only(4)
        }
        MAX-ACCESS  read-only
        STATUS  current
        DESCRIPTION
                      "Display the current TFTP status
                       1: Enable All
                       2: Disable All
                       3: Enable LAN only
                       4: Enable WAN only"
        ::= { remoteFunctionStatusEntry 4 }

        webStatus OBJECT-TYPE
        SYNTAX  INTEGER {
         		enable_all(1),
         		disable_all(2),
         		enable_lan_only(3),
         		enable_wan_only(4)
        }
        MAX-ACCESS  read-only
        STATUS  current
        DESCRIPTION
                      "Display the current Web status
                       1: Enable All
                       2: Disable All
                       3: Enable LAN only
                       4: Enable WAN only"
        ::= { remoteFunctionStatusEntry 5 }

        snmpStatus OBJECT-TYPE
        SYNTAX  INTEGER {
         		enable_all(1),
         		disable_all(2),
         		enable_lan_only(3),
         		enable_wan_only(4)
        }
        MAX-ACCESS  read-only
        STATUS  current
        DESCRIPTION
                      "Display the current SNMP status
                       1: Enable All
                       2: Disable All
                       3: Enable LAN only
                       4: Enable WAN only"
        ::= { remoteFunctionStatusEntry 6 }

        sshStatus OBJECT-TYPE
        SYNTAX  INTEGER {
           		enable_all(1),
         		disable_all(2),
         		enable_lan_only(3),
         		enable_wan_only(4)
        }
        MAX-ACCESS  read-only
        STATUS  current
        DESCRIPTION
                      "Display the current SSH status
                       1: Enable All
                       2: Disable All
                       3: Enable LAN only
                       4: Enable WAN only"
        ::= { remoteFunctionStatusEntry 7 }

        wirelessStatus OBJECT-TYPE
        SYNTAX  INTEGER {
           		disable(1),
         		enable(2)
        }
        MAX-ACCESS  read-only
        STATUS  current
        DESCRIPTION
                      "Display the current Wireless status
                       1: Disable
                       2: Enable"
        ::= { remoteFunctionStatusEntry 8 }
---------------------------------------------------------------------------
---------------------------------------------------------------------------
-- vturMacAddr
	vturMacAddrStatus     	OBJECT IDENTIFIER ::= { vturSwitchStatus 10 }

		vturMacAddrTable OBJECT-TYPE
       	SYNTAX	SEQUENCE OF VturMacAddrEntry
       	MAX-ACCESS  not-accessible
       	STATUS  current
       	DESCRIPTION
      	      	""
       	::= { vturMacAddrStatus 1 }

		vturMacAddrEntry OBJECT-TYPE
       	SYNTAX	VturMacAddrEntry
       	MAX-ACCESS	not-accessible
       	STATUS	current
       	DESCRIPTION    	"An entry in vturMacAddrTable."
       	INDEX          	{ dot1dBasePort, vturMacAddrIndex}
       	::= { vturMacAddrTable 1 }


		VturMacAddrEntry ::=
       	SEQUENCE {
        	vturMacAddrIndex	INTEGER,
        	vturMacAddress	MacAddress,
        	vturInterface	DisplayString
        }

	        vturMacAddrIndex  OBJECT-TYPE
       		SYNTAX  INTEGER
       		MAX-ACCESS  read-only
       		STATUS  current
       		DESCRIPTION
			"The index of associated vtur STA. Max = 32, Min = 1"
        		::= { vturMacAddrEntry 1 }
        	
	        vturMacAddress  OBJECT-TYPE
       		SYNTAX  MacAddress
       		MAX-ACCESS  read-only
       		STATUS  current
       		DESCRIPTION
			"The address of associated vtur STA "
        		::= { vturMacAddrEntry 2 }

        	vturInterface OBJECT-TYPE
        	SYNTAX  DisplayString
	        MAX-ACCESS  read-only
    	    STATUS  current
        	DESCRIPTION
            "The interface of the mac address"
        		::= { vturMacAddrEntry 3 }


-- vturLanStatus
	vturLanStatus     	OBJECT IDENTIFIER ::= { vturSwitchStatus 11 }

	vturLanStatusTable OBJECT-TYPE
       	SYNTAX	SEQUENCE OF VturLanStatusEntry
       	MAX-ACCESS  not-accessible
       	STATUS  current
       	DESCRIPTION
      	      	""
       	::= { vturLanStatus 1 }

	vturLanStatusEntry OBJECT-TYPE
       	SYNTAX	VturLanStatusEntry
       	MAX-ACCESS	not-accessible
       	STATUS	current
       	DESCRIPTION    	"An entry in vturLanTable."
       	INDEX          	{ dot1dBasePort }
       	::= { vturLanStatusTable 1 }

        VturLanStatusEntry ::=
       	SEQUENCE {
	       	vturLanStatusIP  IpAddress,
	       	vturLanStatusSubnetmask    IpAddress,
	       	vturLanStatusDHCPOption     INTEGER,
	       	vturLanStatusDHCPServerStartIPAddr    IpAddress,
	       	vturLanStatusDHCPServerEndIPAddr     IpAddress,
	       	vturLanStatusDHCPServerSubnetmask    IpAddress,
	       	vturLanStatusDHCPServerIPAddr    IpAddress,
	       	vturLanStatusEthPort	INTEGER,
	       	vturLanStatusEthPortIsolate	INTEGER
	    }


        vturLanStatusIP OBJECT-TYPE
        SYNTAX  IpAddress
        MAX-ACCESS  read-only
        STATUS  current
        DESCRIPTION
                      ""
        ::= { vturLanStatusEntry 1 }

        vturLanStatusSubnetmask OBJECT-TYPE
        SYNTAX  IpAddress
        MAX-ACCESS  read-only
        STATUS  current
        DESCRIPTION
                      ""
        ::= { vturLanStatusEntry 2 }

        vturLanStatusDHCPOption OBJECT-TYPE
        SYNTAX  INTEGER{
			disable_dhcp_server(1),
         	enable_dhcp_server(2),
         	dhcp_server_relay(3)
         	}
        MAX-ACCESS  read-only
        STATUS  current
        DESCRIPTION
                      ""
        ::= { vturLanStatusEntry 3 }

        vturLanStatusDHCPServerStartIPAddr OBJECT-TYPE
        SYNTAX  IpAddress 
        MAX-ACCESS  read-only
        STATUS  current
        DESCRIPTION
                      ""
        ::= { vturLanStatusEntry 4 }

        vturLanStatusDHCPServerEndIPAddr OBJECT-TYPE
        SYNTAX  IpAddress 
        MAX-ACCESS  read-only
        STATUS  current
        DESCRIPTION
                      ""
        ::= { vturLanStatusEntry 5 }
        
        vturLanStatusDHCPServerSubnetmask OBJECT-TYPE
        SYNTAX  IpAddress 
        MAX-ACCESS  read-only
        STATUS  current
        DESCRIPTION
                      ""
        ::= { vturLanStatusEntry 6 }

        vturLanStatusDHCPServerIPAddr OBJECT-TYPE
        SYNTAX  IpAddress 
        MAX-ACCESS  read-only
        STATUS  current
        DESCRIPTION
                      ""
        ::= { vturLanStatusEntry 7 }        
        
        vturLanStatusEthPort OBJECT-TYPE
        SYNTAX	INTEGER
        MAX-ACCESS	read-only
        STATUS	current
        DESCRIPTION
        		"Display the current vtur LAN port to be isolated. From LAN1 to LAN4."
        ::= { vturLanStatusEntry 8 }
        
        vturLanStatusEthPortIsolate OBJECT-TYPE
        SYNTAX	INTEGER {
        	enable(1),
        	disable(2)
        }
        MAX-ACCESS	read-only
        STATUS	current
        DESCRIPTION
        			  "Display the current vtur LAN port isolated-enable or isolated-disable."
        ::= { vturLanStatusEntry 9 }

-----------------------------------------------------------------------------------------------
-- vturCFMStatus
	vturCFMStatus     	OBJECT IDENTIFIER ::= { vturSwitchStatus 12 }

	vturCFMStatusTable OBJECT-TYPE
       	SYNTAX	SEQUENCE OF VturCFMStatusEntry
       	MAX-ACCESS  not-accessible
       	STATUS  current
       	DESCRIPTION
      	      	""
       	::= { vturCFMStatus 1 }

	vturCFMStatusEntry OBJECT-TYPE
       	SYNTAX	VturCFMStatusEntry
       	MAX-ACCESS	not-accessible
       	STATUS	current
       	DESCRIPTION    	"An entry in vturCFMTable."
       	INDEX          	{ dot1dBasePort }
       	::= { vturCFMStatusTable 1 }

        VturCFMStatusEntry ::=
       	SEQUENCE {
	       	vturCFMStatusMdName  OCTET STRING,
	       	vturCFMStatusMaName    OCTET STRING,
	       	vturCFMStatusVid     INTEGER,
	       	vturCFMStatusMepId    Dot1agCfmMepId,
	       	vturCFMStatusMdLevel     INTEGER,
--	       	vturCFMAction    INTEGER,
	       	vturCFMStatusDestMAC    OCTET STRING,
	       	vturCFMStatusLBMCount   INTEGER,
	       	vturCFMStatusResultSentLBM     INTEGER,
	       	vturCFMStatusResultInorderLBM     INTEGER,
			vturCFMStatusResultOutorderLBM     INTEGER,
			vturCFMStatusMACAddr		OCTET STRING
        }

--        vturCFMCommit OBJECT-TYPE
--        SYNTAX  INTEGER
--        {
--		commit(1)
--        }
--        MAX-ACCESS  read-write
--        STATUS  current
--        DESCRIPTION
--                      "Set 1 to commit CFM operation and read value always return 0"
--        ::= { vturCFMEntry 1 }

        vturCFMStatusMdName OBJECT-TYPE
        SYNTAX  OCTET STRING
        MAX-ACCESS  read-only
        STATUS  current
        DESCRIPTION
                      ""
        ::= { vturCFMStatusEntry 2 }

        vturCFMStatusMaName OBJECT-TYPE
        SYNTAX  OCTET STRING
        MAX-ACCESS  read-only
        STATUS  current
        DESCRIPTION
                      ""
        ::= { vturCFMStatusEntry 3 }

        vturCFMStatusVid OBJECT-TYPE
        SYNTAX  INTEGER
        MAX-ACCESS  read-only
        STATUS  current
        DESCRIPTION
                      ""
        ::= { vturCFMStatusEntry 4 }

        vturCFMStatusMepId OBJECT-TYPE
        SYNTAX  Dot1agCfmMepId 
        MAX-ACCESS  read-only
        STATUS  current
        DESCRIPTION
                      ""
        ::= { vturCFMStatusEntry 5 }

        vturCFMStatusMdLevel OBJECT-TYPE
        SYNTAX  INTEGER 
        MAX-ACCESS  read-only
        STATUS  current
        DESCRIPTION
                      ""
        ::= { vturCFMStatusEntry 6 }
        
--        vturCFMAction OBJECT-TYPE
--        SYNTAX  INTEGER
--    	{
--		 	save(0),    	
--	        enable_cfm(1),
--	        disable_cfm(2),
--	        send_loopback_message(3),
--	        send_linktrace_message(4),
--	         reset_configuration(5)
--	    }        
--        MAX-ACCESS  read-write
--        STATUS  current
--        DESCRIPTION
--                      "Currently only support 0:save ,3:send loopback message and 5:load cpe cfm default"
--        ::= { vturCFMEntry 7 }

        vturCFMStatusDestMAC OBJECT-TYPE
        SYNTAX  OCTET STRING 
        MAX-ACCESS  read-only
        STATUS  current
        DESCRIPTION
                      ""
        ::= { vturCFMStatusEntry 8 }    

        vturCFMStatusLBMCount OBJECT-TYPE
        SYNTAX  INTEGER 
        MAX-ACCESS  read-only
        STATUS  current
        DESCRIPTION
                      ""
        ::= { vturCFMStatusEntry 9 }            

        vturCFMStatusResultSentLBM OBJECT-TYPE
        SYNTAX  INTEGER 
        MAX-ACCESS  read-only
        STATUS  current
        DESCRIPTION
                      ""
        ::= { vturCFMStatusEntry 10 }            

        vturCFMStatusResultInorderLBM OBJECT-TYPE
        SYNTAX  INTEGER 
        MAX-ACCESS  read-only
        STATUS  current
        DESCRIPTION
                      ""
        ::= { vturCFMStatusEntry 11 }            

        vturCFMStatusResultOutorderLBM OBJECT-TYPE
        SYNTAX  INTEGER 
        MAX-ACCESS  read-only
        STATUS  current
        DESCRIPTION
                      ""
        ::= { vturCFMStatusEntry 12 }  
        
        vturCFMStatusMACAddr OBJECT-TYPE
        SYNTAX  OCTET STRING 
        MAX-ACCESS  read-only
        STATUS  current
        DESCRIPTION
                      "CPE MAC address"
        ::= { vturCFMStatusEntry 13 }             
        
--        vturCFMReadStatus OBJECT-TYPE
--        SYNTAX  INTEGER
--        {
--       	commit(1)
--        }
--        MAX-ACCESS  read-write
--        STATUS  current
--        DESCRIPTION
--                      "Set 1 to commit CFM Read operation and read value always return 0"
--        ::= { vturCFMEntry 14 }               
------------------------------------------------------------------------------------------------

-- PPPoE Intermediate Agent (PPPoEIA)

--  pppoeIASetup

	pppoeIASetup     	OBJECT IDENTIFIER ::= { ves1724-56fanless 119 }

        globalPPPoEIA OBJECT IDENTIFIER ::= { pppoeIASetup 1 }

        globalPPPoEIAEnable OBJECT-TYPE
        SYNTAX  EnabledStatus
        MAX-ACCESS  read-write
        STATUS  current
        DESCRIPTION
                      	"To enable the global PPPoE IA. Once the configuration is enabled, the
                      	DSLAM will automatically generate the Agent Circuit ID field in PPPoE packet 
                      	for identifying access loop logical ports as: slot number,portnumber and VLAN ID."
        ::= { globalPPPoEIA 1 }
        
 --- PPPoE IA circuit id field       

        globalPPPoEIACircuitIDInfoEnable OBJECT-TYPE
        SYNTAX  EnabledStatus
        MAX-ACCESS  read-write
        STATUS  current
        DESCRIPTION
                      	"To enable extra information to be appended into Agnet Circuit ID filed."
        ::= { globalPPPoEIA 2 }

        globalPPPoEIACircuitIDInfoData OBJECT-TYPE
        SYNTAX  DisplayString
        MAX-ACCESS  read-write
        STATUS  current
        DESCRIPTION
                      	""
        ::= { globalPPPoEIA 3 }


--- PPPoE IA remote id field
        globalPPPoEIARemoteIDEnable OBJECT-TYPE
        SYNTAX  EnabledStatus
        MAX-ACCESS  read-write
        STATUS  current
        DESCRIPTION
                      	""
        ::= { globalPPPoEIA 4 }

        globalPPPoEIARemoteIDData OBJECT-TYPE
        SYNTAX  DisplayString
        MAX-ACCESS  read-write
        STATUS  current
        DESCRIPTION
                      	""
        ::= { globalPPPoEIA 5 }

        globalPPPoEIARemoteIDType OBJECT-TYPE
        SYNTAX  INTEGER {
        	port(1),
        	system(2),
			all(3)
        }
        MAX-ACCESS  read-write
        STATUS  current
        DESCRIPTION
                      	"<1:port|2:system>"
        ::= { globalPPPoEIA 6 }

 --- PPPoE IA circuit id field for appending CID-type with host name or system  
		globalPPPoEIACircuitIDType OBJECT-TYPE
        SYNTAX  INTEGER {
        	hostname(1),
        	system(2)
        }
        MAX-ACCESS  read-write
        STATUS  current
        DESCRIPTION
                      	"<1:hostname|2:system>"
        ::= { globalPPPoEIA 7 }
                        
 		globalPPPoEIAOption OBJECT-TYPE
        SYNTAX  INTEGER   
        {        
        	private(0),
 			sp(1),
			sv(2),
     		pv(3),
      		spv(4)
        }
        MAX-ACCESS  read-write
        STATUS  current
        DESCRIPTION
        	"Tag option setting for global PPPoE IA. private(0), SP(1), SV(2), PV(3), SPV(4)."
        ::= { globalPPPoEIA 8 }        
        globalPPPoEIADelim OBJECT-TYPE
        SYNTAX  INTEGER   
        {            
        	none(0),
      		pound(1),
 			semicolon(2),
			dot(3),
     		comma(4),
     		slash(5),
     		space(6)
        }
        MAX-ACCESS  read-write
        STATUS  current
        DESCRIPTION
        	"Delimiter setting for global PPPoE IA. none(0), pound[#](1), semicolon[;](2), dot[.](3), comma[,](4), slash[/](5), space[ ](6)."
        ::= { globalPPPoEIA 9 }
        
        globalPPPoEIARemoteIDDelim OBJECT-TYPE
        SYNTAX  DisplayString
        MAX-ACCESS  read-write
        STATUS  current
        DESCRIPTION
                      	""
        ::= { globalPPPoEIA 10 }
 -- end ab4daa                         
--- PPPoE IA Setup by VLAN

	pppoeIA OBJECT IDENTIFIER ::= { pppoeIASetup 2 }

	maxNumberOfPPPoEIA OBJECT-TYPE
        SYNTAX  INTEGER
        MAX-ACCESS  read-only
        STATUS  current
        DESCRIPTION
                      	"The maximum number of PPPoE IA (by VLAN) entries that can be created. 
                      	A value of 0 for this object implies that there exists settings for 
                      	global PPPoE IA."
        ::= { pppoeIA 1 }
        
 
 -- pppoeIATable (by VLAN)
        
        pppoeIATable OBJECT-TYPE
        SYNTAX	SEQUENCE OF PPPoEIAEntry
        MAX-ACCESS  not-accessible
        STATUS  current
        DESCRIPTION
                 	""
        ::= { pppoeIA 2 }  	


	pppoeIAEntry OBJECT-TYPE
        SYNTAX	PPPoEIAEntry
        MAX-ACCESS	not-accessible
        STATUS	current
        DESCRIPTION    	"An entry in pppoeIATable."
        INDEX          	{ pppoeIAVID}
        ::= { pppoeIATable 1 }

        PPPoEIAEntry ::=
           SEQUENCE {
           	pppoeIAVID			INTEGER,
        	pppoeIACircuitIDInfoEnable      EnabledStatus,
        	pppoeIACircuitIDInfoData   	DisplayString,
        	pppoeIARemoteIDEnable   	EnabledStatus,
        	pppoeIARemoteIDData     	DisplayString,
        	pppoeIARowStatus		RowStatus,
        	pppoeIARemoteIDType   INTEGER,
        	pppoeIACircuitIDType   INTEGER,
					pppoeIAOption		   INTEGER,
			pppoeIADelim		   INTEGER,
					pppoeIARemoteIDDelim	DisplayString
           }
        
        pppoeIAVID OBJECT-TYPE
        SYNTAX  INTEGER
        MAX-ACCESS  read-only
        STATUS  current
        DESCRIPTION
                      	""
        ::= { pppoeIAEntry 1 }
           
-- pppoeIA circuit ID field

        pppoeIACircuitIDInfoEnable OBJECT-TYPE
        SYNTAX  EnabledStatus
        MAX-ACCESS  read-write
        STATUS  current
        DESCRIPTION
                      	""
        ::= { pppoeIAEntry 2 }

        pppoeIACircuitIDInfoData OBJECT-TYPE
        SYNTAX  DisplayString
        MAX-ACCESS  read-write
        STATUS  current
        DESCRIPTION
                      	""
        ::= { pppoeIAEntry 3 }   

--- pppoeIA remote id field

        pppoeIARemoteIDEnable OBJECT-TYPE
        SYNTAX  EnabledStatus
        MAX-ACCESS  read-write
        STATUS  current
        DESCRIPTION
                      	""
        ::= { pppoeIAEntry 4 }

        pppoeIARemoteIDData OBJECT-TYPE
        SYNTAX  DisplayString
        MAX-ACCESS  read-write
        STATUS  current
        DESCRIPTION
                      	""
        ::= { pppoeIAEntry 5 }
        
        pppoeIARowStatus OBJECT-TYPE
        SYNTAX  RowStatus
        MAX-ACCESS  read-create
        STATUS  current
        DESCRIPTION
                     	""
        ::= { pppoeIAEntry 6 }
 
         pppoeIARemoteIDType OBJECT-TYPE
        SYNTAX  INTEGER{
       		port(1),
        	system(2),
			all(3)
        }
        MAX-ACCESS  read-write
        STATUS  current
        DESCRIPTION
                      	"<1:port | 2:system>"
        ::= { pppoeIAEntry 7 }

--- PPPoE IA circuit id field for appending CID-type with host name or system 
		pppoeIACircuitIDType OBJECT-TYPE
        SYNTAX  INTEGER{
       		hostname(1),
        	system(2) 	
        }
        MAX-ACCESS  read-write
        STATUS  current
        DESCRIPTION
                      	"<1:hostname | 2:system>"
        ::= { pppoeIAEntry 8 }
        
 		pppoeIAOption OBJECT-TYPE
        SYNTAX  INTEGER   
        {     
        	private(0),
 			sp(1),
			sv(2),
     		pv(3),
      		spv(4)
        }
        MAX-ACCESS  read-write
        STATUS  current
        DESCRIPTION
        	"Tag option setting for global PPPoE IA. private(0), SP(1), SV(2), PV(3), SPV(4)."
        ::= { pppoeIAEntry 9 }        
        
        pppoeIADelim OBJECT-TYPE
        SYNTAX  INTEGER   
        {
        	none(0),
      		pound(1),
 			semicolon(2),
			dot(3),
     		comma(4),
     		slash(5),
     		space(6)
        }
        MAX-ACCESS  read-write
        STATUS  current
        DESCRIPTION
        	"Delimiter setting for global PPPoE IA. none(0), pound[#](1), semicolon[;](2), dot[.](3), comma[,](4), slash[/](5), space[ ](6)."
        ::= { pppoeIAEntry 10 }
        
        pppoeIARemoteIDDelim OBJECT-TYPE
        SYNTAX  DisplayString
        MAX-ACCESS  read-write
        STATUS  current
        DESCRIPTION
                      	""
        ::= { pppoeIAEntry 11 }
 -- end ab4daa 
        
-- macFlush
	macFlush     	OBJECT IDENTIFIER ::= { ves1724-56fanless 122 }

 	macFlushTable OBJECT-TYPE
       	SYNTAX	SEQUENCE OF MacFlushEntry
       	MAX-ACCESS  not-accessible
       	STATUS  current
       	DESCRIPTION
      	      	""
       	::= { macFlush 1 }

	macFlushEntry OBJECT-TYPE
       	SYNTAX	MacFlushEntry
       	MAX-ACCESS	not-accessible
       	STATUS	current
       	DESCRIPTION    	"An entry in macFlushTable."
       	INDEX          	{ macFlushPortIndex }
       	::= { macFlushTable 1 }

        MacFlushEntry ::=
       	SEQUENCE {
       		macFlushPortIndex	INTEGER,
	       	macFlushPortConfig  INTEGER
        } 
        
        macFlushPortIndex OBJECT-TYPE
        SYNTAX  INTEGER
        MAX-ACCESS  read-only
        STATUS  current
        DESCRIPTION
                      	""
        ::= { macFlushEntry 1 }

        macFlushPortConfig OBJECT-TYPE
        SYNTAX  INTEGER 
        MAX-ACCESS  read-write
        STATUS  current
        DESCRIPTION
                   		"Set 1 to execute mac flush operation in the specified port, read value will always return 0"
        ::= { macFlushEntry 2 }

---------------------------------------------------
--
--  ADSL Fallback
--
---------------------------------------------------

-- iwfSetup
	iwfSetup     	OBJECT IDENTIFIER ::= { ves1724-56fanless 120 }
                               
-- pvcRuleTable
        pvcRuleTable OBJECT-TYPE
        SYNTAX	SEQUENCE OF PvcRuleEntry
        MAX-ACCESS  not-accessible
        STATUS  current
        DESCRIPTION
                 	""
        ::= { iwfSetup 1 }
        
	pvcRuleEntry OBJECT-TYPE
        SYNTAX	PvcRuleEntry
        MAX-ACCESS	not-accessible
        STATUS	current
        DESCRIPTION    	"An entry in PVC rule table"
        INDEX          	{ pvcRulePort, pvcRuleVpi, pvcRuleVci }
        ::= { pvcRuleTable 1 }

        PvcRuleEntry ::=
           SEQUENCE {
	        pvcRulePort			INTEGER,
  	      	pvcRuleVpi			INTEGER,
    	    pvcRuleVci			INTEGER,
      	  	pvcRulePvid			INTEGER,
      	  	pvcRuleEncap		INTEGER,
      	  	pvcRulePriority		INTEGER,
      	  	pvcRuleFCS			INTEGER,
        	pvcRuleMVlan		EnabledStatus,
        	pvcRuleRowStatus	RowStatus
           }

        pvcRulePort OBJECT-TYPE
        SYNTAX  INTEGER
        MAX-ACCESS  read-only
        STATUS  current
        DESCRIPTION
                     	"interface port id"
        ::= { pvcRuleEntry 1 }

        pvcRuleVpi OBJECT-TYPE
        SYNTAX  INTEGER
        MAX-ACCESS  read-only
        STATUS  current
        DESCRIPTION
                     	"VPI"
        ::= { pvcRuleEntry 2 }

        pvcRuleVci OBJECT-TYPE
        SYNTAX  INTEGER
        MAX-ACCESS  read-only
        STATUS  current
        DESCRIPTION
                     	"VCI"
        ::= { pvcRuleEntry 3 }
        
        pvcRulePvid OBJECT-TYPE
        SYNTAX  INTEGER
        MAX-ACCESS  read-write
        STATUS  current
        DESCRIPTION
                     	"PVID"
        ::= { pvcRuleEntry 4 }

        pvcRuleEncap OBJECT-TYPE
        SYNTAX  INTEGER {
        		llc(0),
        		vc(1)
        }
        MAX-ACCESS  read-write
        STATUS  current
        DESCRIPTION
                     	"ATM encapulation method"
        ::= { pvcRuleEntry 5 }
        
        pvcRulePriority OBJECT-TYPE
        SYNTAX  INTEGER {
        		priority_0(0),
        		priority_1(1),
        		priority_2(2),
        		priority_3(3),
        		priority_4(4),
        		priority_5(5),
        		priority_6(6),
        		priority_7(7)
        }
        MAX-ACCESS  read-write
        STATUS  current
        DESCRIPTION
                     	"priority"
        ::= { pvcRuleEntry 6 }

        pvcRuleFCS OBJECT-TYPE
        SYNTAX  INTEGER {
        		fcs(0),
        		no_fcs(1)
        }
        MAX-ACCESS  read-write
        STATUS  current
        DESCRIPTION
                     	"Frame Check Sequence of PDU is preserved or not."
        ::= { pvcRuleEntry 7 }

		pvcRuleMVlan OBJECT-TYPE
        SYNTAX  EnabledStatus
        MAX-ACCESS  read-write
        STATUS  current
        DESCRIPTION
                     	"Multicast VLAN pass through."
        ::= { pvcRuleEntry 8 }
        
        pvcRuleRowStatus OBJECT-TYPE
        SYNTAX  RowStatus
        MAX-ACCESS  read-create
        STATUS  current
        DESCRIPTION
                     	""
        ::= { pvcRuleEntry 9 }

-- ippvcRuleTable
        ippvcRuleTable OBJECT-TYPE
        SYNTAX	SEQUENCE OF IpPvcRuleEntry
        MAX-ACCESS  not-accessible
        STATUS  current
        DESCRIPTION
                 	""
        ::= { iwfSetup 2 }
        
	ippvcRuleEntry OBJECT-TYPE
        SYNTAX	IpPvcRuleEntry
        MAX-ACCESS	not-accessible
        STATUS	current
        DESCRIPTION    	"An entry in IPPVC rule table"
        INDEX          	{ ippvcRulePort, ippvcRuleVpi, ippvcRuleVci }
        ::= { ippvcRuleTable 1 }

        IpPvcRuleEntry ::=
           SEQUENCE {
	        	ippvcRulePort					INTEGER,
  	      	ippvcRuleVpi					INTEGER,
    	    	ippvcRuleVci					INTEGER,
      	  	ippvcRulePvid					INTEGER,
      	  	ippvcRuleEncap				INTEGER,
      	  	ippvcRulePriority			INTEGER,
      	  	ippvcRuleSubnetIp			IpAddress,
      	  	ippvcRuleSubnetMask		IpAddress,
      	  	ippvcRuleDefaultRoute	IpAddress,
        		ippvcRuleRowStatus		RowStatus
           }

        ippvcRulePort OBJECT-TYPE
        SYNTAX  INTEGER
        MAX-ACCESS  read-only
        STATUS  current
        DESCRIPTION
                     	"interface port id"
        ::= { ippvcRuleEntry 1 }

        ippvcRuleVpi OBJECT-TYPE
        SYNTAX  INTEGER
        MAX-ACCESS  read-only
        STATUS  current
        DESCRIPTION
                     	"VPI"
        ::= { ippvcRuleEntry 2 }

        ippvcRuleVci OBJECT-TYPE
        SYNTAX  INTEGER
        MAX-ACCESS  read-only
        STATUS  current
        DESCRIPTION
                     	"VCI"
        ::= { ippvcRuleEntry 3 }
        
        ippvcRulePvid OBJECT-TYPE
        SYNTAX  INTEGER
        MAX-ACCESS  read-write
        STATUS  current
        DESCRIPTION
                     	"PVID"
        ::= { ippvcRuleEntry 4 }

        ippvcRuleEncap OBJECT-TYPE
        SYNTAX  INTEGER {
        		llc(0),
        		vc(1)
        }
        MAX-ACCESS  read-write
        STATUS  current
        DESCRIPTION
                     	"ATM encapulation method"
        ::= { ippvcRuleEntry 5 }
        
        ippvcRulePriority OBJECT-TYPE
        SYNTAX  INTEGER {
        		priority_0(0),
        		priority_1(1),
        		priority_2(2),
        		priority_3(3),
        		priority_4(4),
        		priority_5(5),
        		priority_6(6),
        		priority_7(7)
        }
        MAX-ACCESS  read-write
        STATUS  current
        DESCRIPTION
                     	"priority"
        ::= { ippvcRuleEntry 6 }

        ippvcRuleSubnetIp OBJECT-TYPE
        SYNTAX  IpAddress
        MAX-ACCESS  read-write
        STATUS  current
        DESCRIPTION
                     	"IP address of the subscriber intranet"
        ::= { ippvcRuleEntry 7 }

        ippvcRuleSubnetMask OBJECT-TYPE
        SYNTAX  IpAddress
        MAX-ACCESS  read-write
        STATUS  current
        DESCRIPTION
                     	"netmask of the subscriber intranet"
        ::= { ippvcRuleEntry 8 }

        ippvcRuleDefaultRoute OBJECT-TYPE
        SYNTAX  IpAddress
        MAX-ACCESS  read-write
        STATUS  current
        DESCRIPTION
                     	"default route for outgoing traffic"
        ::= { ippvcRuleEntry 9 }

        ippvcRuleRowStatus OBJECT-TYPE
        SYNTAX  RowStatus
        MAX-ACCESS  read-create
        STATUS  current
        DESCRIPTION
                     	""
        ::= { ippvcRuleEntry 10 }

-- paepvcRuleTable
        paepvcRuleTable OBJECT-TYPE
        SYNTAX	SEQUENCE OF PaePvcRuleEntry
        MAX-ACCESS  not-accessible
        STATUS  current
        DESCRIPTION
                 	""
        ::= { iwfSetup 3 }
        
	paepvcRuleEntry OBJECT-TYPE
        SYNTAX	PaePvcRuleEntry
        MAX-ACCESS	not-accessible
        STATUS	current
        DESCRIPTION    	"An entry in PAEPVC rule table"
        INDEX          	{ paepvcRulePort, paepvcRuleVpi, paepvcRuleVci }
        ::= { paepvcRuleTable 1 }

        PaePvcRuleEntry ::=
           SEQUENCE {
	        	paepvcRulePort			INTEGER,
  	      	paepvcRuleVpi				INTEGER,
    	    	paepvcRuleVci				INTEGER,
      	  	paepvcRulePvid			INTEGER,
      	  	paepvcRuleEncap			INTEGER,
      	  	paepvcRulePriority	INTEGER,
        		paepvcRuleRowStatus	RowStatus
           }

        paepvcRulePort OBJECT-TYPE
        SYNTAX  INTEGER
        MAX-ACCESS  read-only
        STATUS  current
        DESCRIPTION
                     	"interface port id"
        ::= { paepvcRuleEntry 1 }

        paepvcRuleVpi OBJECT-TYPE
        SYNTAX  INTEGER
        MAX-ACCESS  read-only
        STATUS  current
        DESCRIPTION
                     	"VPI"
        ::= { paepvcRuleEntry 2 }

        paepvcRuleVci OBJECT-TYPE
        SYNTAX  INTEGER
        MAX-ACCESS  read-only
        STATUS  current
        DESCRIPTION
                     	"VCI"
        ::= { paepvcRuleEntry 3 }
        
        paepvcRulePvid OBJECT-TYPE
        SYNTAX  INTEGER
        MAX-ACCESS  read-write
        STATUS  current
        DESCRIPTION
                     	"PVID"
        ::= { paepvcRuleEntry 4 }

        paepvcRuleEncap OBJECT-TYPE
        SYNTAX  INTEGER {
        		llc(0),
        		vc(1)
        }
        MAX-ACCESS  read-write
        STATUS  current
        DESCRIPTION
                     	"ATM encapulation method"
        ::= { paepvcRuleEntry 5 }
        
        paepvcRulePriority OBJECT-TYPE
        SYNTAX  INTEGER {
        		priority_0(0),
        		priority_1(1),
        		priority_2(2),
        		priority_3(3),
        		priority_4(4),
        		priority_5(5),
        		priority_6(6),
        		priority_7(7)
        }
        MAX-ACCESS  read-write
        STATUS  current
        DESCRIPTION
                     	"priority"
        ::= { paepvcRuleEntry 6 }

        paepvcRuleRowStatus OBJECT-TYPE
        SYNTAX  RowStatus
        MAX-ACCESS  read-create
        STATUS  current
        DESCRIPTION
                     	""
        ::= { paepvcRuleEntry 7 }

 
---------------------------------------------------
--
--  Bonding
--
---------------------------------------------------
	bonding                 OBJECT IDENTIFIER ::= { ves1724-56fanless 121 }
	bondingNotification     OBJECT IDENTIFIER ::= { bonding 0 }
	bondingSetup            OBJECT IDENTIFIER ::= { bonding 1 }
	bondingStatus           OBJECT IDENTIFIER ::= { bonding 2 }		


	xdslBondingLinkDown NOTIFICATION-TYPE
	OBJECTS
	{
		xdslBondingConfigGroupId
	}
	STATUS     current
	DESCRIPTION
		"This notification indicates that Bonding Group is link down."
	::= { bondingNotification 1 }

	xdslBondingLinkUp NOTIFICATION-TYPE
	OBJECTS
	{
		xdslBondingConfigGroupId
	}
	STATUS     current
	DESCRIPTION
		"This notification indicates that Bonding Group is link up."
	::= { bondingNotification 2 }


        xdslBondingConfigTable	OBJECT-TYPE
        SYNTAX	SEQUENCE OF XdslBondingConfigEntry
        MAX-ACCESS  not-accessible
        STATUS  current
        DESCRIPTION
                 	""
        ::= { bondingSetup 1 }

		xdslBondingConfigEntry OBJECT-TYPE
        SYNTAX	XdslBondingConfigEntry
        MAX-ACCESS	not-accessible
        STATUS	current
        DESCRIPTION    	"An entry in xdslBondingConfigTable."
        INDEX          	{xdslBondingConfigGroupId}
        ::= { xdslBondingConfigTable 1 }

      	XdslBondingConfigEntry ::=
		SEQUENCE {
			xdslBondingConfigGroupId		   		INTEGER,
        	xdslBondingConfigName		       	 	DisplayString,
        	xdslBondingConfigMemberPort 	    	PortList,
        	xdslBondingConfigTemplateMode   		INTEGER,
        	xdslBondingConfigTemplateFirstPort	   	DisplayString,
        	xdslBondingConfigTemplateSecondPort	   	DisplayString,         	  
        	xdslBondingConfigRowStatus 	        	RowStatus,
        	xdslBondingConfigProtocolType			INTEGER
        }
        
        xdslBondingConfigGroupId OBJECT-TYPE
        SYNTAX  INTEGER 
        MAX-ACCESS  read-only
        STATUS  current
        DESCRIPTION
                      	"Group ID of Bonding Group.
                      	The value is defined the range of B1~B12.
                      	B1(1),
			        	B2(2),
			        	B3(3),
			        	B4(4),
			        	B5(5),
			        	B6(6),
			        	B7(7),
			        	B8(8),
			        	B9(9),
			        	B10(10),
			        	B11(11),
			        	B12(12),"
        ::= { xdslBondingConfigEntry 1 }

        xdslBondingConfigName OBJECT-TYPE
        SYNTAX  DisplayString
        MAX-ACCESS  read-write
        STATUS  current
        DESCRIPTION
                      	"Name of xDSL Bonding Group."
        ::= { xdslBondingConfigEntry 2 }
        
        xdslBondingConfigMemberPort OBJECT-TYPE
        SYNTAX  PortList
        MAX-ACCESS  read-write
        STATUS  current
        DESCRIPTION
                      	"Member Ports of Bonding Group"
        ::= { xdslBondingConfigEntry 3 }
        
        xdslBondingConfigTemplateMode  OBJECT-TYPE
        SYNTAX  INTEGER{
        	mode1(1),
        	mode2(2)
        }
        MAX-ACCESS  read-write
        STATUS  current
        DESCRIPTION
                      	"Template mode of Bonding Group.
                      	 Mode 1:Total data rate
                      	 Mode 2:Data rate for per-line"
        ::= { xdslBondingConfigEntry 4 }    
                
        xdslBondingConfigTemplateFirstPort  OBJECT-TYPE
        SYNTAX  DisplayString (SIZE(1..32))
        MAX-ACCESS  read-write
        STATUS  current
        DESCRIPTION
       					"The value of this object identifies the row in the
				         xDSL line configuration Profile Table,
				         (xdslBondingConfigTemplateFirstPort) that applies for this first line."
        ::= { xdslBondingConfigEntry 5 }

        xdslBondingConfigTemplateSecondPort  OBJECT-TYPE
        SYNTAX  DisplayString (SIZE(1..32))
        MAX-ACCESS  read-write
        STATUS  current
        DESCRIPTION
                      	"The value of this object identifies the row in the
				         xDSL line configuration Profile Table,
				        (xdslBondingConfigTemplateSecondPort) that applies for this second line."
        ::= { xdslBondingConfigEntry 6 }


        xdslBondingConfigRowStatus OBJECT-TYPE
        SYNTAX  RowStatus
        MAX-ACCESS  read-create
        STATUS  current
        DESCRIPTION
                      	"Row status for bonding profile"
        ::= { xdslBondingConfigEntry 7 }     
        
         
        xdslBondingConfigProtocolType  OBJECT-TYPE
        SYNTAX  INTEGER{
        	ATM(1),
        	PTM(2)
        }
        MAX-ACCESS  read-write
        STATUS  current
        DESCRIPTION
                      	"Bonding transmission mechanism.
                      	 1: ATM
                      	 2: PTM"
        ::= { xdslBondingConfigEntry 8 }

        
    
        
        xdslBondingStatusTable	OBJECT-TYPE
        SYNTAX	SEQUENCE OF XdslBondingStatusEntry
        MAX-ACCESS  not-accessible
        STATUS  current
        DESCRIPTION
                 	""
        ::= { bondingStatus 1 }

		xdslBondingStatusEntry OBJECT-TYPE
        SYNTAX	XdslBondingStatusEntry
        MAX-ACCESS	not-accessible
        STATUS	current
        DESCRIPTION    	"An entry in xdslBondingStatusTable."
        INDEX          	{xdslBondingStatusGroupId }
        ::= { xdslBondingStatusTable 1 }

      	XdslBondingStatusEntry ::=
		SEQUENCE {
			xdslBondingStatusGroupId				INTEGER,
			xdslBondingStatusActive					INTEGER,
            xdslBondingStatusActivePort 			PortList,
        	xdslBondingStatusMainPort				INTEGER,
            xdslBondingStatusFlagType 				INTEGER,
            xdslBondingStatusRateDs 				INTEGER,
        	xdslBondingStatusRateUs					INTEGER,
        	xdslBondingStatusUpTime					DisplayString
        }
                   
----------------------------------------------------------------
           -- PtmBondingCounters
----------------------------------------------------------------

           -- xdslBondingrxSmallFragments Unsigned32,  
           -- xdslBondingrxLargeFragments Unsigned32,       
           -- xdslBondingrxBadFragments   Unsigned32,
           -- xdslBondingrxLostFragments  Unsigned32,  
           -- xdslBondingrxLostStarts     Unsigned32,
           -- xdslBondingrxLostEnds       Unsigned32,
        xdslBondingStatusGroupId OBJECT-TYPE
        SYNTAX  INTEGER
        MAX-ACCESS  read-only
        STATUS  current
        DESCRIPTION
                      	"The value of Bonding Group ID. 
                      	 The ID is set range from 1~12. 
	                      	B1(1),
				        	B2(2),
				        	B3(3),
				        	B4(4),
				        	B5(5),
				        	B6(6),
				        	B7(7),
				        	B8(8),
				        	B9(9),
				        	B10(10),
				        	B11(11),
				        	B12(12)"
        ::= { xdslBondingStatusEntry 1 }
        
        xdslBondingStatusActive OBJECT-TYPE
        SYNTAX  INTEGER
        MAX-ACCESS  read-only
        STATUS  current
        DESCRIPTION
                      	"Current active group for Bonding.
                      	 Active(1), 
                      	 Inactive(2)"
        ::= { xdslBondingStatusEntry 2 }
                
        xdslBondingStatusActivePort OBJECT-TYPE
        SYNTAX  PortList
        MAX-ACCESS  read-only
        STATUS  current
        DESCRIPTION
                      	"Actually, the group ports are activated for Bonding group."
        ::= { xdslBondingStatusEntry 3 }
        
        xdslBondingStatusMainPort OBJECT-TYPE
        SYNTAX  INTEGER
        MAX-ACCESS  read-only
        STATUS  current
        DESCRIPTION
                      	"Main Port(traffic line) of Bonding Group. 
                      	 4294967295(0xffffffff) for Null Value"
        ::= { xdslBondingStatusEntry 4 } 
                        
        xdslBondingStatusFlagType OBJECT-TYPE
        SYNTAX  INTEGER
        MAX-ACCESS  read-only
        STATUS  current
        DESCRIPTION
                      	"The value is the transfer mode for bonding group, 
                      	 the following represent -> 0:ATM; 1:PTM."
        ::= { xdslBondingStatusEntry 5 }
        
        xdslBondingStatusRateDs OBJECT-TYPE
        SYNTAX  INTEGER
        MAX-ACCESS  read-only
        STATUS  current
        DESCRIPTION
                      	"Down-stream Group Rate for Bonding group. 
                      	 4294967295(0xffffffff) for Null Value"
        ::= { xdslBondingStatusEntry 6 }
        
        xdslBondingStatusRateUs OBJECT-TYPE
        SYNTAX  INTEGER
        MAX-ACCESS  read-only
        STATUS  current
        DESCRIPTION
                      	"Up-stream Group Rate for Bonding group. 
                      	 4294967295(0xffffffff) for Null Value"
        ::= { xdslBondingStatusEntry 7 }
        
        xdslBondingStatusUpTime OBJECT-TYPE
        SYNTAX  DisplayString
        MAX-ACCESS  read-only
        STATUS  current
        DESCRIPTION
                "Bonding Group Up Time."
        ::= { xdslBondingStatusEntry 8 }

------------------------------------------------------------------------------------------------      
   
        ptmBondingCountersStatusTable	OBJECT-TYPE
        SYNTAX	SEQUENCE OF PtmBondingCountersStatusEntry
        MAX-ACCESS  not-accessible
        STATUS  current
        DESCRIPTION
                 	""
        ::= { bondingStatus 2 }

		ptmBondingCountersStatusEntry OBJECT-TYPE
        SYNTAX	PtmBondingCountersStatusEntry
        MAX-ACCESS	not-accessible
        STATUS	current
        DESCRIPTION    	"An entry in PtmBondingCountersStatusTable."
        INDEX          	{xdslBondingStatusGroupId }
        ::= { ptmBondingCountersStatusTable 1 }

      	PtmBondingCountersStatusEntry ::=
		SEQUENCE {
	          xdslBondingrxSmallFragments INTEGER,  
              xdslBondingrxLargeFragments INTEGER,       
              xdslBondingrxBadFragments   INTEGER,
              xdslBondingrxLostFragments  INTEGER,  
              xdslBondingrxLostStarts     INTEGER,
              xdslBondingrxLostEnds       INTEGER
        }

----------------------------------------------------------------
           -- PtmBondingCounters     
----------------------------------------------------------------
   
------------------------------------------------------------------------------------------------   
     --   PtmBondingCounters OBJECT IDENTIFIER ::= { xdslBondingSetup 3 }
                                                                 
        xdslBondingrxSmallFragments OBJECT-TYPE
        SYNTAX  INTEGER
        MAX-ACCESS  read-only
        STATUS  current
        DESCRIPTION 
        			"nbr of fragments discarded due to too small."
                                   	                           
        ::= { ptmBondingCountersStatusEntry 1 }
                                          
        xdslBondingrxLargeFragments OBJECT-TYPE
        SYNTAX  INTEGER
        MAX-ACCESS  read-only
        STATUS  current
        DESCRIPTION 
        			"nbr of fragments discarded due to too long."                      	                     	        
        ::= { ptmBondingCountersStatusEntry 2 }      
        
        xdslBondingrxBadFragments   OBJECT-TYPE
        SYNTAX  INTEGER
        MAX-ACCESS  read-only
        STATUS  current
        DESCRIPTION 
                    "fragments not in sequence"                      	                     	        
        ::= { ptmBondingCountersStatusEntry 3 }     
        
        xdslBondingrxLostFragments  OBJECT-TYPE
        SYNTAX  INTEGER
        MAX-ACCESS  read-only
        STATUS  current
        DESCRIPTION 
        			"nbr of gaps in fragments sequence."                      	                     	        
        ::= { ptmBondingCountersStatusEntry 4 }    
        
        xdslBondingrxLostStarts   OBJECT-TYPE
        SYNTAX  INTEGER
        MAX-ACCESS  read-only
        STATUS  current
        DESCRIPTION 
        			"missing SOPS"                      	                     	        
        ::= { ptmBondingCountersStatusEntry 5 }

        xdslBondingrxLostEnds   OBJECT-TYPE
        SYNTAX  INTEGER
        MAX-ACCESS  read-only
        STATUS  current
        DESCRIPTION 
        			"missing EOPs"                      	                     	        
        ::= { ptmBondingCountersStatusEntry 6 }  

---------------------------------------------------
--
--  Bonding Group Lookup
--
---------------------------------------------------               
        
        bondingGroupLookupTable	OBJECT-TYPE
        SYNTAX	SEQUENCE OF BondingGroupLookupEntry
        MAX-ACCESS  not-accessible
        STATUS  current
        DESCRIPTION
                 	""
        ::= { bondingStatus 3 }

		bondingGroupLookupEntry OBJECT-TYPE
        SYNTAX	BondingGroupLookupEntry
        MAX-ACCESS	not-accessible
        STATUS	current
        DESCRIPTION    	"An entry in xdslBondingGroupLookupTable."
        INDEX          	{ifIndex}
        ::= { bondingGroupLookupTable 1 }

      	BondingGroupLookupEntry ::=
		SEQUENCE {
			bondingGroupIDLookup					INTEGER,
			bondingGroupNameLookup					DisplayString,
			bondingGroupActiveLookup				INTEGER,
			bondingGroupMainPortLookup				INTEGER,
			bondingGroupProfileLookup				DisplayString,
			bondingGroupMaxDSrateLookup				INTEGER,
			bondingGroupMaxUSrateLookup				INTEGER,
			bondingGroupMinDSrateLookup				INTEGER,
			bondingGroupMinUSrateLookup				INTEGER			
        }
        
        bondingGroupIDLookup OBJECT-TYPE
        SYNTAX  INTEGER
        MAX-ACCESS  read-only
        STATUS  current
        DESCRIPTION
                      	"The value of Bonding Group ID. 
                      	 The ID is set range from 1~12. 
	                      	B1(1),
				        	B2(2),
				        	B3(3),
				        	B4(4),
				        	B5(5),
				        	B6(6),
				        	B7(7),
				        	B8(8),
				        	B9(9),
				        	B10(10),
				        	B11(11),
				        	B12(12)"
        ::= { bondingGroupLookupEntry 1 }
        
        bondingGroupNameLookup OBJECT-TYPE
        SYNTAX  DisplayString
        MAX-ACCESS  read-only
        STATUS  current
        DESCRIPTION
                      	"Name of xDSL Bonding Group."
        ::= { bondingGroupLookupEntry 2 }

        bondingGroupActiveLookup OBJECT-TYPE
        SYNTAX  INTEGER
        MAX-ACCESS  read-only
        STATUS  current
        DESCRIPTION
                      	"Current active group for Bonding.
                      	 Active(1), 
                      	 Inactive(2)"
        ::= { bondingGroupLookupEntry 3 }
        
        bondingGroupMainPortLookup OBJECT-TYPE
        SYNTAX  INTEGER
        MAX-ACCESS  read-only
        STATUS  current
        DESCRIPTION
                      	"Main Port(traffic line) of Bonding Group. 
                      	 Others Port(0)
                      	 Main Port(1), 
                      	 Slave Port(2)"
        ::= { bondingGroupLookupEntry 4 } 
               
        bondingGroupProfileLookup  OBJECT-TYPE
        SYNTAX  DisplayString (SIZE(1..32))
        MAX-ACCESS  read-only
        STATUS  current
        DESCRIPTION
       					"The value of this object identifies the row in the
				         xDSL line configuration Profile Table."
        ::= { bondingGroupLookupEntry 5 }               
               
        bondingGroupMaxDSrateLookup OBJECT-TYPE
        SYNTAX  INTEGER
        MAX-ACCESS  read-only
        STATUS  current
        DESCRIPTION
                      	"Max Downstream Rate for the lines. 
                      	 4294967295(0xffffffff) for Null Value"
        ::= { bondingGroupLookupEntry 6 }  
        
        bondingGroupMaxUSrateLookup OBJECT-TYPE
        SYNTAX  INTEGER
        MAX-ACCESS  read-only
        STATUS  current
        DESCRIPTION
                      	"Max Upstream Rate for the lines. 
                      	 4294967295(0xffffffff) for Null Value"
        ::= { bondingGroupLookupEntry 7 }     
                      
        bondingGroupMinDSrateLookup OBJECT-TYPE
        SYNTAX  INTEGER
        MAX-ACCESS  read-only
        STATUS  current
        DESCRIPTION
                      	"Min Downstream Rate for the lines. 
                      	 4294967295(0xffffffff) for Null Value"
        ::= { bondingGroupLookupEntry 8 }  
     
        bondingGroupMinUSrateLookup OBJECT-TYPE
        SYNTAX  INTEGER
        MAX-ACCESS  read-only
        STATUS  current
        DESCRIPTION
                      	"Min Upstream Rate for the lines. 
                      	 4294967295(0xffffffff) for Null Value"
        ::= { bondingGroupLookupEntry 9 }
--------------------------bonding protocol based vlan---------------------------------------------
	    bondingprotoBasedVlanTable  OBJECT-TYPE
	    SYNTAX	SEQUENCE OF BondingProtoBasedVlanEntry 
	    MAX-ACCESS  not-accessible
	    STATUS  current
	    DESCRIPTION
	             	""
	    ::= { bondingStatus 4 }	

	bondingprotoBasedVlanEntry  OBJECT-TYPE
        SYNTAX	BondingProtoBasedVlanEntry 
        MAX-ACCESS	not-accessible
        STATUS	current
        DESCRIPTION    	"An entry in BondingprotoBasedVlanTable."
        INDEX          	{ bondingprotoBasedVlanBondingGroup, bondingprotoBasedVlanPacketType, bondingprotoBasedVlanEtherType }
        ::= { bondingprotoBasedVlanTable 1 }

        BondingProtoBasedVlanEntry ::=
           SEQUENCE {
            bondingprotoBasedVlanBondingGroup			INTEGER,
        	bondingprotoBasedVlanPacketType	INTEGER,
        	bondingprotoBasedVlanEtherType		INTEGER,
        	bondingprotoBasedVlanName			DisplayString,
        	bondingprotoBasedVlanVid			INTEGER,
        	bondingprotoBasedVlanPriority		INTEGER,
        	bondingprotoBasedVlanState			RowStatus
           }

        bondingprotoBasedVlanBondingGroup OBJECT-TYPE
        SYNTAX  INTEGER
        MAX-ACCESS  read-only
        STATUS  current
        DESCRIPTION
                      	""
        ::= { bondingprotoBasedVlanEntry 1 }

        bondingprotoBasedVlanPacketType OBJECT-TYPE
        SYNTAX  INTEGER{
        	etherII(1),
        	snap(2),
        	llc(3)
        }
        MAX-ACCESS  read-only
        STATUS  current
        DESCRIPTION
                      	""
        ::= { bondingprotoBasedVlanEntry 2 }

        bondingprotoBasedVlanEtherType OBJECT-TYPE
        SYNTAX  INTEGER
        MAX-ACCESS  read-only
        STATUS  current
        DESCRIPTION
                      	""
        ::= { bondingprotoBasedVlanEntry 3 }

        bondingprotoBasedVlanName OBJECT-TYPE
        SYNTAX  DisplayString (SIZE (0..32))
        MAX-ACCESS  read-only
        STATUS  current
        DESCRIPTION
                      	""
        ::= { bondingprotoBasedVlanEntry 4 }

        bondingprotoBasedVlanVid OBJECT-TYPE
        SYNTAX  INTEGER (1..4094)
        MAX-ACCESS  read-only
        STATUS  current
        DESCRIPTION
                      	""
        ::= { bondingprotoBasedVlanEntry 5 }

        bondingprotoBasedVlanPriority OBJECT-TYPE
        SYNTAX  INTEGER (0..7)
        MAX-ACCESS  read-only
        STATUS  current
        DESCRIPTION
                      	""
        ::= { bondingprotoBasedVlanEntry 6 }
		
		bondingprotoBasedVlanState OBJECT-TYPE
        SYNTAX  RowStatus
        MAX-ACCESS  read-only
        STATUS  current
        DESCRIPTION
                      	""
        ::= { bondingprotoBasedVlanEntry 7 }
       
              
--------------------------------------------------

         -- mgmdBondingStatusTable
---------------------------------------------------        
        mgmdBondingStatusTable	OBJECT-TYPE
        SYNTAX	SEQUENCE OF MgmdBondingStatusEntry
        MAX-ACCESS  not-accessible
        STATUS  current
        DESCRIPTION
                 	""
        ::= { bondingStatus 5 }

		mgmdBondingStatusEntry OBJECT-TYPE
        SYNTAX	MgmdBondingStatusEntry
        MAX-ACCESS	not-accessible
        STATUS	current
        DESCRIPTION    	"An entry in mgmdBondingStatusTable."
        INDEX          	{mgmdBondingGroupId }
        ::= { mgmdBondingStatusTable 1 }

      	MgmdBondingStatusEntry ::=
		SEQUENCE {
			mgmdBondingGroupId				INTEGER,  
			mgmdBondingActiveMcastGroupNum  INTEGER,
			mgmdBondingGroupImmediateLeave  EnabledStatus
		}
                   
                   
        mgmdBondingGroupId OBJECT-TYPE
        SYNTAX  INTEGER
        MAX-ACCESS  read-only
        STATUS  current
        DESCRIPTION
                      	"The value of Bonding Group ID."
        ::= { mgmdBondingStatusEntry 1 } 
        
        mgmdBondingActiveMcastGroupNum OBJECT-TYPE
        SYNTAX  INTEGER
        MAX-ACCESS  read-only
        STATUS  current
        DESCRIPTION
                      	"The value of active multicast group number for bonding group."
        ::= { mgmdBondingStatusEntry 2 }
        
        mgmdBondingGroupImmediateLeave OBJECT-TYPE
        SYNTAX  EnabledStatus
        MAX-ACCESS  read-only
        STATUS  current
        DESCRIPTION
                      	"Current multicast immediate leave for Bonding group.
                      	 Enable(1), 
                      	 Disable(2)"
        ::= { mgmdBondingStatusEntry 3 }
                


--------------------------------------------------

         -- mvrBondingStatusTable
---------------------------------------------------        
        mvrBondingStatusTable	OBJECT-TYPE
        SYNTAX	SEQUENCE OF MvrBondingStatusEntry
        MAX-ACCESS  not-accessible
        STATUS  current
        DESCRIPTION
                 	""
        ::= { bondingStatus 6 }

		mvrBondingStatusEntry OBJECT-TYPE
        SYNTAX	MvrBondingStatusEntry
        MAX-ACCESS	not-accessible
        STATUS	current
        DESCRIPTION    	"An entry in xdslBondingMgmdStatusTable."
        INDEX          	{mvrVlanID ,mvrBondingGroupId }
        ::= { mvrBondingStatusTable 1 }

      	MvrBondingStatusEntry ::=
		SEQUENCE {
			mvrBondingGroupId				INTEGER,
			mvrBondingPortRole              INTEGER,
			mvrBondingPortTagging			EnabledStatus
		}
                   
                   
        mvrBondingGroupId OBJECT-TYPE
        SYNTAX  INTEGER
        MAX-ACCESS  read-only
        STATUS  current
        DESCRIPTION
                      	"The value of Bonding Group ID."
        ::= { mvrBondingStatusEntry 1 }
        
        mvrBondingPortRole OBJECT-TYPE
        SYNTAX  INTEGER{
        	none(1),
        	source_port(2),
        	receiver_port(3)
        }

        MAX-ACCESS  read-only
        STATUS  current
        DESCRIPTION
                      	"Current mvr port role for Bonding group.
                      	 none(1), 
                      	 source_port(2)
                      	 receiver_port(3)"
        ::= { mvrBondingStatusEntry 2 }
          
        mvrBondingPortTagging OBJECT-TYPE
        SYNTAX  EnabledStatus
        MAX-ACCESS  read-only
        STATUS  current
        DESCRIPTION
                      	"Current mvr tagging status for Bonding group."
        ::= { mvrBondingStatusEntry 3 }  
        

		                                     
---------------------------------------------------
--
--		ifBondingTable
--     
---------------------------------------------------   

        ifBondingStatusTable	OBJECT-TYPE
        SYNTAX	SEQUENCE OF IfBondingStatusEntry
        MAX-ACCESS  not-accessible
        STATUS  current
        DESCRIPTION
                 	""
        ::= { bondingStatus 7 }

		        
		ifBondingStatusEntry	 	OBJECT-TYPE
		SYNTAX	 	IfBondingStatusEntry
		MAX-ACCESS	not-accessible
		STATUS	 	current
		DESCRIPTION	 	
						"An entry containing additional management information
						 applicable to a particular interface."
		INDEX	 	{ifBondingGroupId} 
		::= { ifBondingStatusTable 1 }
		
		IfBondingStatusEntry ::=
		SEQUENCE {
			ifBondingGroupId	 	    		INTEGER, 
			ifBondingGroupActive                INTEGER,
			ifBondingInMulticastPkts	  		Counter32,
			ifBondingInBroadcastPkts	  		Counter32,
			ifBondingOutMulticastPkts	  		Counter32,
			ifBondingOutBroadcastPkts	  		Counter32,
			ifBondingHCInOctets	  				Counter64,
			ifBondingHCInUcastPkts	  			Counter64,
			ifBondingHCInMulticastPkts	  		Counter64,
			ifBondingHCInBroadcastPkts	  		Counter64,
			ifBondingHCOutOctets	  			Counter64,
			ifBondingHCOutUcastPkts	  			Counter64,
			ifBondingHCOutMulticastPkts	  		Counter64,
			ifBondingHCOutBroadcastPkts	  		Counter64,
			ifBondingLinkUpDownTrapEnable	  	EnabledStatus,
			ifBondingHighSpeed	  				Gauge32,
			ifBondingPromiscuousMode	  		TruthValue,
			ifBondingConnectorPresent	  		TruthValue,
			ifBondingCounterDiscontinuityTime	UtcTimeStamp,  
			ifBondingInDiscards					Counter32,
			ifBondingOutDiscards           		Counter32			  
		}
           
        ifBondingGroupId OBJECT-TYPE
        SYNTAX  INTEGER
        MAX-ACCESS  read-only
        STATUS  current
        DESCRIPTION
                      	"The value of Bonding Group ID."
        ::= { ifBondingStatusEntry 1 }
        
	   	
	   	ifBondingGroupActive OBJECT-TYPE
        SYNTAX  INTEGER{
        	active(1),
        	inactive(2)
        }
        MAX-ACCESS  read-only
        STATUS  current
        DESCRIPTION
                      	""
        ::= { ifBondingStatusEntry 2 }
        

	
		ifBondingInMulticastPkts	 	OBJECT-TYPE
		SYNTAX	 	Counter32
		MAX-ACCESS	 	read-only
		STATUS	 	current
		DESCRIPTION	 	
					"The number of packets, delivered by this sub-layer to a
					higher (sub-)layer, which were addressed to a multicast
					address at this sub-layer.  For a MAC layer protocol, this
					includes both Group and Functional addresses.		
					Discontinuities in the value of this counter can occur at
					re-initialization of the management system, and at other
					times as indicated by the value ofi fCounterDiscontinuityTime."
		::= { ifBondingStatusEntry 3 }
	
		                                
		ifBondingInBroadcastPkts	 	OBJECT-TYPE
		SYNTAX	 	Counter32
		MAX-ACCESS	 	read-only
		STATUS	 	current
		DESCRIPTION	 	
					"The number of packets, delivered by this sub-layer to a
					higher (sub-)layer, which were addressed to a broadcast
					address at this sub-layer.		
					Discontinuities in the value of this counter can occur at
					re-initialization of the management system, and at other
					times as indicated by the value of ifCounterDiscontinuityTime."                                
		::= { ifBondingStatusEntry 4 }
		
		                                       
		                                       
		ifBondingOutMulticastPkts	 	OBJECT-TYPE
		SYNTAX	 	Counter32
		MAX-ACCESS	 	read-only
		STATUS	 	current
		DESCRIPTION	 	
					"The total number of packets that higher-level protocols
					requested be transmitted, and which were addressed to a
					multicast address at this sub-layer, including those that
					were discarded or not sent.  For a MAC layer protocol, this
					includes both Group and Functional addresses.		
					Discontinuities in the value of this counter can occur at
					re-initialization of the management system, and at other
					times as indicated by the value of ifCounterDiscontinuityTime."   
		::= { ifBondingStatusEntry 5 } 
		
		
		ifBondingOutBroadcastPkts	 	OBJECT-TYPE
		SYNTAX	 	Counter32
		MAX-ACCESS	 	read-only
		STATUS	 	current
		DESCRIPTION	 	
					"The total number of packets that higher-level protocols
					requested be transmitted, and which were addressed to a
					broadcast address at this sub-layer, including those that
					were discarded or not sent.		
					Discontinuities in the value of this counter can occur at
					re-initialization of the management system, and at other		
					times as indicated by the value of ifCounterDiscontinuityTime."    
		::= { ifBondingStatusEntry 6 }
		                                
		                                
		
		ifBondingHCInOctets	 	OBJECT-TYPE
		SYNTAX	 	Counter64
		MAX-ACCESS	 	read-only
		STATUS	 	current
		DESCRIPTION	 	
					"The total number of octets received on the interface,
					including framing characters.  This object is a 64-bit
					version of ifInOctets.		
					Discontinuities in the value of this counter can occur at
					re-initialization of the management system, and at other
					times as indicated by the value of ifCounterDiscontinuityTime."  
		::= { ifBondingStatusEntry 7 }		
				
		
		ifBondingHCInUcastPkts	 	OBJECT-TYPE
		SYNTAX	 	Counter64
		MAX-ACCESS	 	read-only
		STATUS	 	current
		DESCRIPTION	 	
					"The number of packets, delivered by this sub-layer to a
					higher (sub-)layer, which were not addressed to a multicast
					or broadcast address at this sub-layer.  This object is a
					64-bit version of ifInUcastPkts.		
					Discontinuities in the value of this counter can occur at
					re-initialization of the management system, and at other
					times as indicated by the value of ifCounterDiscontinuityTime."
		::= { ifBondingStatusEntry 8 }    
		    
		
		
		ifBondingHCInMulticastPkts	 	OBJECT-TYPE
		SYNTAX	 	Counter64
		MAX-ACCESS	 	read-only
		STATUS	 	current
		DESCRIPTION	 	
					"The number of packets, delivered by this sub-layer to a
					higher (sub-)layer, which were addressed to a multicast
					address at this sub-layer.  For a MAC layer protocol, this
					includes both Group and Functional addresses.  This object
					is a 64-bit version of ifInMulticastPkts.		
					Discontinuities in the value of this counter can occur at
					re-initialization of the management system, and at other
					times as indicated by the value of ifCounterDiscontinuityTime."         
		::= { ifBondingStatusEntry 9 }
		
		
		ifBondingHCInBroadcastPkts	 	OBJECT-TYPE
		SYNTAX	 	Counter64
		MAX-ACCESS	read-only
		STATUS	 	current
		DESCRIPTION	 	
					"The number of packets, delivered by this sub-layer to a
					higher (sub-)layer, which were addressed to a broadcast
					address at this sub-layer.  This object is a 64-bit version
					of ifInBroadcastPkts.		
					Discontinuities in the value of this counter can occur at
					re-initialization of the management system, and at other
					times as indicated by the value of ifCounterDiscontinuityTime."
        ::= { ifBondingStatusEntry 10 }

        
		
		ifBondingHCOutOctets	 	OBJECT-TYPE
		SYNTAX	 	Counter64
		MAX-ACCESS	 read-only
		STATUS	 	current
		DESCRIPTION	 	
					"The total number of octets transmitted out of the
					interface, including framing characters.  This object is a
					64-bit version of ifOutOctets.		
					Discontinuities in the value of this counter can occur at
					re-initialization of the management system, and at other
					times as indicated by the value of ifCounterDiscontinuityTime."
        ::= { ifBondingStatusEntry 11 }


         
		ifBondingHCOutUcastPkts	 	OBJECT-TYPE
		SYNTAX	 	Counter64
		MAX-ACCESS	 read-only
		STATUS	 	current
		DESCRIPTION	 	
					"The total number of packets that higher-level protocols
					requested be transmitted, and which were not addressed to a
					multicast or broadcast address at this sub-layer, including
					those that were discarded or not sent.  This object is a
					64-bit version of ifOutUcastPkts.		
					Discontinuities in the value of this counter can occur at
					re-initialization of the management system, and at other
					times as indicated by the value of ifCounterDiscontinuityTime."    
		::= { ifBondingStatusEntry 12 }  
		
		
		ifBondingHCOutMulticastPkts	 	OBJECT-TYPE
		SYNTAX	 	Counter64
		MAX-ACCESS	 	read-only
		STATUS	 	current
		DESCRIPTION	 	
					"The total number of packets that higher-level protocols
					requested be transmitted, and which were addressed to a
					multicast address at this sub-layer, including those that
					were discarded or not sent.  For a MAC layer protocol, this
					includes both Group and Functional addresses.  This object
					is a 64-bit version of ifOutMulticastPkts.		
					Discontinuities in the value of this counter can occur at
					re-initialization of the management system, and at other
					times as indicated by the value of ifCounterDiscontinuityTime."
        ::= { ifBondingStatusEntry 13 } 
        
                        
        ifBondingHCOutBroadcastPkts	 	OBJECT-TYPE
		SYNTAX	 	Counter64
		MAX-ACCESS	 	read-only
		STATUS	 	current
		DESCRIPTION	 	
					"The total number of packets that higher-level protocols
					requested be transmitted, and which were addressed to a
					broadcast address at this sub-layer, including those that
					were discarded or not sent.  This object is a 64-bit version
					of ifOutBroadcastPkts.		
					Discontinuities in the value of this counter can occur at
					re-initialization of the management system, and at other
					times as indicated by the value of ifCounterDiscontinuityTime."    
		::= { ifBondingStatusEntry 14 }
		
		
		ifBondingLinkUpDownTrapEnable	 	OBJECT-TYPE
		SYNTAX	EnabledStatus
		MAX-ACCESS	 	read-write
		STATUS	 	current
		DESCRIPTION	 	
					"Indicates whether linkUp/linkDown traps should be generated
					for this interface.
					By default, this object should have the value enabled(1) for
					interfaces which do not operate on 'top' of any other
					interface (as defined in the ifStackTable), and disabled(2)
					otherwise."
        ::= { ifBondingStatusEntry 15 }   
        

		ifBondingHighSpeed	 	OBJECT-TYPE
		SYNTAX	 	Gauge32
		MAX-ACCESS	 	read-only
		STATUS	 	current
		DESCRIPTION	 	
					"An estimate of the interface's current bandwidth in units
					of 1,000,000 bits per second.  If this object reports a
					value of `n' then the speed of the interface is somewhere in
					the range of `n-500,000' to `n+499,999'.  For interfaces
					which do not vary in bandwidth or for those where no
					accurate estimation can be made, this object should contain
					the nominal bandwidth.  For a sub-layer which has no concept
					of bandwidth, this object should be zero."
        ::= { ifBondingStatusEntry 16 } 
        

		ifBondingPromiscuousMode	 	OBJECT-TYPE
		SYNTAX	 	TruthValue
		MAX-ACCESS	 	read-write
		STATUS	 	current
		DESCRIPTION	 	
					"This object has a value of false(2) if this interface only
					accepts packets/frames that are addressed to this station.
					This object has a value of true(1) when the station accepts
					all packets/frames transmitted on the media.  The value
					true(1) is only legal on certain types of media.  If legal,
					setting this object to a value of true(1) may require the
					interface to be reset before becoming effective.		
					The value of ifPromiscuousMode does not affect the reception
					of broadcast and multicast packets/frames by the interface."     
		::= { ifBondingStatusEntry 17 }
		
		
		ifBondingConnectorPresent	 	OBJECT-TYPE
		SYNTAX	 	TruthValue
		MAX-ACCESS	 	read-only
		STATUS	 	current
		DESCRIPTION	 	
					"This object has the value 'true(1)' if the interface
					sublayer has a physical connector and the value 'false(2)'
					otherwise."
		::= { ifBondingStatusEntry 18 }
		
        ifBondingCounterDiscontinuityTime	 	OBJECT-TYPE
		SYNTAX	 	UtcTimeStamp
		MAX-ACCESS	read-only
		STATUS	 	current
		DESCRIPTION	 	
					"The value of sysUpTime on the most recent occasion at which
					any one or more of this interface's counters suffered a
					discontinuity.  The relevant counters are the specific
					instances associated with this interface of any Counter32 or
					Counter64 object contained in the ifTable or ifXTable.  If
					no such discontinuities have occurred since the last re-
					initialization of the local management subsystem, then this
					object contains a zero value."  
		::= { ifBondingStatusEntry 19 }                                     

        ifBondingInDiscards OBJECT-TYPE
        SYNTAX  	Counter32
        MAX-ACCESS  read-only
        STATUS  	current
        DESCRIPTION
                      	"The number of inbound packets which were chosen to be
						discarded even though no errors had been detected to prevent
						their being deliverable to a higher-layer protocol.  One
						possible reason for discarding such a packet could be to
						free up buffer space.
						
						Discontinuities in the value of this counter can occur at
						re-initialization of the management system, and at other
						times as indicated by the value of
						ifCounterDiscontinuityTime."
        ::= { ifBondingStatusEntry 20 }
                                       
                             
        ifBondingOutDiscards OBJECT-TYPE
		SYNTAX	 	Counter32
		MAX-ACCESS	read-only
		STATUS	 	current
		DESCRIPTION	 	
		
					"The number of outbound packets which were chosen to be
					discarded even though no errors had been detected to prevent
					their being transmitted.  One possible reason for discarding
					such a packet could be to free up buffer space.
					
					Discontinuities in the value of this counter can occur at
					re-initialization of the management system, and at other
					times as indicated by the value of
					ifCounterDiscontinuityTime."
		::= { ifBondingStatusEntry 21 } 
				
------------------------------------------------------		
--		   
-- 		switchCounterTable
--
------------------------------------------------------
        switchCounterBondingStatusTable OBJECT-TYPE
        SYNTAX	SEQUENCE OF SwitchCounterBondingStatusEntry
        MAX-ACCESS  not-accessible
        STATUS  current
        DESCRIPTION
                 	""
        ::= { bondingStatus 8 }

		switchCounterBondingStatusEntry OBJECT-TYPE
        SYNTAX	SwitchCounterBondingStatusEntry
        MAX-ACCESS	not-accessible
        STATUS	current
        DESCRIPTION    	"An entry in switchCounterTable."
        INDEX          	{ switchCounterBondingGroupId }
        ::= { switchCounterBondingStatusTable 1 }

        SwitchCounterBondingStatusEntry ::=
           SEQUENCE {       
            switchCounterBondingGroupId 	INTEGER,
        	switchBondingUnknownUnicastCounter		Counter32,
        	switchBondingTxRatelimitDropCounter	Counter32,
        	switchBondingRxRatelimitDropCounter	Counter64,
        	switchBondingRxMeterDropCounter	 	Counter64
           }             
           
        switchCounterBondingGroupId OBJECT-TYPE
        SYNTAX  INTEGER
        MAX-ACCESS  read-only
        STATUS  current
        DESCRIPTION
       			 "The Bonding Group ID for SwitchCounterBondingStatusEntry."
        ::= { switchCounterBondingStatusEntry 1 }


        switchBondingUnknownUnicastCounter OBJECT-TYPE
        SYNTAX  Counter32
        MAX-ACCESS  read-only
        STATUS  current
        DESCRIPTION
        			"Unknown unicast counter for the port."
        ::= { switchCounterBondingStatusEntry 2 }

        switchBondingTxRatelimitDropCounter OBJECT-TYPE
        SYNTAX  Counter32
        MAX-ACCESS  read-only
        STATUS  current
        DESCRIPTION
        			"Rx Ratelimit drop counter."
        ::= { switchCounterBondingStatusEntry 3 }

        switchBondingRxRatelimitDropCounter OBJECT-TYPE
        SYNTAX  Counter64
        MAX-ACCESS  read-only
        STATUS  current
        DESCRIPTION
        			"Tx Ratelimit drop counter."
        ::= { switchCounterBondingStatusEntry 4 }

        switchBondingRxMeterDropCounter OBJECT-TYPE
        SYNTAX  Counter64
        MAX-ACCESS  read-only
        STATUS  current
        DESCRIPTION
        			"Rx Metering drop counter."
        ::= { switchCounterBondingStatusEntry 5 }


---------------------------------------------------
--
--  sfp Threshold Setup
--
---------------------------------------------------

-- sfpThresholdSetup
	sfpThresholdSetup     	OBJECT IDENTIFIER ::= { ves1724-56fanless 123 }

                                               
-- sfpThresholdTable
                                
      	sfpUserInputActive	OBJECT-TYPE
        SYNTAX	INTEGER {
        		active(1),
        		inactive(2)
         }

        MAX-ACCESS  read-write
        STATUS  current
        DESCRIPTION
                 	"Active transceiver threshold as user input."
        ::= { sfpThresholdSetup 1 }

     	sfpThresholdTable OBJECT-TYPE
        SYNTAX	SEQUENCE OF SfpThresholdUserInputEntry
        MAX-ACCESS  not-accessible
        STATUS  current 
        DESCRIPTION
                 	""
        ::= { sfpThresholdSetup 2 }
        
		sfpThresholdUserInputEntry OBJECT-TYPE
        SYNTAX	SfpThresholdUserInputEntry
        MAX-ACCESS	not-accessible
        STATUS	current 
        DESCRIPTION    	"An entry in sfpThresholdTable."
        INDEX          	{ sfpPortIndex }
        ::= { sfpThresholdTable 1 }

        SfpThresholdUserInputEntry ::=
           SEQUENCE {   
           		sfpPortIndex            	INTEGER,
	        	sfpTempHighAlarmThresh		DisplayString,
	        	sfpTempHighWarnThresh		DisplayString,
	        	sfpTempLowWarnThresh   		DisplayString,
	        	sfpTempLowAlarmThresh  		DisplayString,
        	    sfpVoltageHighAlarmThresh	DisplayString,
	        	sfpVoltageHighWarnThresh	DisplayString,
	        	sfpVoltageLowWarnThresh   	DisplayString,
	        	sfpVoltageLowAlarmThresh  	DisplayString,
	        	sfpTxBiasHighAlarmThresh	DisplayString,
	        	sfpTxBiasHighWarnThresh		DisplayString,
	        	sfpTxBiasLowWarnThresh   	DisplayString,
	        	sfpTxBiasLowAlarmThresh  	DisplayString,
	        	sfpTxPowerHighAlarmThresh	DisplayString,
	        	sfpTxPowerHighWarnThresh	DisplayString,
	        	sfpTxPowerLowWarnThresh   	DisplayString,
	        	sfpTxPowerLowAlarmThresh  	DisplayString,
	        	sfpRxPowerHighAlarmThresh	DisplayString,
	        	sfpRxPowerHighWarnThresh	DisplayString,
	        	sfpRxPowerLowWarnThresh   	DisplayString,
	        	sfpRxPowerLowAlarmThresh  	DisplayString 	
           }

        sfpPortIndex OBJECT-TYPE
        SYNTAX  INTEGER
        MAX-ACCESS  read-only
        STATUS  current 
        DESCRIPTION
                      	"sfp port index"
        ::= { sfpThresholdUserInputEntry 1 }


        sfpTempHighAlarmThresh OBJECT-TYPE
        SYNTAX  DisplayString
        MAX-ACCESS  read-write
        STATUS  current 
        DESCRIPTION
                      	"User defined high alarm threshold of temperature of sfp port"
        ::= { sfpThresholdUserInputEntry 2 }

        sfpTempHighWarnThresh OBJECT-TYPE
        SYNTAX  DisplayString
        MAX-ACCESS  read-write
        STATUS  current 
        DESCRIPTION
                      	"User defined high warning threshold of temperature of sfp port"
        ::= { sfpThresholdUserInputEntry 3 }

        sfpTempLowWarnThresh OBJECT-TYPE
        SYNTAX  DisplayString
        MAX-ACCESS  read-write
        STATUS  current 
        DESCRIPTION
                      	"User defined low warning threshold of temperature of sfp port"
        ::= { sfpThresholdUserInputEntry 4 }

        sfpTempLowAlarmThresh OBJECT-TYPE
        SYNTAX  DisplayString
        MAX-ACCESS  read-write
        STATUS  current 
        DESCRIPTION
                      	"User defined low alarm threshold of temperature of sfp port"
        ::= { sfpThresholdUserInputEntry 5 }
        
         
        sfpVoltageHighAlarmThresh OBJECT-TYPE
        SYNTAX  DisplayString
        MAX-ACCESS  read-write
        STATUS  current 
        DESCRIPTION
                      	"User defined high alarm threshold of voltage of sfp port"
        ::= { sfpThresholdUserInputEntry 6 }

        sfpVoltageHighWarnThresh OBJECT-TYPE
        SYNTAX  DisplayString
        MAX-ACCESS  read-write
        STATUS  current 
        DESCRIPTION
                      	"User defined high warning threshold of voltage of sfp port"
        ::= { sfpThresholdUserInputEntry 7 }

        sfpVoltageLowWarnThresh OBJECT-TYPE
        SYNTAX  DisplayString
        MAX-ACCESS  read-write
        STATUS  current 
        DESCRIPTION
                      	"User defined low warning threshold of voltage of sfp port"
        ::= { sfpThresholdUserInputEntry 8 }

        sfpVoltageLowAlarmThresh OBJECT-TYPE
        SYNTAX  DisplayString
        MAX-ACCESS  read-write
        STATUS  current 
        DESCRIPTION
                      	"User defined low alarm threshold of voltage of sfp port"
        ::= { sfpThresholdUserInputEntry 9 }
        
        
        sfpTxBiasHighAlarmThresh OBJECT-TYPE
        SYNTAX  DisplayString
        MAX-ACCESS  read-write
        STATUS  current 
        DESCRIPTION
                      	"User defined high alarm threshold of tx bias of sfp port"
        ::= { sfpThresholdUserInputEntry 10 }

        sfpTxBiasHighWarnThresh OBJECT-TYPE
        SYNTAX  DisplayString
        MAX-ACCESS  read-write
        STATUS  current 
        DESCRIPTION
                      	"User defined high warning threshold of tx bias of sfp port"
        ::= { sfpThresholdUserInputEntry 11 }

        sfpTxBiasLowWarnThresh OBJECT-TYPE
        SYNTAX  DisplayString
        MAX-ACCESS  read-write
        STATUS  current 
        DESCRIPTION
                      	"User defined low warning threshold of tx bias of sfp port"
        ::= { sfpThresholdUserInputEntry 12 }

        sfpTxBiasLowAlarmThresh OBJECT-TYPE
        SYNTAX  DisplayString
        MAX-ACCESS  read-write
        STATUS  current 
        DESCRIPTION
                      	"User defined low alarm threshold of tx bias of sfp port"
        ::= { sfpThresholdUserInputEntry 13 }
        
        
        sfpTxPowerHighAlarmThresh OBJECT-TYPE
        SYNTAX  DisplayString
        MAX-ACCESS  read-write
        STATUS  current 
        DESCRIPTION
                      	"User defined high alarm threshold of tx power of sfp port"
        ::= { sfpThresholdUserInputEntry 14 }

        sfpTxPowerHighWarnThresh OBJECT-TYPE
        SYNTAX  DisplayString
        MAX-ACCESS  read-write
        STATUS  current 
        DESCRIPTION
                      	"User defined high warning threshold of tx power of sfp port"
        ::= { sfpThresholdUserInputEntry 15 }

        sfpTxPowerLowWarnThresh OBJECT-TYPE
        SYNTAX  DisplayString
        MAX-ACCESS  read-write
        STATUS  current 
        DESCRIPTION
                      	"User defined low warning threshold of tx power of sfp port"
        ::= { sfpThresholdUserInputEntry 16 }

        sfpTxPowerLowAlarmThresh OBJECT-TYPE
        SYNTAX  DisplayString
        MAX-ACCESS  read-write
        STATUS  current 
        DESCRIPTION
                      	"User defined low alarm threshold of tx power of sfp port"
        ::= { sfpThresholdUserInputEntry 17 }
                        
     
        sfpRxPowerHighAlarmThresh OBJECT-TYPE
        SYNTAX  DisplayString
        MAX-ACCESS  read-write
        STATUS  current 
        DESCRIPTION
                      	"User defined high alarm threshold of rx power of sfp port"
        ::= { sfpThresholdUserInputEntry 18 }

        sfpRxPowerHighWarnThresh OBJECT-TYPE
        SYNTAX  DisplayString
        MAX-ACCESS  read-write
        STATUS  current 
        DESCRIPTION
                      	"User defined high warning threshold of rx power of sfp port"
        ::= { sfpThresholdUserInputEntry 19 }

        sfpRxPowerLowWarnThresh OBJECT-TYPE
        SYNTAX  DisplayString
        MAX-ACCESS  read-write
        STATUS  current 
        DESCRIPTION
                      	"User defined low warning threshold of rx power of sfp port"
        ::= { sfpThresholdUserInputEntry 20 }

        sfpRxPowerLowAlarmThresh OBJECT-TYPE
        SYNTAX  DisplayString
        MAX-ACCESS  read-write
        STATUS  current 
        DESCRIPTION
                      	"User defined low alarm threshold of rx power of sfp port"
        ::= { sfpThresholdUserInputEntry 21 }
                               
                                                 
---------------------------------------------------
--
--  SVI for IPv6 Setup
--
---------------------------------------------------
                                                       
    
	sviIpv6Setup	OBJECT IDENTIFIER ::={ ves1724-56fanless 124 }   
	                                       
	globalIpv6HopLimit	OBJECT-TYPE
        SYNTAX  INTEGER
        MAX-ACCESS  read-only
        STATUS  current
        DESCRIPTION
        "IPv6 Hop Limit."
        ::= { sviIpv6Setup 1 }      

	                                       
    globalIpv6IcmpErrorInterval	OBJECT-TYPE
        SYNTAX  INTEGER
        MAX-ACCESS  read-only
        STATUS  current
        DESCRIPTION
       	"ICMPv6 error rate-limit, User can specify the value of error interval to control the sending rate of error messages, and the minimum accuracy is 10 milliseconds. "
        ::= { sviIpv6Setup 2 }                
                                     
	globalIpv6IcmpBucketSize	OBJECT-TYPE
        SYNTAX  INTEGER
        MAX-ACCESS  read-only
        STATUS  current
        DESCRIPTION
        "User can specify the value of bucket size to control the number of ICMPv6 message allowed per error interval. "
        ::= { sviIpv6Setup 3 }  
                                       
     globalIpv6DefaultMgmtIfName	OBJECT-TYPE
        SYNTAX  OCTET STRING
        MAX-ACCESS  read-write
        STATUS  current
        DESCRIPTION
        "Specifies the interface name be the default management interface. 
        For example:
        The ifName = MGMT0 represents out-of-band IPv6 interface, ifName = VLAN + vid represents inband per-VLAN interfaces"
        ::= { sviIpv6Setup 4 }  
    ipv6MaxNumberOfStaticAddr OBJECT-TYPE
        SYNTAX  INTEGER
        MAX-ACCESS  read-only
        STATUS  current
        DESCRIPTION
        "The maximum number of IPv6 Static Address entries that can be created"
        ::= { sviIpv6Setup 5 }
                                                                          
--  inbandSviIpv6Table  
	
	inbandSviIpv6Setup	OBJECT IDENTIFIER ::={ sviIpv6Setup 6 }
	
    inbandSviIpv6SettingTable	OBJECT-TYPE
        SYNTAX	SEQUENCE OF InbandSviIpv6Entry
        MAX-ACCESS  not-accessible
        STATUS  current
        DESCRIPTION
                 	""
        ::= { inbandSviIpv6Setup 1 }

	inbandSviIpv6Entry OBJECT-TYPE
        SYNTAX	InbandSviIpv6Entry
        MAX-ACCESS	not-accessible
        STATUS	current
        DESCRIPTION    	"An entry in inbandSviIpv6InfoTable."
        INDEX          	{ inbandSviVid }
        ::= { inbandSviIpv6SettingTable 1 }

        InbandSviIpv6Entry ::=
	SEQUENCE {
			inbandSviVid					INTEGER,
	       	inbandSviIpv6Active				EnabledStatus,	       	
        	inbandSviIpv6AddrAutoConfig		EnabledStatus,
        	inbandSviIpv6LinkLocalAddrType	InetAddressType,
        	inbandSviIpv6DefaultLinkLocalAddr		InetAddress,    
        	inbandSviIpv6DefaultGatewayType	InetAddressType,
        	inbandSviIpv6DefaultGateway		InetAddress,  
        	inbandSviRowStatus				RowStatus
        }

        inbandSviVid OBJECT-TYPE
        SYNTAX  INTEGER
        MAX-ACCESS  read-only
        STATUS  current
        DESCRIPTION
        "IPv6 SVI Interface VID."
        ::= { inbandSviIpv6Entry 1 }

        inbandSviIpv6Active OBJECT-TYPE
        SYNTAX  EnabledStatus
        MAX-ACCESS  read-write
        STATUS  current
        DESCRIPTION
        "Enable IPv6 Active."
        ::= { inbandSviIpv6Entry 2 }

        inbandSviIpv6AddrAutoConfig OBJECT-TYPE
        SYNTAX  EnabledStatus
        MAX-ACCESS  read-write
        STATUS  current
        DESCRIPTION
        "Enable Stateless Address Autoconfiguration Active."
        ::= { inbandSviIpv6Entry 3 }

        inbandSviIpv6LinkLocalAddrType OBJECT-TYPE
        SYNTAX  InetAddressType
        MAX-ACCESS  read-only
        STATUS  current
        DESCRIPTION
        "IPv6 Link Local Address Type."
        ::= { inbandSviIpv6Entry 4 }

        inbandSviIpv6DefaultLinkLocalAddr OBJECT-TYPE
        SYNTAX  InetAddress
        MAX-ACCESS  read-only
        STATUS  current
        DESCRIPTION
        "IPv6 Link Local Address."
        ::= { inbandSviIpv6Entry 5 }        
        
        inbandSviIpv6DefaultGatewayType OBJECT-TYPE
        SYNTAX  InetAddressType
        MAX-ACCESS  read-only
        STATUS  current
        DESCRIPTION
        "IPv6 Default Gateway Type." 
        ::= { inbandSviIpv6Entry 6 }

        inbandSviIpv6DefaultGateway OBJECT-TYPE
        SYNTAX  InetAddress
        MAX-ACCESS  read-write
        STATUS  current
        DESCRIPTION
        "IPv6 Default Gateway."
        ::= { inbandSviIpv6Entry 7 }
    
        inbandSviRowStatus OBJECT-TYPE
        SYNTAX  RowStatus
        MAX-ACCESS  read-create
        STATUS  current
        DESCRIPTION
                      	""
        ::= { inbandSviIpv6Entry 8 }   
        
--  inband IPV6 Static Address Table
        inbandIpv6StaticAddrTable	OBJECT-TYPE
        SYNTAX	SEQUENCE OF InbandIPv6StaticAddrEntry
        MAX-ACCESS  not-accessible
        STATUS  current
        DESCRIPTION
                 	""
        ::= { inbandSviIpv6Setup 2 }

		inbandIpv6StaticAddrEntry OBJECT-TYPE
        SYNTAX	InbandIPv6StaticAddrEntry
        MAX-ACCESS	not-accessible
        STATUS	current
        DESCRIPTION    	"An entry in inbandIpv6StaticAddrTable."
        INDEX          {
            inbandIpv6StaticAddrVid,
        	inbandIpv6StaticAddrAddrType,
        	inbandIpv6StaticAddrAddr,
        	inbandIpv6StaticAddrAddrPrefixLength,
        	inbandIpv6StaticAddrEUI64
          }
        ::= { inbandIpv6StaticAddrTable 1 }

        InbandIPv6StaticAddrEntry ::=
	SEQUENCE {
    		inbandIpv6StaticAddrVid					INTEGER,
            inbandIpv6StaticAddrAddrType    		InetAddressType, 
            inbandIpv6StaticAddrAddr       			InetAddress,   
            inbandIpv6StaticAddrAddrPrefixLength    INTEGER,
            inbandIpv6StaticAddrEUI64            	EnabledStatus,  
            inbandIpv6StaticAddrAddrStatus       	INTEGER,
            inbandIpv6StaticAddrRowStatus          	RowStatus           
          }

        inbandIpv6StaticAddrVid OBJECT-TYPE
        SYNTAX  INTEGER
        MAX-ACCESS  read-only
        STATUS  current
        DESCRIPTION
        "IPv6 Static Address Interface VID." 
        ::= { inbandIpv6StaticAddrEntry 1 }

        inbandIpv6StaticAddrAddrType OBJECT-TYPE
        SYNTAX  InetAddressType
        MAX-ACCESS  read-only
        STATUS  current
        DESCRIPTION
        "The address type of ipAddressAddr."
        ::= { inbandIpv6StaticAddrEntry 2 }

        inbandIpv6StaticAddrAddr OBJECT-TYPE
        SYNTAX  InetAddress
        MAX-ACCESS  read-only
        STATUS  current
        DESCRIPTION
         "IPv6 Static Address."
        ::= { inbandIpv6StaticAddrEntry 3 }

        inbandIpv6StaticAddrAddrPrefixLength OBJECT-TYPE
        SYNTAX  INTEGER
        MAX-ACCESS  read-only
        STATUS  current
        DESCRIPTION
        "IPv6 Static Address Prefix Length."
        ::= { inbandIpv6StaticAddrEntry 4 }
                             
        inbandIpv6StaticAddrEUI64 OBJECT-TYPE
        SYNTAX  EnabledStatus
        MAX-ACCESS  read-only
        STATUS  current
        DESCRIPTION
        "Enable EUI-64 Active."
        ::= { inbandIpv6StaticAddrEntry 5 }
        
        inbandIpv6StaticAddrAddrStatus OBJECT-TYPE
        SYNTAX  INTEGER{
 	        preferred(1),
	        deprecated(2),
	        invalid(3),
            inaccessible(4),
            unknown(5),
            tentative(6),
            duplicate(7)
        }
        MAX-ACCESS  read-only
        STATUS  current
        DESCRIPTION
        "The Status of IPv6 Static Address."
        ::= { inbandIpv6StaticAddrEntry 6 }
        
        inbandIpv6StaticAddrRowStatus OBJECT-TYPE
        SYNTAX  RowStatus
        MAX-ACCESS  read-create
        STATUS  current
        DESCRIPTION
        "IPv6 Static Address rowstatus."
        ::= { inbandIpv6StaticAddrEntry 7 }                  
        
                                                       
  -- SVI for inband IPv6 neighbor cache                                                       
  	inbandIpv6NeighborCacheSetup	OBJECT IDENTIFIER ::={ sviIpv6Setup 7}
    
    inbandIpv6NeighborCacheTable	OBJECT-TYPE
        SYNTAX	SEQUENCE OF InbandIpv6NeighborCacheEntry
        MAX-ACCESS  not-accessible
        STATUS  current
        DESCRIPTION
                 	""
        ::= { inbandIpv6NeighborCacheSetup 1 }

	inbandIpv6NeighborCacheEntry OBJECT-TYPE
        SYNTAX	InbandIpv6NeighborCacheEntry
        MAX-ACCESS	not-accessible
        STATUS	current
        DESCRIPTION    	"An entry in ipv6NeighborCacheTable."
        INDEX          	{ inbandIpv6NeighborCacheVid, inbandIpv6NeighborCacheIpv6Addr, inbandIpv6NeighborCacheMACAddr}
        ::= { inbandIpv6NeighborCacheTable 1 }

        InbandIpv6NeighborCacheEntry ::=
	SEQUENCE {	       
	       	inbandIpv6NeighborCacheVid		INTEGER,
        	inbandIpv6NeighborCacheIpv6Addr		InetAddress,        	
        	inbandIpv6NeighborCacheMACAddr		MacAddress,     
			inbandIpv6NeighborCacheState       	INTEGER,
			inbandIpv6NeighborCacheType			INTEGER,	        
        	inbandIpv6NeighborCacheRowStatus	RowStatus
        }

        inbandIpv6NeighborCacheVid OBJECT-TYPE
        SYNTAX  INTEGER
        MAX-ACCESS  read-only
        STATUS  current
        DESCRIPTION
        	"Show inband IPv6 VID"
        ::= { inbandIpv6NeighborCacheEntry 1 }

        inbandIpv6NeighborCacheIpv6Addr OBJECT-TYPE
        SYNTAX  InetAddress
        MAX-ACCESS  read-only
        STATUS  current
        DESCRIPTION
        	"Show IPv6 neighbor IPv6 Address"
        ::= { inbandIpv6NeighborCacheEntry 2 }

        inbandIpv6NeighborCacheMACAddr OBJECT-TYPE
        SYNTAX  MacAddress
        MAX-ACCESS  read-only
        STATUS  current
        DESCRIPTION      
        	"Show IPv6 neighbor MAC Address"
        ::= { inbandIpv6NeighborCacheEntry 3 }
        
        inbandIpv6NeighborCacheState OBJECT-TYPE     
        SYNTAX  INTEGER{
 	        invalid(1),
	        incomplete(2),
	        reachable(3),
            stable(4),
            delay(5),
            probe(6),
            unknown(7)
        }                
        MAX-ACCESS  read-only  
      	STATUS  current     
        DESCRIPTION
        	"Show IPv6 neighbor connection state"
        ::= { inbandIpv6NeighborCacheEntry 4 }       
                                               
		inbandIpv6NeighborCacheType OBJECT-TYPE
        SYNTAX  INTEGER{
 	        local(1),
	        dynamic(2),
	        static(3),
            other(4)            
        }       
        MAX-ACCESS  read-only
        STATUS  current
        DESCRIPTION
        	"Show IPv6 neighbor connection type"
        ::= { inbandIpv6NeighborCacheEntry 5 }       
                                                       
        inbandIpv6NeighborCacheRowStatus OBJECT-TYPE
        SYNTAX  RowStatus
        MAX-ACCESS  read-create
        STATUS  current
        DESCRIPTION
                      	""
        ::= { inbandIpv6NeighborCacheEntry 6 }                                                        

--dhcp6ClientRestartTable
		dhcp6ClientRestartTable	OBJECT-TYPE
		SYNTAX 	SEQUENCE OF dhcp6ClientRestartEntry
		ACCESS	not-accessible
		STATUS	mandatory
		DESCRIPTION
					""
		::= { inbandSviIpv6Setup 3 }
		
		dhcp6ClientRestartEntry	OBJECT-TYPE
		SYNTAX	dhcp6ClientRestartEntry
		ACCESS	not-accessible
		STATUS	mandatory
		DESCRIPTION		"An entry in dhcp6ClientRestartTable."
		INDEX	{ dhcp6ClientIfIndex }
		::= { dhcp6ClientRestartTable 1}
		
		dhcp6ClientRestartEntry ::=
			SEQUENCE {
				dhcp6ClientVid 		INTEGER,
				dhcp6ClientRestart		EnabledStatus
			}
	
		dhcp6ClientVid	OBJECT-TYPE
		SYNTAX	INTEGER
		ACCESS	read-only
		STATUS	mandatory
		DESCRIPTION
					""
		::= { dhcp6ClientRestartEntry 1}
		
		dhcp6ClientRestart	OBJECT-TYPE
		SYNTAX	EnabledStatus
		ACCESS	read-write
		STATUS	mandatory
		DESCRIPTION
					""
		::= { dhcp6ClientRestartEntry 2}
		
--dhcp6ClientTable
		dhcp6ClientTable	OBJECT-TYPE
		SYNTAX 	SEQUENCE OF dhcp6ClientEntry
		ACCESS	not-accessible
		STATUS	mandatory
		DESCRIPTION
					""
		::= { inbandSviIpv6Setup 4 }
		
		dhcp6ClientEntry	OBJECT-TYPE
		SYNTAX	dhcp6ClientEntry
		ACCESS	not-accessible
		STATUS	mandatory
		DESCRIPTION		"An entry in dhcp6ClientTable."
		INDEX	{ dhcp6ClientIfIndex }
		::= { dhcp6ClientTable 1}
		
		dhcp6ClientEntry ::=
			SEQUENCE {
				dhcp6ClientVid						INTEGER,
				dhcp6ClientIATypeEnable					INTEGER,
				dhcp6ClientIATypeRapidCommitEnable 		INTEGER,
				dhcp6ClientOptionDNSEnable				EnabledStatus,
				dhcp6ClientOptionDomainListEnable		EnabledStatus,
				dhcp6ClientInformationRefreshMinimum	INTEGER
			}
	
		dhcp6ClientVid	OBJECT-TYPE
		SYNTAX	INTEGER
		ACCESS	read-only
		STATUS	mandatory
		DESCRIPTION
					""
		::= { dhcp6ClientEntry 1}
		
		dhcp6ClientIATypeEnable	OBJECT-TYPE
		SYNTAX	INTEGER
		ACCESS	read-write
		STATUS	mandatory
		DESCRIPTION
					""
		::= { dhcp6ClientEntry 2 }
		
		dhcp6ClientIATypeRapidCommitEnable	OBJECT-TYPE
		SYNTAX	INTEGER
		ACCESS	read-write
		STATUS	mandatory
		DESCRIPTION
					""
		::= { dhcp6ClientEntry 3 }
		
		dhcp6ClientOptionDNSEnable	OBJECT-TYPE
		SYNTAX	EnabledStatus
		ACCESS	read-write
		STATUS	mandatory
		DESCRIPTION
					""
		::= { dhcp6ClientEntry 4 }
		
		dhcp6ClientOptionDomainListEnable	OBJECT-TYPE
		SYNTAX	EnabledStatus
		ACCESS	read-write
		STATUS	mandatory
		DESCRIPTION
					""
		::= { dhcp6ClientEntry 5}
		
		dhcp6ClientInformationRefreshMinimum	OBJECT-TYPE
		SYNTAX	INTEGER
		ACCESS	read-write
		STATUS	mandatory
		DESCRIPTION
					""
		::= { dhcp6ClientEntry 6}
		
		
		
                                                       
--  outbandSviIpv6Table  
	
	outbandSviIpv6Setup	OBJECT IDENTIFIER ::={ sviIpv6Setup 8 }
	
    outbandSviIpv6SettingTable	OBJECT-TYPE
        SYNTAX	SEQUENCE OF OutbandSviIpv6Entry
        MAX-ACCESS  not-accessible
        STATUS  current
        DESCRIPTION
                 	""
        ::= { outbandSviIpv6Setup 1 }

	outbandSviIpv6Entry OBJECT-TYPE
        SYNTAX	OutbandSviIpv6Entry
        MAX-ACCESS	not-accessible
        STATUS	current
        DESCRIPTION    	"An entry in outbandSviIpv6InfoTable."
        INDEX          	{ outbandEntrySviIfNum }
        ::= { outbandSviIpv6SettingTable 1 }

        OutbandSviIpv6Entry ::=
	SEQUENCE {
			outbandEntrySviIfNum					INTEGER,
	       	outbandSviIpv6Active					EnabledStatus,	       	
        	outbandSviIpv6AddrAutoConfig			EnabledStatus,
        	outbandSviIpv6LinkLocalAddrType			InetAddressType,
        	outbandSviIpv6DefaultLinkLocalAddr		InetAddress,    
        	outbandSviIpv6DefaultGatewayType		InetAddressType,
        	outbandSviIpv6DefaultGateway			InetAddress,  
        	outbandSviRowStatus						RowStatus
        }

        outbandEntrySviIfNum OBJECT-TYPE
        SYNTAX  INTEGER
        MAX-ACCESS  not-accessible
        STATUS  current
        DESCRIPTION
        "Outband IPv6 SVI Interface Number."
        ::= { outbandSviIpv6Entry 1 }

        outbandSviIpv6Active OBJECT-TYPE
        SYNTAX  EnabledStatus
        MAX-ACCESS  read-write
        STATUS  current
        DESCRIPTION
        "Enable IPv6 Active."
        ::= { outbandSviIpv6Entry 2 }

        outbandSviIpv6AddrAutoConfig OBJECT-TYPE
        SYNTAX  EnabledStatus
        MAX-ACCESS  read-write
        STATUS  current
        DESCRIPTION
        "Enable Stateless Address Autoconfiguration Active."
        ::= { outbandSviIpv6Entry 3 }

        outbandSviIpv6LinkLocalAddrType OBJECT-TYPE
        SYNTAX  InetAddressType
        MAX-ACCESS  read-only
        STATUS  current
        DESCRIPTION
        "IPv6 Link Local Address Type."
        ::= { outbandSviIpv6Entry 4 }

        outbandSviIpv6DefaultLinkLocalAddr OBJECT-TYPE
        SYNTAX  InetAddress
        MAX-ACCESS  read-only
        STATUS  current
        DESCRIPTION
        "IPv6 Link Local Address."
        ::= { outbandSviIpv6Entry 5 }        
                              
        outbandSviIpv6DefaultGatewayType OBJECT-TYPE
        SYNTAX  InetAddressType
        MAX-ACCESS  read-only
        STATUS  current
        DESCRIPTION
        "IPv6 Default Gateway Type." 
        ::= { outbandSviIpv6Entry 6 }

        outbandSviIpv6DefaultGateway OBJECT-TYPE
        SYNTAX  InetAddress
        MAX-ACCESS  read-write
        STATUS  current
        DESCRIPTION
        "IPv6 Default Gateway."
        ::= { outbandSviIpv6Entry 7 }
    
        outbandSviRowStatus OBJECT-TYPE
        SYNTAX  RowStatus
        MAX-ACCESS  read-create
        STATUS  current
        DESCRIPTION
                      	""
        ::= { outbandSviIpv6Entry 8 }   
        
--  outband IPV6 Static Address Table
        outbandIpv6StaticAddrTable	OBJECT-TYPE
        SYNTAX	SEQUENCE OF OutbandIPv6StaticAddrEntry
        MAX-ACCESS  not-accessible
        STATUS  current
        DESCRIPTION
                 	""
        ::= { outbandSviIpv6Setup 2 }

		outbandIpv6StaticAddrEntry OBJECT-TYPE
        SYNTAX	OutbandIPv6StaticAddrEntry
        MAX-ACCESS	not-accessible
        STATUS	current
        DESCRIPTION    	"An entry in outbandIpv6StaticAddrTable."
        INDEX          {
            outbandIpv6StaticAddrIfNum,
        	outbandIpv6StaticAddrAddrType,
        	outbandIpv6StaticAddrAddr,
        	outbandIpv6StaticAddrAddrPrefixLength,
        	outbandIpv6StaticAddrEUI64
          }
        ::= { outbandIpv6StaticAddrTable 1 }

        OutbandIPv6StaticAddrEntry ::=
	SEQUENCE {
    		outbandIpv6StaticAddrIfNum					INTEGER,
            outbandIpv6StaticAddrAddrType    		InetAddressType, 
            outbandIpv6StaticAddrAddr       			InetAddress,   
            outbandIpv6StaticAddrAddrPrefixLength    INTEGER,
            outbandIpv6StaticAddrEUI64            	EnabledStatus,  
            outbandIpv6StaticAddrAddrStatus       	INTEGER,
            outbandIpv6StaticAddrRowStatus          	RowStatus           
          }

        outbandIpv6StaticAddrIfNum OBJECT-TYPE
        SYNTAX  INTEGER
        MAX-ACCESS  not-accessible
        STATUS  current
        DESCRIPTION
        "Outband IPv6 Static Address Interface Number." 
        ::= { outbandIpv6StaticAddrEntry 1 }

        outbandIpv6StaticAddrAddrType OBJECT-TYPE
        SYNTAX  InetAddressType
        MAX-ACCESS  read-only
        STATUS  current
        DESCRIPTION
        "The address type of ipAddressAddr."
        ::= { outbandIpv6StaticAddrEntry 2 }

        outbandIpv6StaticAddrAddr OBJECT-TYPE
        SYNTAX  InetAddress
        MAX-ACCESS  read-only
        STATUS  current
        DESCRIPTION
         "IPv6 Static Address."
        ::= { outbandIpv6StaticAddrEntry 3 }

        outbandIpv6StaticAddrAddrPrefixLength OBJECT-TYPE
        SYNTAX  INTEGER
        MAX-ACCESS  read-only
        STATUS  current
        DESCRIPTION
        "IPv6 Static Address Prefix Length."
        ::= { outbandIpv6StaticAddrEntry 4 }
                             
        outbandIpv6StaticAddrEUI64 OBJECT-TYPE
        SYNTAX  EnabledStatus
        MAX-ACCESS  read-only
        STATUS  current
        DESCRIPTION
        "Enable EUI-64 Active."
        ::= { outbandIpv6StaticAddrEntry 5 }
        
        outbandIpv6StaticAddrAddrStatus OBJECT-TYPE
        SYNTAX  INTEGER{
 	        preferred(1),
	        deprecated(2),
	        invalid(3),
            inaccessible(4),
            unknown(5),
            tentative(6),
            duplicate(7)
        }
        MAX-ACCESS  read-only
        STATUS  current
        DESCRIPTION
        "The Status of IPv6 Static Address."
        ::= { outbandIpv6StaticAddrEntry 6 }
        
        outbandIpv6StaticAddrRowStatus OBJECT-TYPE
        SYNTAX  RowStatus
        MAX-ACCESS  read-create
        STATUS  current
        DESCRIPTION
        "IPv6 Static Address rowstatus."
        ::= { outbandIpv6StaticAddrEntry 7 }                  
      

-- SVI for outband IPv6 neighbor cache                                                       
    outbandIpv6NeighborCacheSetup	OBJECT IDENTIFIER ::={ sviIpv6Setup 9}
    
    outbandIpv6NeighborCacheTable	OBJECT-TYPE
        SYNTAX	SEQUENCE OF OutbandIpv6NeighborCacheEntry
        MAX-ACCESS  not-accessible
        STATUS  current
        DESCRIPTION
                 	""
        ::= { outbandIpv6NeighborCacheSetup 1 }

	outbandIpv6NeighborCacheEntry OBJECT-TYPE
        SYNTAX	OutbandIpv6NeighborCacheEntry
        MAX-ACCESS	not-accessible
        STATUS	current
        DESCRIPTION    	"An entry in ipv6NeighborCacheTable."
        INDEX          	{ outbandIpv6NeighborCacheIfNum, outbandIpv6NeighborCacheIpv6Addr, outbandIpv6NeighborCacheMACAddr}
        ::= { outbandIpv6NeighborCacheTable 1 }

        OutbandIpv6NeighborCacheEntry ::=
	SEQUENCE {	       
	       	outbandIpv6NeighborCacheIfNum			INTEGER,
        	outbandIpv6NeighborCacheIpv6Addr		InetAddress,        	
        	outbandIpv6NeighborCacheMACAddr		MacAddress,     
			outbandIpv6NeighborCacheState       INTEGER,
			outbandIpv6NeighborCacheType		INTEGER,	        
        	outbandIpv6NeighborCacheRowStatus	RowStatus
        }

        outbandIpv6NeighborCacheIfNum OBJECT-TYPE
        SYNTAX  INTEGER
        MAX-ACCESS  read-only
        STATUS  current
        DESCRIPTION
        	"Show outband IPv6 interface number"
        ::= { outbandIpv6NeighborCacheEntry 1 }

        outbandIpv6NeighborCacheIpv6Addr OBJECT-TYPE
        SYNTAX  InetAddress
        MAX-ACCESS  read-only
        STATUS  current
        DESCRIPTION
        	"Show IPv6 neighbor IPv6 Address"
        ::= { outbandIpv6NeighborCacheEntry 2 }

        outbandIpv6NeighborCacheMACAddr OBJECT-TYPE
        SYNTAX  MacAddress
        MAX-ACCESS  read-only
        STATUS  current
        DESCRIPTION      
        	"Show IPv6 neighbor MAC Address"
        ::= { outbandIpv6NeighborCacheEntry 3 }
        
        outbandIpv6NeighborCacheState OBJECT-TYPE     
        SYNTAX  INTEGER{
 	        invalid(1),
	        incomplete(2),
	        reachable(3),
            stable(4),
            delay(5),
            probe(6),
            unknown(7)
        }       
        MAX-ACCESS  read-only  
        STATUS  current
        DESCRIPTION
        	"Show IPv6 neighbor connection state"
        ::= { outbandIpv6NeighborCacheEntry 4 }       
                                               
		outbandIpv6NeighborCacheType OBJECT-TYPE
	    SYNTAX  INTEGER{
 	        local(1),
	        dynamic(2),
	        static(3),
            other(4)            
        }       
        MAX-ACCESS  read-only
        STATUS  current
        DESCRIPTION
        	"Show IPv6 neighbor connection type"
        ::= { outbandIpv6NeighborCacheEntry 5 }       
                                                       
        outbandIpv6NeighborCacheRowStatus OBJECT-TYPE
        SYNTAX  RowStatus
        MAX-ACCESS  read-create
        STATUS  current
        DESCRIPTION
                      	""
        ::= { outbandIpv6NeighborCacheEntry 6 }                                                                                  
                                                        
                                                       
-- ******************************************************************
-- *
-- 125.NDP mib
-- *
-- ****************************************************************** 
	ndp OBJECT IDENTIFIER ::= { ves1724-56fanless 125 }   
     
-- * 
-- * Inband NDP Table
-- *
	inbandNdpTable OBJECT-TYPE
	 	      SYNTAX      SEQUENCE OF InbandNDPEntry
	          MAX-ACCESS  not-accessible
	          STATUS      current
	          DESCRIPTION       
	            ""              
              ::= { ndp 1 }  
    
    inbandNdpEntry OBJECT-TYPE
        SYNTAX      InbandNDPEntry
        MAX-ACCESS  not-accessible
        STATUS      current
        DESCRIPTION
            "An entry in ndpTable."
        INDEX {           
        	inbandNdpVid             
        }
    ::= { inbandNdpTable 1 }

    InbandNDPEntry ::=
        SEQUENCE {       
        	inbandNdpVid					INTEGER,
            inbandNdpDADAttempts   			INTEGER, 
            inbandNdpNSInterval       		INTEGER,  
            inbandNdpReachableTime            INTEGER
      }     
        
    inbandNdpVid OBJECT-TYPE
        SYNTAX      INTEGER
        MAX-ACCESS  read-only
       	STATUS      current
        DESCRIPTION
         "NDP Interface Vid."
    ::= { inbandNdpEntry 1 }
                           
    inbandNdpDADAttempts OBJECT-TYPE
        SYNTAX      INTEGER
        MAX-ACCESS  read-write
       	STATUS      current
        DESCRIPTION
         "NDP DAD Attempts."
    ::= { inbandNdpEntry 2 }
 
     inbandNdpNSInterval OBJECT-TYPE
        SYNTAX      INTEGER
        MAX-ACCESS  read-write
       	STATUS      current
        DESCRIPTION
         "NDP NS Interval."
    ::= { inbandNdpEntry 3 }
                 
     inbandNdpReachableTime OBJECT-TYPE
        SYNTAX      INTEGER
        MAX-ACCESS  read-write
       	STATUS      current
        DESCRIPTION
         "NDP Reachable Time."
    ::= { inbandNdpEntry 4 }

      
-- * 
-- * Outband NDP Table
-- *
	outbandNdpTable OBJECT-TYPE
	 	      SYNTAX      SEQUENCE OF OutbandNDPEntry
	          MAX-ACCESS  not-accessible
	          STATUS      current
	          DESCRIPTION       
	            ""              
              ::= { ndp 2 }  
    
    outbandNdpEntry OBJECT-TYPE
        SYNTAX      OutbandNDPEntry
        MAX-ACCESS  not-accessible
        STATUS      current
        DESCRIPTION
            "An entry in ndpTable."
        INDEX {           
        	outbandNdpIfNum             
        }
    ::= { outbandNdpTable 1 }

    OutbandNDPEntry ::=
        SEQUENCE {       
        	outbandNdpIfNum					INTEGER,
            outbandNdpDADAttempts   			INTEGER, 
            outbandNdpNSInterval       		INTEGER,  
            outbandNdpReachableTime            INTEGER
      }     
        
    outbandNdpIfNum OBJECT-TYPE
        SYNTAX      INTEGER
        MAX-ACCESS  not-accessible
       	STATUS      current
        DESCRIPTION
         "NDP Outband Interface Num."
    ::= { outbandNdpEntry 1 }
                           
    outbandNdpDADAttempts OBJECT-TYPE
        SYNTAX      INTEGER
        MAX-ACCESS  read-write
       	STATUS      current
        DESCRIPTION
         "NDP DAD Attempts."
    ::= { outbandNdpEntry 2 }
 
    outbandNdpNSInterval OBJECT-TYPE
        SYNTAX      INTEGER
        MAX-ACCESS  read-write
       	STATUS      current
        DESCRIPTION
         "NDP NS Interval."
    ::= { outbandNdpEntry 3 }
                 
     outbandNdpReachableTime OBJECT-TYPE
        SYNTAX      INTEGER
        MAX-ACCESS  read-write
       	STATUS      current
        DESCRIPTION
         "NDP Reachable Time."
    ::= { outbandNdpEntry 4 }
                             
    
--	Path MTU Discovery
        pathMtuDiscovery	OBJECT IDENTIFIER ::= { ves1724-56fanless 126 }  

	--	pathMtuTable
		pathMtuTable	OBJECT-TYPE
        SYNTAX	SEQUENCE OF PathMtuEntry
        MAX-ACCESS  not-accessible
        STATUS  current
        DESCRIPTION	"The table keeps track of the inforamtion of each Packet Too Big error message and sets a timer for aging each entry."
        ::= { pathMtuDiscovery 1 }    

		pathMtuEntry OBJECT-TYPE
        SYNTAX	PathMtuEntry
        MAX-ACCESS	not-accessible
        STATUS	current
        DESCRIPTION    	"An entry in the mldSnoopingProxyVlanTable."
        INDEX          	
        { 
        	pathMtuDiscoveryDestinationAddressType,
        	pathMtuDiscoveryDestinationAddress 
        }
        ::= { pathMtuTable 1 }

        PathMtuEntry ::=
		SEQUENCE 
		{
        	pathMtuDiscoveryDestinationAddressType	InetAddressType,
        	pathMtuDiscoveryDestinationAddress	InetAddress,
        	pathMtuDiscoveryMTU	INTEGER,
        	pathMtuDiscoveryExpiredTime	Gauge32 
        }

        pathMtuDiscoveryDestinationAddressType OBJECT-TYPE
        SYNTAX  InetAddressType
        MAX-ACCESS  not-accessible
        STATUS  current
        DESCRIPTION	"The destination address type in the message body of ICMPv6 Packet Too Big error message."
        ::= { pathMtuEntry 1 }     
 
        pathMtuDiscoveryDestinationAddress OBJECT-TYPE
        SYNTAX  InetAddress
        MAX-ACCESS  not-accessible
        STATUS  current
        DESCRIPTION	"The destination address in the message body of ICMPv6 Packet Too Big error message."
        ::= { pathMtuEntry 2 }  

        pathMtuDiscoveryMTU OBJECT-TYPE
        SYNTAX  INTEGER
        MAX-ACCESS  read-only
        STATUS  current
        DESCRIPTION	"The MTU in the ICMPv6 Packet Too Big error message."
        ::= { pathMtuEntry 3 }         

        pathMtuDiscoveryExpiredTime OBJECT-TYPE
        SYNTAX  Gauge32
        MAX-ACCESS  read-only
        STATUS  current
        DESCRIPTION	"The aging time of each entry in the path MTU discovery table."
        ::= { pathMtuEntry 4 }      
                                                  
------------------------------------------------------                             

--	DHCPv6 Relay LDRA

------------------------------------------------------
        dhcpv6Relay	OBJECT IDENTIFIER ::= { ves1724-56fanless 127 }  

	--	dhcpv6LdraTable
		dhcpv6LdraTable	OBJECT-TYPE
        SYNTAX	SEQUENCE OF LdraEntry
        MAX-ACCESS  not-accessible
        STATUS  current
        DESCRIPTION	"The table keeps track of the LDRA information."
        ::= {dhcpv6Relay 1 }    

		ldraEntry OBJECT-TYPE
        SYNTAX	LdraEntry
        MAX-ACCESS	not-accessible
        STATUS	current
        DESCRIPTION    	"An entry in the LdraTable."
        INDEX          	
        { 
        	ldraVlanID
        }
        ::= { dhcpv6LdraTable 1 }

        LdraEntry ::=
		SEQUENCE 
		{
        	ldraVlanID	INTEGER,
        	ldraEnable	EnabledStatus,
        	ldraOptionInterfaceIDEnable	EnabledStatus,
        	ldraOptionInterfaceIDData	DisplayString,
        	ldraOptionRemoteIDEnable	EnabledStatus,
        	ldraOptionRemoteIDData	DisplayString,           
        	ldraClientFacingPortList	 PortList,
        	ldraNetworkFacingPortList	 PortList,
        	ldraUntrustClientPortList	 PortList,
        	ldraRowStatus	RowStatus
        }

        ldraVlanID OBJECT-TYPE
        SYNTAX  INTEGER
        MAX-ACCESS  not-accessible
        STATUS  current
        DESCRIPTION	"LDRA relay in this VLAN."
        ::= { ldraEntry 1 }     
 
        ldraEnable OBJECT-TYPE
        SYNTAX  EnabledStatus
        MAX-ACCESS  read-write
        STATUS  current
        DESCRIPTION	"Enable LDRA in this VLAN."
        ::= { ldraEntry 2 }  

        ldraOptionInterfaceIDEnable OBJECT-TYPE
        SYNTAX  EnabledStatus
        MAX-ACCESS  read-write
        STATUS  current
        DESCRIPTION	"Enable relay agent option of Interface-ID to appending to outgoing DHCP packets."
        ::= { ldraEntry 3 }         
             
        ldraOptionInterfaceIDData OBJECT-TYPE
        SYNTAX  DisplayString
        MAX-ACCESS  read-write
        STATUS  current
        DESCRIPTION	"Set relay agent option of Interface-ID to appending to outgoing DHCP packets."
        ::= { ldraEntry 4 }         
                                
        ldraOptionRemoteIDEnable OBJECT-TYPE
        SYNTAX  EnabledStatus
        MAX-ACCESS  read-write
        STATUS  current
        DESCRIPTION	"Enable relay agent option of Remote-ID to appending to outgoing DHCP packets."
        ::= { ldraEntry 5 }         
             
        ldraOptionRemoteIDData OBJECT-TYPE
        SYNTAX  DisplayString
        MAX-ACCESS  read-write
        STATUS  current
        DESCRIPTION	"Set relay agent option of Remote-ID to appending to outgoing DHCP packets."
        ::= { ldraEntry 6 }                          
        
        ldraClientFacingPortList OBJECT-TYPE
        SYNTAX  PortList
        MAX-ACCESS  read-write
        STATUS  current
        DESCRIPTION "Setup LDRA client-facing interface."
        ::= { ldraEntry 7 }

        ldraNetworkFacingPortList OBJECT-TYPE
        SYNTAX  PortList
        MAX-ACCESS  read-write
        STATUS  current
        DESCRIPTION "Setup LDRA network-facing interface."
        ::= { ldraEntry 8 }           
               
        ldraUntrustClientPortList OBJECT-TYPE
        SYNTAX  PortList
        MAX-ACCESS  read-write
        STATUS  current
        DESCRIPTION "Setup LDRA untrust client interface."
        ::= { ldraEntry 9 }

                     
        ldraRowStatus OBJECT-TYPE
        SYNTAX  RowStatus
        MAX-ACCESS  read-create
        STATUS  current
        DESCRIPTION	""
        ::= { ldraEntry 10 }                
        
--
--  dhcpv6 relay counter table
--

        dhcpv6RelayCounterTable	OBJECT-TYPE
        SYNTAX	SEQUENCE OF Dhcpv6RelayCounterEntry
        MAX-ACCESS  not-accessible
        STATUS  current
        DESCRIPTION
         "Show DHCPv6 Relay packet counter on client-facing."
        ::= { dhcpv6Relay 2 }

	dhcpv6RelayCounterEntry OBJECT-TYPE
        SYNTAX	Dhcpv6RelayCounterEntry
        MAX-ACCESS	not-accessible
        STATUS	current
        DESCRIPTION    	""
        INDEX          	{ dhcpv6RelayCounterEntryPort }
        ::= { dhcpv6RelayCounterTable 1 }

        Dhcpv6RelayCounterEntry ::=
	SEQUENCE {
        	dhcpv6RelayCounterEntryPort		INTEGER,
        	dhcpv6SolicitMsgCnt		Counter32,
        	dhcpv6AdvertiseMsgCnt		Counter32,
        	dhcpv6RequestMsgCnt		Counter32,
        	dhcpv6ConfirmMsgCnt		Counter32,
        	dhcpv6RenewMsgCnt		Counter32,
        	dhcpv6RebindMsgCnt		Counter32,
        	dhcpv6ReplyMsgCnt		Counter32,
        	dhcpv6ReleaseMsgCnt		Counter32,
        	dhcpv6DeclineMsgCnt		Counter32,  
        	dhcpv6ReconfigureMsgCnt		Counter32,  
        	dhcpv6InfoReqMsgCnt		Counter32,  
        	dhcpv6RelayForwMsgCnt		Counter32,
        	dhcpv6RelayReplyMsgCnt		Counter32
        }

        dhcpv6RelayCounterEntryPort OBJECT-TYPE
        SYNTAX  INTEGER
        MAX-ACCESS  read-only
        STATUS  current
        DESCRIPTION
                      	""
        ::= { dhcpv6RelayCounterEntry 1 }

        dhcpv6SolicitMsgCnt OBJECT-TYPE
        SYNTAX  Counter32 
        MAX-ACCESS  read-only
        STATUS  current
        DESCRIPTION                      
        "The total number of DHCPv6 Solicit messages on this interface."
        ::= { dhcpv6RelayCounterEntry 2 }
                                                                 
        dhcpv6AdvertiseMsgCnt OBJECT-TYPE
        SYNTAX  Counter32 
        MAX-ACCESS  read-only
        STATUS  current
        DESCRIPTION
        "The total number of DHCPv6 Advertise messages on this interface."
        ::= { dhcpv6RelayCounterEntry 3 }
        
        dhcpv6RequestMsgCnt OBJECT-TYPE
        SYNTAX  Counter32 
        MAX-ACCESS  read-only
        STATUS  current
        DESCRIPTION
        "The total number of DHCPv6 Request messages on this interface."
        ::= { dhcpv6RelayCounterEntry 4 }
                                                                 
        dhcpv6ConfirmMsgCnt OBJECT-TYPE
        SYNTAX  Counter32 
        MAX-ACCESS  read-only
        STATUS  current
        DESCRIPTION
        "The total number of DHCPv6 Confirm messages on this interface."
        ::= { dhcpv6RelayCounterEntry 5 }             
        
        dhcpv6RenewMsgCnt OBJECT-TYPE
        SYNTAX  Counter32 
        MAX-ACCESS  read-only
        STATUS  current
        DESCRIPTION
        "The total number of DHCPv6 Renew messages on this interface."
        ::= { dhcpv6RelayCounterEntry 6 }
                                                                 
        dhcpv6RebindMsgCnt OBJECT-TYPE
        SYNTAX  Counter32 
        MAX-ACCESS  read-only
        STATUS  current
        DESCRIPTION
        "The total number of DHCPv6 Rebind messages on this interface."
        ::= { dhcpv6RelayCounterEntry 7 }     
        
        dhcpv6ReplyMsgCnt OBJECT-TYPE
        SYNTAX  Counter32 
        MAX-ACCESS  read-only
        STATUS  current
        DESCRIPTION
        "The total number of DHCPv6 Reply messages on this interface."
        ::= { dhcpv6RelayCounterEntry 8 }
                                                                 
        dhcpv6ReleaseMsgCnt OBJECT-TYPE
        SYNTAX  Counter32 
        MAX-ACCESS  read-only
        STATUS  current
        DESCRIPTION
        "The total number of DHCPv6 Release messages on this interface."
        ::= { dhcpv6RelayCounterEntry 9 }           
        
        dhcpv6DeclineMsgCnt OBJECT-TYPE
        SYNTAX  Counter32 
        MAX-ACCESS  read-only
        STATUS  current
        DESCRIPTION
        "The total number of DHCPv6 Decline messages on this interface."
        ::= { dhcpv6RelayCounterEntry 10 }     
        
        dhcpv6ReconfigureMsgCnt OBJECT-TYPE
        SYNTAX  Counter32 
        MAX-ACCESS  read-only
        STATUS  current
        DESCRIPTION
        "The total number of DHCPv6 Reconfigure messages on this interface."
        ::= { dhcpv6RelayCounterEntry 11 }
                                                                 
        dhcpv6InfoReqMsgCnt OBJECT-TYPE
        SYNTAX  Counter32 
        MAX-ACCESS  read-only
        STATUS  current
        DESCRIPTION
        "The total number of DHCPv6 Information Request messages on this interface."
        ::= { dhcpv6RelayCounterEntry 12 }

        dhcpv6RelayForwMsgCnt OBJECT-TYPE
        SYNTAX  Counter32 
        MAX-ACCESS  read-only
        STATUS  current
        DESCRIPTION
        "The total number of DHCPv6 Relay-Forward messages on this interface."
        ::= { dhcpv6RelayCounterEntry 13 }
                                                                 
        dhcpv6RelayReplyMsgCnt OBJECT-TYPE
        SYNTAX  Counter32 
        MAX-ACCESS  read-only
        STATUS  current
        DESCRIPTION
        "The total number of DHCPv6 Relay-Reply Request messages on this interface."
        ::= { dhcpv6RelayCounterEntry 14 }
                                                                 
-- dhcp6RelayTable
		dhcp6RelayTable	OBJECT-TYPE
		SYNTAX 	SEQUENCE OF dhcp6RelayEntry
		ACCESS	not-accessible
		STATUS	mandatory
		DESCRIPTION
					""
		::= { dhcpv6Relay 3 }
		
		dhcp6RelayEntry	OBJECT-TYPE
		SYNTAX	dhcp6RelayEntry
		ACCESS	not-accessible
		STATUS	mandatory
		DESCRIPTION		"An entry in dhcp6RelayTable."
		INDEX	{ dhcp6RelayVlanID }
		::= { dhcp6RelayTable 1}
		
		dhcp6RelayEntry ::=
			SEQUENCE {
				dhcp6RelayVlanID 					INTEGER,
				dhcp6RelayHelperAddress 			InetAddress,
				dhcp6RelayHelperAddressType			InetAddressType,
				dhcp6RelayOptionInterfaceIDEnable	EnabledStatus,
				dhcp6RelayOptionRemoteIDData		DisplayString,
				dhcp6RelayEntryRowStatus			RowStatus
			}
		
		dhcp6RelayVlanID	OBJECT-TYPE
		SYNTAX	INTEGER
		ACCESS	read-only
		STATUS	mandatory
		DESCRIPTION
					""
		::= { dhcp6RelayEntry 1 }
		
		dhcp6RelayHelperAddress	OBJECT-TYPE
		SYNTAX	InetAddress
		ACCESS	read-write
		STATUS	mandatory
		DESCRIPTION
					""
		::= { dhcp6RelayEntry 2}
		
		dhcp6RelayHelperAddressType OBJECT-TYPE
		SYNTAX	InetAddressType
		ACCESS	read-write
		STATUS	mandatory
		DESCRIPTION
					""
		::= { dhcp6RelayEntry 3}
		
		dhcp6RelayOptionInterfaceIDEnable	OBJECT-TYPE
		SYNTAX	EnabledStatus
		ACCESS	read-write
		STATUS	mandatory
		DESCRIPTION
					""
		::= { dhcp6RelayEntry 4}
		
		dhcp6RelayOptionRemoteIDData	OBJECT-TYPE
		SYNTAX	DisplayString
		ACCESS	read-write
		STATUS	mandatory
		DESCRIPTION
					""
		::= { dhcp6RelayEntry 5}
		
		dhcp6RelayEntryRowStatus	OBJECT-TYPE
		SYNTAX	RowStatus
		ACCESS	read-create
		STATUS	mandatory
		DESCRIPTION
					""
		::= { dhcp6RelayEntry 6}                                                               
        
-- -------------------------------------------------
--
--  dhcpv6 snooping
--
-- -------------------------------------------------

	dhcpv6Snp     	OBJECT IDENTIFIER ::= { ves1724-56fanless 128 }

                                                           
                                                           
--
--  dhcpv6 snooping interface table
--

        dhcpv6SnpPortTable	OBJECT-TYPE
        SYNTAX	SEQUENCE OF Dhcpv6SnpPortEntry
        MAX-ACCESS  not-accessible
        STATUS  current
        DESCRIPTION
                 	""
        ::= { dhcpv6Snp 1 }

	dhcpv6SnpPortEntry OBJECT-TYPE
        SYNTAX	Dhcpv6SnpPortEntry
        MAX-ACCESS	not-accessible
        STATUS	current
        DESCRIPTION    	""
        INDEX          	{ dhcpv6SnpPortEntryPort }
        ::= { dhcpv6SnpPortTable 1 }

        Dhcpv6SnpPortEntry ::=
	SEQUENCE {
        	dhcpv6SnpPortEntryPort		INTEGER,
        	dhcpv6SnpPortEntryRate		INTEGER
        }

        dhcpv6SnpPortEntryPort OBJECT-TYPE
        SYNTAX  INTEGER
        MAX-ACCESS  read-only
        STATUS  current
        DESCRIPTION
                      	""
        ::= { dhcpv6SnpPortEntry 1 }

        dhcpv6SnpPortEntryRate OBJECT-TYPE
        SYNTAX  INTEGER (0..2048)
        MAX-ACCESS  read-write
        STATUS  current
        DESCRIPTION
                      	"0 means unlimited"
        ::= { dhcpv6SnpPortEntry 2 }
                                                           

-- ******************************************************************
-- *
-- 130. errdisable
-- *
-- ****************************************************************** 
	errdisable     					OBJECT IDENTIFIER ::= { ves1724-56fanless 130 }         
         

	recovery             OBJECT IDENTIFIER ::= { errdisable 1 }
	

	errdisableRecoverySetup  OBJECT IDENTIFIER ::= { recovery 1 }

        errdisableRecoveryState OBJECT-TYPE
        SYNTAX  EnabledStatus
        ACCESS  read-write
        STATUS  mandatory
        DESCRIPTION
                      ""
        ::= { errdisableRecoverySetup 1 }

	--errdisableRecoveryReasonTable
	errdisableRecoveryReasonTable OBJECT-TYPE
        SYNTAX	SEQUENCE OF ErrdisableRecoveryReasonEntry
        ACCESS  not-accessible
        STATUS  mandatory
        DESCRIPTION
                 	""
        ::= { errdisableRecoverySetup 2 }
        
	errdisableRecoveryReasonEntry OBJECT-TYPE
        SYNTAX	ErrdisableRecoveryReasonEntry
        ACCESS	not-accessible
        STATUS	mandatory
        DESCRIPTION    	""
        INDEX          	{ errdisableRecoveryReason }
        ::= { errdisableRecoveryReasonTable 1 }

        ErrdisableRecoveryReasonEntry ::=
           SEQUENCE {
        	errdisableRecoveryReason	INTEGER,
        	errdisableRecoveryReasonActive	EnabledStatus,
			errdisableRecoveryReasonInterval	INTEGER       	
           }

        errdisableRecoveryReason OBJECT-TYPE
        SYNTAX  INTEGER {
        		arp(1),
        		bpdu(2)
        }
        ACCESS  read-only
        STATUS  mandatory
        DESCRIPTION
                      	""
        ::= { errdisableRecoveryReasonEntry 1 }

        errdisableRecoveryReasonActive OBJECT-TYPE
        SYNTAX  INTEGER {
        		enabled(1),
        		disabled(2)
        }
        		
        ACCESS  read-write
        STATUS  mandatory
        DESCRIPTION
                      	""
        ::= { errdisableRecoveryReasonEntry 2 }

        errdisableRecoveryReasonInterval OBJECT-TYPE
        SYNTAX  INTEGER (30..2592000)
        ACCESS  read-write
        STATUS  mandatory
        DESCRIPTION
                      	""
        ::= { errdisableRecoveryReasonEntry 3 }

	--errdisableRecoveryIfStatusTable
	errdisableRecoveryIfStatusTable OBJECT-TYPE
        SYNTAX	SEQUENCE OF ErrdisableRecoveryIfStatusEntry
        ACCESS  not-accessible
        STATUS  mandatory
        DESCRIPTION
                 	""
        ::= { errdisableRecoverySetup 3 }
        
	errdisableRecoveryIfStatusEntry OBJECT-TYPE
        SYNTAX	ErrdisableRecoveryIfStatusEntry
        ACCESS	not-accessible
        STATUS	mandatory
        DESCRIPTION    	""
        INDEX          	{ errdisableRecoveryIfStatusReason,errdisableRecoveryIfStatusPort }
        ::= { errdisableRecoveryIfStatusTable 1 }

        ErrdisableRecoveryIfStatusEntry ::=
           SEQUENCE {
        	errdisableRecoveryIfStatusReason	INTEGER,
        	errdisableRecoveryIfStatusPort	    INTEGER,
			errdisableRecoveryIfStatusTimeToRecover	INTEGER       	
           }

        errdisableRecoveryIfStatusReason OBJECT-TYPE
        SYNTAX  INTEGER { 
        	arp(1),
        	bpdu(2)
        }
        ACCESS  read-only
        STATUS  mandatory
        DESCRIPTION
                      	""
        ::= { errdisableRecoveryIfStatusEntry 1 }

        errdisableRecoveryIfStatusPort OBJECT-TYPE
        SYNTAX  INTEGER
        ACCESS  read-only
        STATUS  mandatory
        DESCRIPTION
                      	""
        ::= { errdisableRecoveryIfStatusEntry 2 }

        errdisableRecoveryIfStatusTimeToRecover OBJECT-TYPE
        SYNTAX  INTEGER (-1..2592000)
        ACCESS  read-only
        STATUS  mandatory
        DESCRIPTION
                      	"If reason dectect is inactive, this value would be -1"
        ::= { errdisableRecoveryIfStatusEntry 3 }              

	detect             OBJECT IDENTIFIER ::= { errdisable 2 }       
	                                        

	    errdisableDetectReasonTable	OBJECT-TYPE
        SYNTAX	SEQUENCE OF  ErrdisableDetectReasonEntry
        ACCESS  not-accessible
        STATUS  mandatory
        DESCRIPTION
                 	""
        ::= { detect 1 }  	 
        
       	errdisableDetectReasonEntry OBJECT-TYPE
        SYNTAX	ErrdisableDetectReasonEntry
        ACCESS	not-accessible
        STATUS	mandatory
        DESCRIPTION    	"An entry in errdisableDetectReasonTable."
        INDEX          	{ errdisableDetectReason }
        ::= { errdisableDetectReasonTable 1 }          
        
        ErrdisableDetectReasonEntry ::=
	SEQUENCE {
        	errdisableDetectReason    INTEGER,
        	errdisableDetectReasonEnable	EnabledStatus,
        	errdisableDetectReasonMode	INTEGER
         }        
         

        errdisableDetectReason OBJECT-TYPE
        SYNTAX  INTEGER{
        	arp(1),
        	bpdu(2)
       	}
        ACCESS  read-only
        STATUS  mandatory
        DESCRIPTION
                      	""
        ::= { errdisableDetectReasonEntry 1 }
                                                    
                                                    

        errdisableDetectReasonEnable OBJECT-TYPE
        SYNTAX  EnabledStatus
        ACCESS  read-write
        STATUS  mandatory
        DESCRIPTION
                      	""
        ::= { errdisableDetectReasonEntry 2 }
                                                

        errdisableDetectReasonMode OBJECT-TYPE
        SYNTAX  INTEGER{
        	inactive-reason(2),
        	rate-limitation(3)
        }
        ACCESS  read-write
        STATUS  mandatory
        DESCRIPTION
                      	""
        ::= { errdisableDetectReasonEntry 3 }
                                                                    
	errdisableTrapInfoObject  OBJECT IDENTIFIER ::= { errdisable 3 }    

    errdisableTrapPort OBJECT-TYPE
        SYNTAX  INTEGER
        ACCESS   read-only
        STATUS  mandatory
        DESCRIPTION
                      ""             
        ::= { errdisableTrapInfoObject 1 }     

    errdisableTrapReason OBJECT-TYPE
        SYNTAX  INTEGER
        {
			arp(1),
			bpdu(2)
        }
        ACCESS  read-only
        STATUS  mandatory
        DESCRIPTION
                      ""             
        ::= { errdisableTrapInfoObject 2 }     
        

	errdisableTrapMode  OBJECT-TYPE
        SYNTAX  INTEGER
        {
        	inactive-reason(1),
        	rate-limitation(2)
        }
        ACCESS   read-only
        STATUS  mandatory
        DESCRIPTION
                      ""             
        ::= { errdisableTrapInfoObject 3 }        
        

	errdisableTrapNotifications  OBJECT IDENTIFIER ::= { errdisable 4 }         
	   
	
	     errdisableDetectTrap NOTIFICATION-TYPE
         OBJECTS {
               errdisableTrapPort,
               errdisableTrapReason,
               errdisableTrapMode
         }
         STATUS  current
         DESCRIPTION
          ""
		   
		  ::= { errdisableTrapNotifications 1 }
      
         errdisableRecoveryTrap NOTIFICATION-TYPE
         OBJECTS {
               errdisableTrapPort,
               errdisableTrapReason,
               errdisableTrapMode
         }
         STATUS  current
         DESCRIPTION
          ""
		   ::= { errdisableTrapNotifications 2 }
	                                                                  
-- ******************************************************************
-- *
-- 131. CPU protection
-- *
-- ****************************************************************** 
	cpuProtectionSetup    			OBJECT IDENTIFIER ::= { ves1724-56fanless 131 }

     cpuProtectionTable	OBJECT-TYPE
        SYNTAX	SEQUENCE OF CPUProtectionEntry
        ACCESS  not-accessible
        STATUS  mandatory
        DESCRIPTION
                 	""
        ::= { cpuProtectionSetup 1 }   
        
		cpuProtectionEntry OBJECT-TYPE
        SYNTAX	CPUProtectionEntry
        ACCESS	not-accessible
        STATUS	mandatory
        DESCRIPTION    	"An entry in CPUProtectionTable."
        INDEX          	{ cpuProtectionPort, cpuProtectionReason}
        ::= { cpuProtectionTable 1 }

        CPUProtectionEntry ::=
	SEQUENCE {
        	cpuProtectionPort          INTEGER,
        	cpuProtectionReason    	INTEGER,
        	cpuProtectionRateLimitSet 	INTEGER
          }
                
        cpuProtectionPort OBJECT-TYPE
        SYNTAX  INTEGER           
        ACCESS  read-only
        STATUS  mandatory
        DESCRIPTION
                      	"The Protected Port"
        ::= { cpuProtectionEntry 1 }      
        
        
        cpuProtectionReason OBJECT-TYPE
        SYNTAX  INTEGER{
        arp(1),
        bpdu(2)
        }
        ACCESS  read-only
        STATUS  mandatory
        DESCRIPTION
                      	"The Protected Reason"
        ::= { cpuProtectionEntry 2}    
        

        cpuProtectionRateLimitSet OBJECT-TYPE
        SYNTAX  INTEGER(0..256)
        ACCESS  read-write
        STATUS  mandatory
        DESCRIPTION
                      	"The rate limit of a reason on a port"
        ::= { cpuProtectionEntry 3}
        

        END
