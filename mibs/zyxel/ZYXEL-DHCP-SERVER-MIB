-- ZyXEL Communications Corporation
-- Private Enterprise MIB definition 
  
-- This file describes the ZyXEL Communications Corporation Enterprise MIB.
-- It contains ZyXEL products OIDs, and common managed objects.

-- $Log: ZYXEL-DHCP-SERVER-MIB.mib $ 
-- Revision 1.5  2015/02/02 08:10:45  Julian 
-- support DHCP Server Lease Time 
-- Revision 1.4  2013/12/06 07:03:34  ccho 
-- remove uncessary imports 
-- Revision 1.3  2012/09/19 07:31:10  Kevin 
-- if it's leaf node, revise the vender name from zyxel to zy 
-- Revision 1.2  2012/07/05 06:22:30  Kevin 
-- 1. upgrade from SNMP to SNMPv2  
-- 2. clean warning 
-- Revision 1.1  2012/05/30 07:48:44  Kevin 
-- Initial revision 

ZYXEL-DHCP-SERVER-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
   	
	IpAddress
		FROM SNMPv2-SMI

	esMgmt			
		FROM ZYXEL-ES-SMI;

	zyxelDhcpServer MODULE-IDENTITY
		LAST-UPDATED	"201207010000Z"    
		ORGANIZATION "Enterprise Solution ZyXEL"     
		CONTACT-INFO
			""	   
		DESCRIPTION
			"The subtree for dhcp server"
		::= { esMgmt 19 }		
		
	zyxelDhcpServerSetup 		OBJECT IDENTIFIER ::= { zyxelDhcpServer 1 }		

	zyDhcpServerMaxNumberOfServers OBJECT-TYPE
        SYNTAX  	INTEGER
        MAX-ACCESS  read-only
        STATUS  	current
        DESCRIPTION
		"The maximum number of DHCP server entries that can be created. 
		 A value of 0 for this object implies that there exist settings for global DHCP relay."
	::= { zyxelDhcpServerSetup 1 }
 
 -- 		zyxelDhcpServerTable
        zyxelDhcpServerTable OBJECT-TYPE
        SYNTAX	SEQUENCE OF ZyxelDhcpServerEntry
        MAX-ACCESS  not-accessible
        STATUS  current
        DESCRIPTION
        "The table contains DHCP server configuration."
        ::= { zyxelDhcpServerSetup 2 }
        
		zyxelDhcpServerEntry OBJECT-TYPE
        SYNTAX	ZyxelDhcpServerEntry
        MAX-ACCESS	not-accessible
        STATUS	current
        DESCRIPTION    	
		"An entry contains DHCP server configuration."
        INDEX          	{ zyDhcpServerVid }
        ::= { zyxelDhcpServerTable 1 }

        ZyxelDhcpServerEntry ::=
           SEQUENCE {
        	zyDhcpServerVid				INTEGER,
        	zyDhcpServerStartIpAddress	IpAddress,
        	zyDhcpServerPoolSize		INTEGER,
        	zyDhcpServerMask			IpAddress,
        	zyDhcpServerGateway			IpAddress,
        	zyDhcpServerPrimaryDNS 		IpAddress,
        	zyDhcpServerSecondaryDNS	IpAddress,
        	zyDhcpServerRowStatus		RowStatus,
			zyDhcpServerLeaseTime		Unsigned32
           }  

      	zyDhcpServerVid OBJECT-TYPE
        SYNTAX  INTEGER
        MAX-ACCESS  not-accessible
        STATUS  current
        DESCRIPTION
        "The VLAN ID to which these DHCP settings apply."
        ::= { zyxelDhcpServerEntry 1 }
                        
        zyDhcpServerStartIpAddress OBJECT-TYPE
        SYNTAX  IpAddress
        MAX-ACCESS  read-write
        STATUS  current
        DESCRIPTION
        "Specify the first of the contiguous addresses for DHCP clients in the IP address pool."
        ::= { zyxelDhcpServerEntry 2 }        
        
        zyDhcpServerPoolSize OBJECT-TYPE
        SYNTAX  INTEGER
        MAX-ACCESS  read-write
        STATUS  current
        DESCRIPTION
        "Specify the size, or counts of the IP address pool. The switch can issue from 1 to 253 IP addresses to DHCP clients."
        ::= { zyxelDhcpServerEntry 3 }    
        
        zyDhcpServerMask OBJECT-TYPE
        SYNTAX  IpAddress
        MAX-ACCESS  read-write
        STATUS  current
        DESCRIPTION
        "The subnet mask for the client IP pool."
        ::= { zyxelDhcpServerEntry 4 }            

        zyDhcpServerGateway OBJECT-TYPE
        SYNTAX  IpAddress
        MAX-ACCESS  read-write
        STATUS  current
        DESCRIPTION
        "The IP address of the default gateway device."
        ::= { zyxelDhcpServerEntry 5 }            
        
        zyDhcpServerPrimaryDNS OBJECT-TYPE
        SYNTAX  IpAddress
        MAX-ACCESS  read-write
        STATUS  current
        DESCRIPTION
        "The IP addresses of primary DNS server. The DNS servers are passed to the DHCP clients 
		 along with the IP address and the subnet mask."
        ::= { zyxelDhcpServerEntry 6 }           
        
        zyDhcpServerSecondaryDNS OBJECT-TYPE
        SYNTAX  IpAddress
        MAX-ACCESS  read-write
        STATUS  current
        DESCRIPTION
        "The IP addresses of secondary DNS server. The DNS servers are passed to the 
		 DHCP clients along with the IP address and the subnet mask."
        ::= { zyxelDhcpServerEntry 7 }                  

        zyDhcpServerRowStatus OBJECT-TYPE
        SYNTAX  RowStatus
        MAX-ACCESS  read-create
        STATUS  current
        DESCRIPTION
        "This object allows DHCP server entries to be created and deleted."
        ::= { zyxelDhcpServerEntry 8 }
		
        zyDhcpServerLeaseTime OBJECT-TYPE
        SYNTAX  Unsigned32
        MAX-ACCESS  read-write
        STATUS  current
        DESCRIPTION
        "Specifies the duration of the lease (in seconds)."
        ::= { zyxelDhcpServerEntry 9 }     
END
