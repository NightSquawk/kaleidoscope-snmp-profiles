--
-- defines STS.mib for XPort-SNMP agent
--
-- Mib is used for STS Units
--
-- Eltek Valere Industrial GmbH - Enterprise 16640
-- renamed from CONVERTRONIC OIDs - Enterprise 16640
-- Version:      1.01
-- Date:         08 January, 2008
-- Developed By: Michael Schulz
--               Software Engineer
--               Eltek Valere Industrial GmbH
--
-- Version:      1.02
-- Date:         18  June, 2009
-- Developed By: Christian Fisch
--               Software Engineer
--               Eltek Valere Industrial GmbH
--
-- Update 18.06.2009:
-- Fix: trap definition string "" instead of "
--
--
-- Update 25.09.2008:
-- Change inv_OutVoltage to inv_InputVoltage
-- add text "Bit_" for direct info, this is a Bit-Information
--       inv_Bit_ShortCircuit, inv_Bit_OutputVoltage, inv_Bit_InputVoltLow, inv_Bit_InputVoltHigh,
--       inv_Bit_OutputVoltLow, inv_Bit_OutputVoltHigh, inv_Bit_OutputCurrHigh, inv_Bit_RemoteOff
--       inv_Bit_CentralAlarm
--
-- Update 07.10.2008:
-- Change trap-descriptions: Modification for HP OpenView
--
-- Version:      1.03
-- Date:         06  Jan., 2010
-- Developed By: Dirk Meise-Reckefuss
--               Software Engineer
--               Eltek Valere Industrial GmbH
--
-- Copyright (c) 2010 Eltek Valere Industrial GmbH.
--

STS_SEQUENZ-MIB DEFINITIONS ::= BEGIN


IMPORTS
  enterprises, IpAddress, Counter, TimeTicks  FROM RFC1155-SMI
  OBJECT-TYPE                                 FROM RFC-1212
  TRAP-TYPE                                   FROM RFC-1215  
  DisplayString                               FROM RFC1213-MIB;


  convertronic                    OBJECT IDENTIFIER ::= { enterprises 16460 }

  sts_system MODULE-IDENTITY
                                  LAST-UPDATED "201001061200Z"  --  Jan. 06 2010 12:00:00 EST

                                  ORGANIZATION "Eltek Valere Industrial GmbH"
                                  CONTACT-INFO
                                        "Michael Schulz

                                        Eltek Valere Industrial GmbH
                                        Im Obrock 33
                                        D-32278 Kirchlengern

                                        Tel: +49 5223 7641 450
                                        Fax: +49 5223 7641 222

                                        E-mail: michael.schulz@eltekvalere.com"
                                    DESCRIPTION
                                        "The MIB module to describe all object of STS Unit "

-- sts_system                       OBJECT IDENTIFIER
                                                   ::= { convertronic 4 }

measureValues                    OBJECT IDENTIFIER ::= { sts_system 1 }
settings                         OBJECT IDENTIFIER ::= { sts_system 2 }
extendedSettings                 OBJECT IDENTIFIER ::= { sts_system 3 }
tables                            OBJECT IDENTIFIER ::= { sts_system 4 }
traps                            OBJECT IDENTIFIER ::= { sts_system 5 }

sts_measureValues                OBJECT IDENTIFIER ::= { measureValues 1 }
inverter_measureValues           OBJECT IDENTIFIER ::= { measureValues 2 }

networkSettings                  OBJECT IDENTIFIER ::= { settings 1 }
unitSettings                     OBJECT IDENTIFIER ::= { settings 2 }

netSyncronisationSet             OBJECT IDENTIFIER ::= { extendedSettings 1 }
adjustValues                     OBJECT IDENTIFIER ::= { extendedSettings 2 }

baseSettings                     OBJECT IDENTIFIER ::= { networkSettings 1 }
serviceSettings                  OBJECT IDENTIFIER ::= { networkSettings 2 }

basicSettings                    OBJECT IDENTIFIER ::= { unitSettings 1 }
advancedSettings                 OBJECT IDENTIFIER ::= { unitSettings 2 }
advancedSettings2                OBJECT IDENTIFIER ::= { unitSettings 3 }


-- ****************************************
-- ****************************************
-- ****************************************

sVal_UN OBJECT-TYPE
  SYNTAX    INTEGER(0..65535)
  ACCESS    read-only
  STATUS    mandatory
  DESCRIPTION "Mains voltage (V), Value: 230(230V)"
::= { sts_measureValues 1 }

sVal_FreqNetz OBJECT-TYPE
  SYNTAX    INTEGER(0..65535)
  ACCESS    read-only
  STATUS    mandatory
  DESCRIPTION "Mains frequency (Hz), Value: 50(50Hz)"
::= { sts_measureValues 2 }

sVal_UWR OBJECT-TYPE
  SYNTAX    INTEGER(0..65535)
  ACCESS    read-only
  STATUS    mandatory
  DESCRIPTION "Inverter voltage (V), Value: 230(230V)"
::= { sts_measureValues 3 }

sVal_FreqWR OBJECT-TYPE
  SYNTAX    INTEGER(0..65535)
  ACCESS    read-only
  STATUS    mandatory
  DESCRIPTION "Inverter frequency (Hz), Value: 50(50Hz)"
::= { sts_measureValues 4 }

sVal_UDC OBJECT-TYPE
  SYNTAX    INTEGER(0..65535)
  ACCESS    read-only
  STATUS    mandatory
  DESCRIPTION "Battery voltage (V), Value: 120(12V)"
::= { sts_measureValues 5 }

sVal_U10 OBJECT-TYPE
  SYNTAX    INTEGER(0..65535)
  ACCESS    read-only
  STATUS    mandatory
  DESCRIPTION "STS Output Voltage (V), Value: 230(230V)"
::= { sts_measureValues 6 }

sVal_IO1 OBJECT-TYPE
  SYNTAX    INTEGER(0..65535)
  ACCESS    read-only
  STATUS    mandatory
  DESCRIPTION "STS Output current (A), Value: 15(15A)"
::= { sts_measureValues 7 }

sVal_P OBJECT-TYPE
  SYNTAX    INTEGER(0..65535)
  ACCESS    read-only
  STATUS    mandatory
  DESCRIPTION "STS active power (W), Value: 2105(2105W)"
::= { sts_measureValues 8 }

sVal_S OBJECT-TYPE
  SYNTAX    INTEGER(0..65535)
  ACCESS    read-only
  STATUS    mandatory
  DESCRIPTION "STS apparent power (VA), Value: 495(495VA)"
::= { sts_measureValues 9 }

sVal_FAN1 OBJECT-TYPE
  SYNTAX    INTEGER(0..65535)
  ACCESS    read-only
  STATUS    mandatory
  DESCRIPTION "Fan 1 speed (rpm), Value: 4200(4200rpm)"
::= { sts_measureValues 10 }

sVal_FAN2 OBJECT-TYPE
  SYNTAX    INTEGER(0..65535)
  ACCESS    read-only
  STATUS    mandatory
  DESCRIPTION "Fan 2 speed (rpm), Value: 3800(3800rpm)"
::= { sts_measureValues 11 }

sVal_TK OBJECT-TYPE
  SYNTAX    INTEGER(0..65535)
  ACCESS    read-only
  STATUS    mandatory
  DESCRIPTION "STS temperature (°C), Value: 301(30,1°C)"
::= { sts_measureValues 12 }

sVal_IO2 OBJECT-TYPE
  SYNTAX    INTEGER(0..65535)
  ACCESS    read-only
  STATUS    mandatory
  DESCRIPTION "STS output current 2 (A), Value: 18(18A)"
::= { sts_measureValues 13 }

sVal_IDC OBJECT-TYPE
  SYNTAX    INTEGER(0..65535)
  ACCESS    read-only
  STATUS    mandatory
  DESCRIPTION "battery output current (A), Value: 24(24A)"
::= { sts_measureValues 14 }

-- ****************************************
-- ****************************************
-- ****************************************
bETHSpeed OBJECT-TYPE
  SYNTAX    INTEGER(0..4)
  ACCESS    read-write
  STATUS    mandatory
  DESCRIPTION "Communication speed setting:
  Value:
  0= autonegotation
  1= 10Mb Halfduplex
  2= 10Mb Fullduplex
  3= 100Mb Halfduplex
  4= 100Mb Fullduplex"
::= { baseSettings 1 }

bLocalIP OBJECT-TYPE
  SYNTAX  IpAddress
  ACCESS    read-write
  STATUS    mandatory
  DESCRIPTION "IP-Adress of the Unit,
  Value: xxx.xxx.xxx.xxx"
::= { baseSettings 2 }

bSubnetMask OBJECT-TYPE
  SYNTAX  IpAddress
  ACCESS    read-write
  STATUS    mandatory
  DESCRIPTION "Used Subnetmask of the Unit,
  Value: xxx.xxx.xxx.xxx"
::= { baseSettings 3 }

bGateway OBJECT-TYPE
  SYNTAX  IpAddress
  ACCESS    read-write
  STATUS    mandatory
  DESCRIPTION "IP of the used Gateway,
  Value: xxx.xxx.xxx.xxx"
::= { baseSettings 4 }

bDNSServer OBJECT-TYPE
  SYNTAX  IpAddress
  ACCESS    read-write
  STATUS    mandatory
  DESCRIPTION "IP of the used Domain Name Service Server,
  Value: xxx.xxx.xxx.xxx"
::= { baseSettings 5 }

bDHCPServer OBJECT-TYPE
  SYNTAX    DisplayString (SIZE (0..16))
  ACCESS    read-write
  STATUS    mandatory
  DESCRIPTION "Name of the DHCP-Server to use,
  Value: max. 16 char."
::= { baseSettings 6 }

bFixedIP_OnOff OBJECT-TYPE
  SYNTAX    INTEGER(0..1)
  ACCESS    read-write
  STATUS    mandatory
  DESCRIPTION "Use Fixed connection settings,
  Value:
  1= Use IP set with LocalIP
  0= Use automatic IP-Configuration"
::= { baseSettings 7 }

bDefaultIP_OnOff OBJECT-TYPE
  SYNTAX    INTEGER(0..1)
  ACCESS    read-write
  STATUS    mandatory
  DESCRIPTION "Usue Fix IP,
  Value:
  0= off
  1= Use IP 192.168.0.10"
::= { baseSettings 8 }

bDHCP_OnOff OBJECT-TYPE
  SYNTAX    INTEGER(0..1)
  ACCESS    read-write
  STATUS    mandatory
  DESCRIPTION "
  Value:
  0= off
  1= Use DHCP for automatic Network configuration"
::= { baseSettings 9 }

bBOOTP_OnOff OBJECT-TYPE
  SYNTAX    INTEGER(0..1)
  ACCESS    read-write
  STATUS    mandatory
  DESCRIPTION "
  Value:
  0= off
  1= Use BOOTP for automatic Network configuration"
::= { baseSettings 10 }

bLocation OBJECT-TYPE
  SYNTAX    DisplayString (SIZE (0..16))
  ACCESS    read-write
  STATUS    mandatory
  DESCRIPTION "Location of the seen Unit,
  Value:
  max. 16 char."
::= { baseSettings 11 }

-- ****************************************
-- ****************************************
-- ****************************************

servSNMP_OnOff OBJECT-TYPE
  SYNTAX    INTEGER(0..1)
  ACCESS    read-write
  STATUS    mandatory
  DESCRIPTION "Use Simple Network Management Protocol,
  Value:
  0= off
  1= on"
::= { serviceSettings 1 }

servTrapReceiver1 OBJECT-TYPE
  SYNTAX  IpAddress
  ACCESS    read-write
  STATUS    mandatory
  DESCRIPTION "IP of SNMP-Trapreceiver 1,
  Value:
  xxx.xxx.xxx.xxx"
::= { serviceSettings 2 }

servTrapReceiver2 OBJECT-TYPE
  SYNTAX  IpAddress
  ACCESS    read-write
  STATUS    mandatory
  DESCRIPTION "IP of SNMP-Trapreceiver 2,
  Value:
  xxx.xxx.xxx.xxx"
::= { serviceSettings 3 }

servTrapReceiver3 OBJECT-TYPE
  SYNTAX  IpAddress
  ACCESS    read-write
  STATUS    mandatory
  DESCRIPTION "IP of SNMP-Trapreceiver 3,
  Value:
  xxx.xxx.xxx.xxx"
::= { serviceSettings 4 }

servTrapReceiver4 OBJECT-TYPE
  SYNTAX  IpAddress
  ACCESS    read-write
  STATUS    mandatory
  DESCRIPTION "IP of SNMP-Trapreceiver 4,
   Value:
   xxx.xxx.xxx.xxx"
::= { serviceSettings 5 }

servReadCommunity OBJECT-TYPE
  SYNTAX    DisplayString (SIZE (0..13))
  ACCESS    read-write
  STATUS    mandatory
  DESCRIPTION "SNMP read community,
  Value:
  max. 13 char."
::= { serviceSettings 6 }

servWriteCommunity OBJECT-TYPE
  SYNTAX    DisplayString (SIZE (0..13))
  ACCESS    read-write
  STATUS    mandatory
  DESCRIPTION "SNMP write community,
  Value:
  max. 13 char."
::= { serviceSettings 7 }

servSMTP_OnOff OBJECT-TYPE
  SYNTAX    INTEGER(0..1)
  ACCESS    read-write
  STATUS    mandatory
  DESCRIPTION "Use Simple Mail Transfer Protocol,
  Value:
  0= off
  1= on"
::= { serviceSettings 8 }

servMailServer OBJECT-TYPE
  SYNTAX    DisplayString (SIZE (0..19))
  ACCESS    read-write
  STATUS    mandatory
  DESCRIPTION "Ip or Name of the used mailserver,
  Value:
  max. 19 char."
::= { serviceSettings 9 }

servMailUsername OBJECT-TYPE
  SYNTAX    DisplayString (SIZE (0..10))
  ACCESS    read-write
  STATUS    mandatory
  DESCRIPTION "Username for the mailserver,
  Value:
  max. 10 char."
::= { serviceSettings 10 }

servMailPassword OBJECT-TYPE
  SYNTAX    DisplayString (SIZE (0..10))
  ACCESS    read-write
  STATUS    mandatory
  DESCRIPTION "Password for the mailserver,
  Value:
  max. 10 char."
::= { serviceSettings 11 }

servMailReceiver1 OBJECT-TYPE
  SYNTAX    DisplayString (SIZE (0..48))
  ACCESS    read-write
  STATUS    mandatory
  DESCRIPTION "First receiver e-mail address,
  Value:
  max. 48 char."
::= { serviceSettings 12 }

servMailTrapLevel1 OBJECT-TYPE
  SYNTAX    INTEGER(0..3)
  ACCESS    read-write
  STATUS    mandatory
  DESCRIPTION "Traplevel for first mailreceiver,
  Value:
  0= Off
  ...
  3= send maximum Traps"
::= { serviceSettings 13 }

servMailReceiver2 OBJECT-TYPE
  SYNTAX    DisplayString (SIZE (0..48))
  ACCESS    read-write
  STATUS    mandatory
  DESCRIPTION "second receiver e-mail address,
  Value:
  max. 48 char."
::= { serviceSettings 14 }

servMailTrapLevel2 OBJECT-TYPE
  SYNTAX    INTEGER(0..3)
  ACCESS    read-write
  STATUS    mandatory
  DESCRIPTION "Traplevel for second mailreceiver,
  Value:
  0= Off
  ...
  3= send maximum Traps"
::= { serviceSettings 15 }

servSNTP_OnOff OBJECT-TYPE
  SYNTAX    INTEGER(0..1)
  ACCESS    read-write
  STATUS    mandatory
  DESCRIPTION "Simple Network Time Protocol,
  Value:
  0= off
  1= on"
::= { serviceSettings 16 }

servSNTPServer1 OBJECT-TYPE
  SYNTAX    DisplayString (SIZE (0..19))
  ACCESS    read-write
  STATUS    mandatory
  DESCRIPTION "IP or name for first SNTP server,
  Value:
  max. 19 char."
::= { serviceSettings 17 }

servSNTPServer2 OBJECT-TYPE
  SYNTAX    DisplayString (SIZE (0..19))
  ACCESS    read-write
  STATUS    mandatory
  DESCRIPTION "IP or name for second SNTP server,
  Value:
  max. 19 char."
::= { serviceSettings 18 }

servTelnet_OnOff OBJECT-TYPE
  SYNTAX    INTEGER(0..1)
  ACCESS    read-write
  STATUS    mandatory
  DESCRIPTION "Configuration over Telnet,
  Value:
  0= off
  1= on"
::= { serviceSettings 19 }

servSyslog_OnOff OBJECT-TYPE
  SYNTAX    INTEGER(0..1)
  ACCESS    read-write
  STATUS    mandatory
  DESCRIPTION "Syslog feature,
  Value:
  0= off
  1= on"
::= { serviceSettings 20 }

-- ****************************************
-- ****************************************
-- ****************************************

sts_Version OBJECT-TYPE
  SYNTAX    INTEGER(0..65535)
  ACCESS    read-only
  STATUS    mandatory
  DESCRIPTION "STS Software version,
  Value:
  99(Ver 0.99)"
::= { basicSettings 1 }

sts_Inverter OBJECT-TYPE
  SYNTAX    INTEGER(0..15)
  ACCESS    read-write
  STATUS    mandatory
  DESCRIPTION "STS count of needed inverter,
  Value:
  0 - 15"
::= { basicSettings 2 }

sts_SigCF_b0 OBJECT-TYPE
  SYNTAX    INTEGER(0..1)
  ACCESS    read-write
  STATUS    mandatory
  DESCRIPTION "Central failure signal: Source 1 failure,
  Value:
  0= off
  1= on"
::= { basicSettings 3 }

sts_SigCF_b1 OBJECT-TYPE
  SYNTAX    INTEGER(0..1)
  ACCESS    read-write
  STATUS    mandatory
  DESCRIPTION "Central failure signal: Source 2 failure,
  Value:
  0= off
  1= on"
::= { basicSettings 4 }

sts_SigCF_b2 OBJECT-TYPE
  SYNTAX    INTEGER(0..1)
  ACCESS    read-write
  STATUS    mandatory
  DESCRIPTION "Central failure signal: Syncronisation error,
  Value:
  0= off
  1= on"
::= { basicSettings 5 }

sts_SigCF_b3 OBJECT-TYPE
  SYNTAX    INTEGER(0..1)
  ACCESS    read-write
  STATUS    mandatory
  DESCRIPTION "Central failure signal: Inverter failure,
  Value:
  0= off
  1= on"
::= { basicSettings 6 }

sts_SigCF_b4 OBJECT-TYPE
  SYNTAX    INTEGER(0..1)
  ACCESS    read-write
  STATUS    mandatory
  DESCRIPTION "Central failure signal: STS overtemperature,
  Value:
  0= off
  1= on"
::= { basicSettings 7 }

sts_SigCF_b5 OBJECT-TYPE
  SYNTAX    INTEGER(0..1)
  ACCESS    read-write
  STATUS    mandatory
  DESCRIPTION "Central failure signal: STS overload,
  Value:
  0= off
  1= on"
::= { basicSettings 8 }

sts_SigCF_b6 OBJECT-TYPE
  SYNTAX    INTEGER(0..1)
  ACCESS    read-write
  STATUS    mandatory
  DESCRIPTION "Central failure signal: Inverter overload,
  Value:
  0= off
  1= on"
::= { basicSettings 9 }

sts_SigCF_b7 OBJECT-TYPE
  SYNTAX    INTEGER(0..1)
  ACCESS    read-write
  STATUS    mandatory
  DESCRIPTION "Central failure signal: DC voltage low,
  Value:
  0= off
  1= on"
::= { basicSettings 10 }

sts_SigCF_b8 OBJECT-TYPE
  SYNTAX    INTEGER(0..1)
  ACCESS    read-write
  STATUS    mandatory
  DESCRIPTION "Central failure signal: DC voltage high,
  Value:
  0= off
  1= on"
::= { basicSettings 11 }

sts_SigCF_b9 OBJECT-TYPE
  SYNTAX    INTEGER(0..1)
  ACCESS    read-write
  STATUS    mandatory
  DESCRIPTION "Central failure signal: U batterie< warning,
  Value:
  0= off
  1= on"
::= { basicSettings 12 }

sts_SigCF_b10 OBJECT-TYPE
  SYNTAX    INTEGER(0..1)
  ACCESS    read-write
  STATUS    mandatory
  DESCRIPTION "Central failure signal: U batterie> warning,
  Value:
  0= off
  1= on"
::= { basicSettings 13 }

sts_SigCF_b11 OBJECT-TYPE
  SYNTAX    INTEGER(0..1)
  ACCESS    read-write
  STATUS    mandatory
  DESCRIPTION "Central failure signal: Fan error,
  Value:
  0= off
  1= on"
::= { basicSettings 14 }

sts_SigCF_b12 OBJECT-TYPE
  SYNTAX    INTEGER(0..1)
  ACCESS    read-write
  STATUS    mandatory
  DESCRIPTION "Central failure signal: future use"
::= { basicSettings 15 }

sts_SigCF_b13 OBJECT-TYPE
  SYNTAX    INTEGER(0..1)
  ACCESS    read-write
  STATUS    mandatory
  DESCRIPTION "Central failure signal: future use"
::= { basicSettings 16 }

sts_SigCF_b14 OBJECT-TYPE
  SYNTAX    INTEGER(0..1)
  ACCESS    read-write
  STATUS    mandatory
  DESCRIPTION "Central failure signal: future use"
::= { basicSettings 17 }

sts_SigCF_b15 OBJECT-TYPE
  SYNTAX    INTEGER(0..1)
  ACCESS    read-write
  STATUS    mandatory
  DESCRIPTION "Central failure signal: future use"
::= { basicSettings 18 }

sts_DelayRelCA OBJECT-TYPE
  SYNTAX    INTEGER(1..60)
  ACCESS    read-write
  STATUS    mandatory
  DESCRIPTION "Delay of the Central failure relay signaling,
  Value:
  1(1sec.)
  ...
  60(60sec.)"
::= { basicSettings 19 }

sts_DelayLEDCA OBJECT-TYPE
  SYNTAX    INTEGER(1..60)
  ACCESS    read-write
  STATUS    mandatory
  DESCRIPTION "Delay of the Central failure LED signaling,
  Value:
  1(1sec.)
  ...
  60(60sec.)"
::= { basicSettings 20 }

sts_LCDContrast OBJECT-TYPE
  SYNTAX    INTEGER(0..100)
  ACCESS    read-write
  STATUS    mandatory
  DESCRIPTION "LCD contrast from 0% to 100%. Use 10% steps,
  Value:
  0(0%)
  10 (10%)
  20(20%)
  ...
  90(90%)
  100(100%)"
::= { basicSettings 21 }

sts_Language OBJECT-TYPE
  SYNTAX    INTEGER(0..4)
  ACCESS    read-write
  STATUS    mandatory
  DESCRIPTION "LCD Language,
  Value:
  0= English
  1= German
  2= Polish
  3= Swedish
  4= Italian"
::= { basicSettings 22 }

-- ****************************************
-- ****************************************
-- ****************************************

sts_OpMode OBJECT-TYPE
  SYNTAX    INTEGER(0..1)
  ACCESS    read-write
  STATUS    mandatory
  DESCRIPTION "Operation mode,
  Value:
  0= Inverter priority
  1= Mains priority"
::= { advancedSettings 1 }

sts_UpperSwitchLimS1 OBJECT-TYPE
  SYNTAX    INTEGER(5..20)
  ACCESS    read-write
  STATUS    mandatory
  DESCRIPTION "Source 1 upper switch limit in % of nominal voltage,
  Value:
  5(5%)
  ...
  20(20%)"
::= { advancedSettings 2 }

sts_LowerSwitchLimS1 OBJECT-TYPE
  SYNTAX    INTEGER(5..20)
  ACCESS    read-write
  STATUS    mandatory
  DESCRIPTION "Source 1 lower switch limit in % of nominal voltage,
  Value:
  5(5%)
  ...
  20(20%)"
::= { advancedSettings 3 }

sts_SwitchDelayS1 OBJECT-TYPE
  SYNTAX    INTEGER(1..8)
  ACCESS    read-write
  STATUS    mandatory
  DESCRIPTION "Source 1 switching delay, if source 1 leave limits,
  Value:
  1= 0.5ms
  2= 1.0ms
  3= 1.5ms
  4= 2.0ms
  5= 2.5ms
  6= 3.0ms
  7= 3.5ms
  8= 4.0ms"
::= { advancedSettings 4 }

sts_UpperSwitchLimS2 OBJECT-TYPE
  SYNTAX    INTEGER(5..20)
  ACCESS    read-write
  STATUS    mandatory
  DESCRIPTION "Source 2 upper switch limit in % of nominal voltage,
  Value:
  5(5%)
  ...
  20(20%)"
::= { advancedSettings 5 }

sts_LowerSwitchLimS2 OBJECT-TYPE
  SYNTAX    INTEGER(5..20)
  ACCESS    read-write
  STATUS    mandatory
  DESCRIPTION "Source 2 lower switch limit in % of nominal voltage,
  Value:
  5(5%)
  ...
  20(20%)"
::= { advancedSettings 6 }

sts_SwitchDelayS2 OBJECT-TYPE
  SYNTAX    INTEGER(1..8)
  ACCESS    read-write
  STATUS    mandatory
  DESCRIPTION "Source 2 switching delay, if source 2 leave limits,
  Value:
  1= 0.5ms
  2= 1.0ms
  3= 1.5ms
  4= 2.0ms
  5= 2.5ms
  6= 3.0ms
  7= 3.5ms
  8= 4.0ms"
::= { advancedSettings 7 }

sts_MaxCellVolt1 OBJECT-TYPE
  SYNTAX    INTEGER(200..300)
  ACCESS    read-write
  STATUS    mandatory
  DESCRIPTION "Umax1 voltage/cell 2,0V - 3,0V,
  Value:
  200(2,0V)
  ...
  300(3,0V)"
::= { advancedSettings 8 }

sts_MinCellVolt1 OBJECT-TYPE
  SYNTAX    INTEGER(70..250)
  ACCESS    read-write
  STATUS    mandatory
  DESCRIPTION "Umin1 voltage/cell 0,7V - 2,5V,
  Value:
  70(0,7V)
  ...
  250(2,5V)"
::= { advancedSettings 9 }

sts_MinCellVolt2 OBJECT-TYPE
  SYNTAX    INTEGER(60..250)
  ACCESS    read-write
  STATUS    mandatory
  DESCRIPTION "Umin2 voltage/cell 0,6V - 2,5V,
  Value:
  60(0,6V)
  ...
  250(2,5V)"
::= { advancedSettings 10 }

sts_MinULimit OBJECT-TYPE
  SYNTAX    INTEGER(170..210)
  ACCESS    read-write
  STATUS    mandatory
  DESCRIPTION "Lower limit voltage/cell for generating error, 1,7V - 2,1V,
  Value:
  170(1,7V)
  ...
  210(2,1V)"
::= { advancedSettings 11 }

sts_MaxULimit OBJECT-TYPE
  SYNTAX    INTEGER(220..250)
  ACCESS    read-write
  STATUS    mandatory
  DESCRIPTION "Upper limit voltage/cell for generating error, 2,2V - 2,5V,
  Value:
  220(2,2V)
  ...
  250(2,5V)"
::= { advancedSettings 12 }

-- ****************************************
-- ****************************************
-- ****************************************

sts_NomPower OBJECT-TYPE
  SYNTAX    INTEGER(120..500)
  ACCESS    read-write
  STATUS    mandatory
  DESCRIPTION "Power 1,2KVA - 5KVA,
  Value:
  120(1,2KVA)
  ...
  500(5KVA)"
::= { advancedSettings2 1 }

sts_NomVolt OBJECT-TYPE
  SYNTAX    INTEGER(200..250)
  ACCESS    read-write
  STATUS    mandatory
  DESCRIPTION "Nominal voltage 200VAC - 250VAC,
  Value:
  200(200VAC)
  ...
  250(250VAC)"
::= { advancedSettings2 2 }

sts_NomFreq OBJECT-TYPE
  SYNTAX    INTEGER(0..1)
  ACCESS    read-write
  STATUS    mandatory
  DESCRIPTION "Nominal frequency 50Hz or 60Hz,
  Value:
  0= 50Hz
  1= 60Hz"
::= { advancedSettings2 3 }

sts_FreqRange OBJECT-TYPE
  SYNTAX    INTEGER(1..20)
  ACCESS    read-write
  STATUS    mandatory
  DESCRIPTION "Frequency range 0,1Hz - 2,0Hz,
  Value:
  1(0,1Hz)
  ...
  20(2,0Hz)"
::= { advancedSettings2 4 }

sts_MaxCurrent OBJECT-TYPE
  SYNTAX    INTEGER(10..2500)
  ACCESS    read-write
  STATUS    mandatory
  DESCRIPTION "Max output current 1,0A - 250A,
  Value:
  10(1,0A)
  ...
  2500(250A)"
::= { advancedSettings2 5 }

sts_PresentCell OBJECT-TYPE
  SYNTAX    INTEGER(12..200)
  ACCESS    read-write
  STATUS    mandatory
  DESCRIPTION "Number of present battery cell 12 - 200,
  Value:
  12
  ...
  200"
::= { advancedSettings2 6 }

sts_CellVoltage OBJECT-TYPE
  SYNTAX    INTEGER(0..1)
  ACCESS    read-write
  STATUS    mandatory
  DESCRIPTION "Voltage per Cell,
  Value:
  0=2.0V
  1=1.2V"
::= { advancedSettings2 7 }

sts_Adress OBJECT-TYPE
  SYNTAX    INTEGER(0..31)
  ACCESS    read-write
  STATUS    mandatory
  DESCRIPTION ""
::= { advancedSettings2 8 }

sts_SigRel2_b0 OBJECT-TYPE
  SYNTAX    INTEGER(0..1)
  ACCESS    read-write
  STATUS    mandatory
  DESCRIPTION "Relay 2 failure signal: Source 1 failure,
  Value:
  0= off
  1= on"
::= { advancedSettings2 9 }

sts_SigRel2_b1 OBJECT-TYPE
  SYNTAX    INTEGER(0..1)
  ACCESS    read-write
  STATUS    mandatory
  DESCRIPTION "Relay 2 failure signal: Source 2 failure,
  Value:
  0= off
  1= on"
::= { advancedSettings2 10 }

sts_SigRel2_b2 OBJECT-TYPE
  SYNTAX    INTEGER(0..1)
  ACCESS    read-write
  STATUS    mandatory
  DESCRIPTION "Relay 2 failure signal: Syncronisation error,
  Value:
  0= off
  1= on"
::= { advancedSettings2 11 }

sts_SigRel2_b3 OBJECT-TYPE
  SYNTAX    INTEGER(0..1)
  ACCESS    read-write
  STATUS    mandatory
  DESCRIPTION "Relay 2 failure signal: Inverter failure,
  Value:
  0= off
  1= on"
::= { advancedSettings2 12 }

sts_SigRel2_b4 OBJECT-TYPE
  SYNTAX    INTEGER(0..1)
  ACCESS    read-write
  STATUS    mandatory
  DESCRIPTION "Relay 2 failure signal: STS overtemperature,
  Value:
  0= off
  1= on"
::= { advancedSettings2 13 }

sts_SigRel2_b5 OBJECT-TYPE
  SYNTAX    INTEGER(0..1)
  ACCESS    read-write
  STATUS    mandatory
  DESCRIPTION "Relay 2 failure signal: STS overload,
  Value:
  0= off
  1= on"
::= { advancedSettings2 14 }

sts_SigRel2_b6 OBJECT-TYPE
  SYNTAX    INTEGER(0..1)
  ACCESS    read-write
  STATUS    mandatory
  DESCRIPTION "Relay 2 failure signal: Inverter overload,
  Value:
  0= off
  1= on"
::= { advancedSettings2 15 }

sts_SigRel2_b7 OBJECT-TYPE
  SYNTAX    INTEGER(0..1)
  ACCESS    read-write
  STATUS    mandatory
  DESCRIPTION "Relay 2 failure signal: DC voltage low,
  Value:
  0= off
  1= on"
::= { advancedSettings2 16 }

sts_SigRel2_b8 OBJECT-TYPE
  SYNTAX    INTEGER(0..1)
  ACCESS    read-write
  STATUS    mandatory
  DESCRIPTION "Relay 2 failure signal: DC voltage high,
  Value:
  0= off
  1= on"
::= { advancedSettings2 17 }

sts_SigRel2_b9 OBJECT-TYPE
  SYNTAX    INTEGER(0..1)
  ACCESS    read-write
  STATUS    mandatory
  DESCRIPTION "Relay 2 failure signal: U batterie< warning,
  Value:
  0= off
  1= on"
::= { advancedSettings2 18 }

sts_SigRel2_b10 OBJECT-TYPE
  SYNTAX    INTEGER(0..1)
  ACCESS    read-write
  STATUS    mandatory
  DESCRIPTION "Relay 2 failure signal: U batterie> warning,
  Value:
  0= off
  1= on"
::= { advancedSettings2 19 }

sts_SigRel2_b11 OBJECT-TYPE
  SYNTAX    INTEGER(0..1)
  ACCESS    read-write
  STATUS    mandatory
  DESCRIPTION "Relay 2 failure signal: Fan error,
  Value:
  0= off
  1= on"
::= { advancedSettings2 20 }

sts_SigRel2_b12 OBJECT-TYPE
  SYNTAX    INTEGER(0..1)
  ACCESS    read-write
  STATUS    mandatory
  DESCRIPTION "Relay 2 failure signal: future use"
::= { advancedSettings2 21 }

sts_SigRel2_b13 OBJECT-TYPE
  SYNTAX    INTEGER(0..1)
  ACCESS    read-write
  STATUS    mandatory
  DESCRIPTION "Relay 2 failure signal: future use"
::= { advancedSettings2 22 }

sts_SigRel2_b14 OBJECT-TYPE
  SYNTAX    INTEGER(0..1)
  ACCESS    read-write
  STATUS    mandatory
  DESCRIPTION "Relay 2 failure signal: future use"
::= { advancedSettings2 23 }

sts_SigRel2_b15 OBJECT-TYPE
  SYNTAX    INTEGER(0..1)
  ACCESS    read-write
  STATUS    mandatory
  DESCRIPTION "Relay 2 failure signal: future use"
::= { advancedSettings2 24 }

sts_ModeRel2 OBJECT-TYPE
  SYNTAX    INTEGER(0..1)
  ACCESS    read-write
  STATUS    mandatory
  DESCRIPTION "Relay 2 mode,
  Value:
  0= normal operation
  1= inverted operation"
::= { advancedSettings2 25 }

sts_DelayRel2 OBJECT-TYPE
  SYNTAX    INTEGER(1..60)
  ACCESS    read-write
  STATUS    mandatory
  DESCRIPTION "Delay of relay 2 signaling 1sec. - 60sec.,
  Value:
  1(1sec.)
  ...
  60(60sec.)"
::= { advancedSettings2 26 }

sts_OverTemp OBJECT-TYPE
  SYNTAX    INTEGER(358..358)
  ACCESS    read-only
  STATUS    mandatory
  DESCRIPTION "STS Overtemperature 85(°C),
  Value:
  85(85°C)"
::= { advancedSettings2 27 }

-- ****************************************
-- ****************************************
-- ****************************************

net_EdgeDetectionDelay OBJECT-TYPE
  SYNTAX    INTEGER(0..20)
  ACCESS    read-write
  STATUS    mandatory
  DESCRIPTION "Edge detection delay 0ms - 20ms,
  Value:
  0(0ms)
  ...
  20(20ms)"
::= { netSyncronisationSet 1 }

net_TimeOutDelay OBJECT-TYPE
  SYNTAX    INTEGER(0..20)
  ACCESS    read-write
  STATUS    mandatory
  DESCRIPTION "Timeout delay 0ms - 20ms,
  Value:
  0(0ms)
  ...
  20(20ms)"
::= { netSyncronisationSet 2 }

net_MaxCorrPhi OBJECT-TYPE
  SYNTAX    INTEGER(1..255)
  ACCESS    read-write
  STATUS    mandatory
  DESCRIPTION "Max correction cosinus Phi. 333ns - 84915ns (1dig.=>333ns),
  Value:
  1(333ns)
  ...
  255(84915ns)"
::= { netSyncronisationSet 3 }

net_DivDeltaPhi OBJECT-TYPE
  SYNTAX    INTEGER(0..8)
  ACCESS    read-write
  STATUS    mandatory
  DESCRIPTION "1 - 1/256,
  Value:
  0=1
  1=1/2
  2=1/4
  3=1/8
  4=1/16
  5=1/32
  6=1/64
  7=1/128
  8=1/256"
::= { netSyncronisationSet 4 }

net_DivCorrPhi_I OBJECT-TYPE
  SYNTAX    INTEGER(0..8)
  ACCESS    read-write
  STATUS    mandatory
  DESCRIPTION " 1 - 1/256,
  Value:
  0=1
  1=1/2
  2=1/4
  3=1/8
  4=1/16
  5=1/32
  6=1/64
  7=1/128
  8=1/256"
::= { netSyncronisationSet 5 }

net_MaxCorrT OBJECT-TYPE
  SYNTAX    INTEGER(1..255)
  ACCESS    read-write
  STATUS    mandatory
  DESCRIPTION "333ns - 84915ns (1dig.=>333ns),
  Value:
  1(333ns)
  ...
  255(84915ns)"
::= { netSyncronisationSet 6 }

net_DivDeltaT OBJECT-TYPE
  SYNTAX    INTEGER(0..8)
  ACCESS    read-write
  STATUS    mandatory
  DESCRIPTION "1 - 1/256,
  Value:
  0=1
  1=1/2
  2=1/4
  3=1/8
  4=1/16
  5=1/32
  6=1/64
  7=1/128
  8=1/256"
::= { netSyncronisationSet 7 }

net_SyncOKNr OBJECT-TYPE
  SYNTAX    INTEGER(1..255)
  ACCESS    read-write
  STATUS    mandatory
  DESCRIPTION "1 - 255,
  Value:
  1
  ...
  255"
::= { netSyncronisationSet 8 }

net_SyncErrorNr OBJECT-TYPE
  SYNTAX    INTEGER(1..255)
  ACCESS    read-write
  STATUS    mandatory
  DESCRIPTION "1 - 255,
  Value:
  1
  ...
  255"
::= { netSyncronisationSet 9 }

net_P_Diff OBJECT-TYPE
  SYNTAX    INTEGER(150..15000)
  ACCESS    read-write
  STATUS    mandatory
  DESCRIPTION "150 - 1500,
  Value:
  150
  ...
  1500"
::= { netSyncronisationSet 10 }

-- ****************************************
-- ****************************************
-- ****************************************

adj_UMains OBJECT-TYPE
  SYNTAX    INTEGER(368..432)
  ACCESS    read-write
  STATUS    mandatory
  DESCRIPTION ""
::= { adjustValues 1 }

adj_UInv OBJECT-TYPE
  SYNTAX    INTEGER(368..432)
  ACCESS    read-write
  STATUS    mandatory
  DESCRIPTION ""
::= { adjustValues 2 }

adj_UDC OBJECT-TYPE
  SYNTAX    INTEGER(1372..1628)
  ACCESS    read-write
  STATUS    mandatory
  DESCRIPTION ""
::= { adjustValues 3 }

adj_Uout OBJECT-TYPE
  SYNTAX    INTEGER(368..432)
  ACCESS    read-write
  STATUS    mandatory
  DESCRIPTION ""
::= { adjustValues 4 }

adj_Iout OBJECT-TYPE
  SYNTAX    INTEGER(1988..3012)
  ACCESS    read-write
  STATUS    mandatory
  DESCRIPTION ""
::= { adjustValues 5 }

-- ****************************************
-- ****************************************
-- ****************************************
-- ****************************************
-- ****************************************
-- ****************************************

trapLastMessageStringTest OBJECT-TYPE
  SYNTAX OCTET STRING 
  ACCESS not-accessible
  STATUS mandatory
  DESCRIPTION "Message giving more detailed information on alarms."
::= { traps 1 }

trapLastMessageNbrTest OBJECT-TYPE
  SYNTAX INTEGER(16..46) 
  ACCESS not-accessible
  STATUS mandatory
  DESCRIPTION "Referenced Trap number"
::= { traps 2 }

trapSourceIPTest OBJECT-TYPE
  SYNTAX IpAddress 
  ACCESS not-accessible
  STATUS mandatory
  DESCRIPTION "Alarm Source IP address"
::= { traps 3 }

-- source_mains_failue_present NOTIFICATION-TYPE
--   STATUS    obsolete
--   DESCRIPTION "Error with Source mains present"
-- ::= { traps 17 }

trap_source_mains_failue_present OBJECT-TYPE
  SYNTAX INTEGER(0..1) 
  ACCESS not-accessible
  STATUS mandatory
  DESCRIPTION "STS mains failure present"
::= { traps 17 }

source_mains_failue_present_trap TRAP-TYPE
    ENTERPRISE  convertronic
    VARIABLES   {
                  trap_source_mains_failue_present,
    		          trapLastMessageStringTest,
    	  	        trapLastMessageNbrTest,
    	  	        trapSourceIPTest
    		        }
    DESCRIPTION
        "Error with Source mains present"
    -- NMS trap annotation
    --#TYPE "Error with Source mains present"
    --#SUMMARY "Failure %d, Text: %s, No: %d."
    --#ARGUMENTS {0,1,2}
    --#SEVERITY MAJOR
    --#TIMEINDEX 99
    --#STATE OPERATIONAL    
    ::= 16
    
-- source_inverter_failure_present NOTIFICATION-TYPE
--   STATUS    mandatory
--   DESCRIPTION "Error with Source inverter present"
-- ::= { traps 18 }

trap_source_inverter_failure_present OBJECT-TYPE
  SYNTAX INTEGER(0..1) 
  ACCESS not-accessible
  STATUS mandatory
  DESCRIPTION "STS inverter source failure present"
::= { traps 18 }

source_inverter_failure_present TRAP-TYPE
    ENTERPRISE  convertronic
    VARIABLES   {
                  trap_source_inverter_failure_present,
    		          trapLastMessageStringTest,
    	  	        trapLastMessageNbrTest,
    	  	        trapSourceIPTest
    		        }
    DESCRIPTION
        "Error with Source inverter present"
    -- NMS trap annotation
    --#TYPE "Error with Source inverter present"
    --#SUMMARY "Failure %d, Text: %s, No: %d."
    --#ARGUMENTS {0,1,2}
    --#SEVERITY MAJOR
    --#TIMEINDEX 99
    --#STATE OPERATIONAL    
    ::= 17

-- 
-- syncronisation_error_present NOTIFICATION-TYPE
--   STATUS    mandatory
--   DESCRIPTION "Syncronisation between Source Mains and Source Inverter lost"
-- ::= { traps 19 }

trap_syncronisation_error_present OBJECT-TYPE
  SYNTAX INTEGER(0..1) 
  ACCESS not-accessible
  STATUS mandatory
  DESCRIPTION "STS syncronisation error present"
::= { traps 19 }

syncronisation_error_present TRAP-TYPE
    ENTERPRISE  convertronic
    VARIABLES   {
                  trap_syncronisation_error_present,
    		          trapLastMessageStringTest,
    	  	        trapLastMessageNbrTest,
    	  	        trapSourceIPTest
    		        }
    DESCRIPTION
        "Syncronisation between Source Mains and Source Inverter lost"
    -- NMS trap annotation
    --#TYPE "Syncronisation between Source Mains and Source Inverter lost"
    --#SUMMARY "Failure %d, Text: %s, No: %d."
    --#ARGUMENTS {0,1,2}
    --#SEVERITY MAJOR
    --#TIMEINDEX 99
    --#STATE OPERATIONAL    
    ::= 18

-- 
-- inverter_failure_present NOTIFICATION-TYPE
--   STATUS    mandatory
--   DESCRIPTION "Inverter failure active"
-- ::= { traps 20 }

trap_inverter_failure_present OBJECT-TYPE
  SYNTAX INTEGER(0..1) 
  ACCESS not-accessible
  STATUS mandatory
  DESCRIPTION "STS inverter failure present"
::= { traps 20 }

inverter_failure_present TRAP-TYPE
    ENTERPRISE  convertronic
    VARIABLES   {
                  trap_inverter_failure_present,
    		          trapLastMessageStringTest,
    	  	        trapLastMessageNbrTest,
    	  	        trapSourceIPTest
    		        }
    DESCRIPTION
        "Inverter failure active"
    -- NMS trap annotation
    --#TYPE "Inverter failure active"
    --#SUMMARY "Failure %d, Text: %s, No: %d."
    --#ARGUMENTS {0,1,2}
    --#SEVERITY MAJOR
    --#TIMEINDEX 99
    --#STATE OPERATIONAL    
    ::= 19

-- 
-- no_redundant_inverter_present NOTIFICATION-TYPE
--   STATUS    mandatory
--   DESCRIPTION "No more redundant inverter present"
-- ::= { traps 21 }

trap_no_redundant_inverter_present OBJECT-TYPE
  SYNTAX INTEGER(0..1) 
  ACCESS not-accessible
  STATUS mandatory
  DESCRIPTION "STS no redundant inverter present"
::= { traps 21 }

no_redundant_inverter_present TRAP-TYPE
    ENTERPRISE  convertronic
    VARIABLES   {
                  trap_no_redundant_inverter_present,
    		          trapLastMessageStringTest,
    	  	        trapLastMessageNbrTest,
    	  	        trapSourceIPTest
    		        }
    DESCRIPTION
        "No more redundant inverter present"
    -- NMS trap annotation
    --#TYPE "No more redundant inverter present"
    --#SUMMARY "Failure %d, Text: %s, No: %d."
    --#ARGUMENTS {0,1,2}
    --#SEVERITY MINOR
    --#TIMEINDEX 99
    --#STATE OPERATIONAL    
    ::= 20
    
-- 
-- critical_inverter_quantity_present NOTIFICATION-TYPE
--   STATUS    mandatory
--   DESCRIPTION "Inverter quantity is lower than needed"
-- ::= { traps 22 }

trap_critical_inverter_quantity_present OBJECT-TYPE
  SYNTAX INTEGER(0..1) 
  ACCESS not-accessible
  STATUS mandatory
  DESCRIPTION "STS critical inverter quantity present"
::= { traps 22 }

critical_inverter_quantity_present TRAP-TYPE
    ENTERPRISE  convertronic
    VARIABLES   {
                  trap_critical_inverter_quantity_present,
    		          trapLastMessageStringTest,
    	  	        trapLastMessageNbrTest,
    	  	        trapSourceIPTest
    		        }
    DESCRIPTION
        "Inverter quantity is lower than needed"
    -- NMS trap annotation
    --#TYPE "Inverter quantity is lower than needed"
    --#SUMMARY "Failure %d, Text: %s, No: %d."
    --#ARGUMENTS {0,1,2}
    --#SEVERITY MAJOR
    --#TIMEINDEX 99
    --#STATE OPERATIONAL    
    ::= 21

-- 
-- sts_overtemperature_present NOTIFICATION-TYPE
--   STATUS    mandatory
--   DESCRIPTION "STS temperature warning is active"
-- ::= { traps 23 }

trap_sts_overtemperature_present OBJECT-TYPE
  SYNTAX INTEGER(0..1) 
  ACCESS not-accessible
  STATUS mandatory
  DESCRIPTION "STS sts overtemperature present"
::= { traps 23 }

sts_overtemperature_present TRAP-TYPE
    ENTERPRISE  convertronic
    VARIABLES   {
                  trap_sts_overtemperature_present,
    		          trapLastMessageStringTest,
    	  	        trapLastMessageNbrTest,
    	  	        trapSourceIPTest
    		        }
    DESCRIPTION
        "STS temperature warning is active"
    -- NMS trap annotation
    --#TYPE "STS temperature warning is active"
    --#SUMMARY "Failure %d, Text: %s, No: %d."
    --#ARGUMENTS {0,1,2}
    --#SEVERITY MAJOR
    --#TIMEINDEX 99
    --#STATE OPERATIONAL    
    ::= 22

-- 
-- sts_overload_present NOTIFICATION-TYPE
--   STATUS    mandatory
--   DESCRIPTION "STS overload is active"
-- ::= { traps 24 }

trap_sts_overload_present OBJECT-TYPE
  SYNTAX INTEGER(0..1) 
  ACCESS not-accessible
  STATUS mandatory
  DESCRIPTION "STS sts overload present"
::= { traps 24 }

sts_overload_present TRAP-TYPE
    ENTERPRISE  convertronic
    VARIABLES   {
                  trap_sts_overload_present,
    		          trapLastMessageStringTest,
    	  	        trapLastMessageNbrTest,
    	  	        trapSourceIPTest
    		        }
    DESCRIPTION
        "STS overload is active"
    -- NMS trap annotation
    --#TYPE "STS overload is active"
    --#SUMMARY "Failure %d, Text: %s, No: %d."
    --#ARGUMENTS {0,1,2}
    --#SEVERITY MAJOR
    --#TIMEINDEX 99
    --#STATE OPERATIONAL    
    ::= 23

-- 
-- inverter_overload_present NOTIFICATION-TYPE
--   STATUS    mandatory
--   DESCRIPTION "Inverter overload is active"
-- ::= { traps 25 }

trap_inverter_overload_present OBJECT-TYPE
  SYNTAX INTEGER(0..1) 
  ACCESS not-accessible
  STATUS mandatory
  DESCRIPTION "STS inverter overload present"
::= { traps 25 }

inverter_overload_present TRAP-TYPE
    ENTERPRISE  convertronic
    VARIABLES   {
                  trap_inverter_overload_present,
    		          trapLastMessageStringTest,
    	  	        trapLastMessageNbrTest,
    	  	        trapSourceIPTest
    		        }
    DESCRIPTION
        "Inverter overload is active"
    -- NMS trap annotation
    --#TYPE "Inverter overload is active"
    --#SUMMARY "Failure %d, Text: %s, No: %d."
    --#ARGUMENTS {0,1,2}
    --#SEVERITY MAJOR
    --#TIMEINDEX 99
    --#STATE OPERATIONAL    
    ::= 24
    
-- 
-- sts_current_need_redandancy_present NOTIFICATION-TYPE
--   STATUS    mandatory
--   DESCRIPTION "STS actual current need an redundant inverter"
-- ::= { traps 26 }

trap_sts_current_need_redandancy_present OBJECT-TYPE
  SYNTAX INTEGER(0..1) 
  ACCESS not-accessible
  STATUS mandatory
  DESCRIPTION "STS current need redandancy present"
::= { traps 26 }

sts_current_need_redandancy_present TRAP-TYPE
    ENTERPRISE  convertronic
    VARIABLES   {
                  trap_sts_current_need_redandancy_present,
    		          trapLastMessageStringTest,
    	  	        trapLastMessageNbrTest,
    	  	        trapSourceIPTest
    		        }
    DESCRIPTION
        "STS actual current need an redundant inverter"
    -- NMS trap annotation
    --#TYPE "STS actual current need an redundant inverter"
    --#SUMMARY "Failure %d, Text: %s, No: %d."
    --#ARGUMENTS {0,1,2}
    --#SEVERITY MINOR
    --#TIMEINDEX 99
    --#STATE OPERATIONAL    
    ::= 25
-- 
-- dc_voltage_low_present NOTIFICATION-TYPE
--   STATUS    mandatory
--   DESCRIPTION "DC voltage is low"
-- ::= { traps 27 }

trap_dc_voltage_low_present OBJECT-TYPE
  SYNTAX INTEGER(0..1) 
  ACCESS not-accessible
  STATUS mandatory
  DESCRIPTION "STS dc voltage low present"
::= { traps 27 }

dc_voltage_low_present TRAP-TYPE
    ENTERPRISE  convertronic
    VARIABLES   {
                  trap_dc_voltage_low_present,
    		          trapLastMessageStringTest,
    	  	        trapLastMessageNbrTest,
    	  	        trapSourceIPTest
    		        }
    DESCRIPTION
        "DC voltage is low"
    -- NMS trap annotation
    --#TYPE "DC voltage is low"
    --#SUMMARY "Failure %d, Text: %s, No: %d."
    --#ARGUMENTS {0,1,2}
    --#SEVERITY MAJOR
    --#TIMEINDEX 99
    --#STATE OPERATIONAL    
    ::= 26
    
-- 
-- dc_voltage_high_present NOTIFICATION-TYPE
--   STATUS    mandatory
--   DESCRIPTION "DC voltage is high"
-- ::= { traps 28 }

trap_dc_voltage_high_present OBJECT-TYPE
  SYNTAX INTEGER(0..1) 
  ACCESS not-accessible
  STATUS mandatory
  DESCRIPTION "STS DC voltage is high"
::= { traps 28 }

dc_voltage_high_present TRAP-TYPE
    ENTERPRISE  convertronic
    VARIABLES   {
                  trap_dc_voltage_high_present,
    		          trapLastMessageStringTest,
    	  	        trapLastMessageNbrTest,
    	  	        trapSourceIPTest
    		        }
    DESCRIPTION
        "DC voltage is high"
    -- NMS trap annotation
    --#TYPE "DC voltage is high"
    --#SUMMARY "Failure %d, Text: %s, No: %d."
    --#ARGUMENTS {0,1,2}
    --#SEVERITY MAJOR
    --#TIMEINDEX 99
    --#STATE OPERATIONAL    
    ::= 27
    
-- 
-- fan_error_present NOTIFICATION-TYPE
--   STATUS    mandatory
--   DESCRIPTION "Fan is in error-state"
-- ::= { traps 29 }

trap_fan_error_present OBJECT-TYPE
  SYNTAX INTEGER(0..1) 
  ACCESS not-accessible
  STATUS mandatory
  DESCRIPTION "STS Fan is in error-state"
::= { traps 29 }

fan_error_present TRAP-TYPE
    ENTERPRISE  convertronic
    VARIABLES   {
                  trap_fan_error_present,
    		          trapLastMessageStringTest,
    	  	        trapLastMessageNbrTest,
    	  	        trapSourceIPTest
    		        }
    DESCRIPTION
        "Fan is in error-state"
    -- NMS trap annotation
    --#TYPE "Fan is in error-state"
    --#SUMMARY "Failure %d, Text: %s, No: %d."
    --#ARGUMENTS {0,1,2}
    --#SEVERITY MAJOR
    --#TIMEINDEX 99
    --#STATE OPERATIONAL    
    ::= 28
  
-- 
-- uout_low_present NOTIFICATION-TYPE
--   STATUS    mandatory
--   DESCRIPTION "STS outputvoltage is low"
-- ::= { traps 30 }

trap_uout_low_present OBJECT-TYPE
  SYNTAX INTEGER(0..1) 
  ACCESS not-accessible
  STATUS mandatory
  DESCRIPTION "STS outputvoltage is low"
::= { traps 30 }

uout_low_present TRAP-TYPE
    ENTERPRISE  convertronic
    VARIABLES   {
                  trap_uout_low_present,
    		          trapLastMessageStringTest,
    	  	        trapLastMessageNbrTest,
    	  	        trapSourceIPTest
    		        }
    DESCRIPTION
        "STS outputvoltage is low"
    -- NMS trap annotation
    --#TYPE "STS outputvoltage is low"
    --#SUMMARY "Failure %d, Text: %s, No: %d."
    --#ARGUMENTS {0,1,2}
    --#SEVERITY MAJOR
    --#TIMEINDEX 99
    --#STATE OPERATIONAL    
    ::= 29
    
-- 
-- u_batterie_lower_warning_present NOTIFICATION-TYPE
--   STATUS    mandatory
--   DESCRIPTION "Battery voltage is lower warninglevel"
-- ::= { traps 31 }

trap_u_batterie_lower_warning_present OBJECT-TYPE
  SYNTAX INTEGER(0..1) 
  ACCESS not-accessible
  STATUS mandatory
  DESCRIPTION "STS Battery voltage is lower warninglevel"
::= { traps 31 }

u_batterie_lower_warning_present TRAP-TYPE
    ENTERPRISE  convertronic
    VARIABLES   {
                  trap_u_batterie_lower_warning_present,
    		          trapLastMessageStringTest,
    	  	        trapLastMessageNbrTest,
    	  	        trapSourceIPTest
    		        }
    DESCRIPTION
        "Battery voltage is lower warninglevel"
    -- NMS trap annotation
    --#TYPE "Battery voltage is lower warninglevel"
    --#SUMMARY "Failure %d, Text: %s, No: %d."
    --#ARGUMENTS {0,1,2}
    --#SEVERITY MINOR
    --#TIMEINDEX 99
    --#STATE OPERATIONAL    
    ::= 30

-- 
-- u_batterie_higher_warning_present NOTIFICATION-TYPE
--   STATUS    mandatory
--   DESCRIPTION "Battery voltage is higher warninglevel"
-- ::= { traps 32 }

trap_u_batterie_higher_warning_present OBJECT-TYPE
  SYNTAX INTEGER(0..1) 
  ACCESS not-accessible
  STATUS mandatory
  DESCRIPTION "Battery voltage is higher warninglevel"
::= { traps 32 }

u_batterie_higher_warning_present TRAP-TYPE
    ENTERPRISE  convertronic
    VARIABLES   {
                  trap_u_batterie_higher_warning_present,
    		          trapLastMessageStringTest,
    	  	        trapLastMessageNbrTest,
    	  	        trapSourceIPTest
    		        }
    DESCRIPTION
        "Battery voltage is higher warninglevel"
    -- NMS trap annotation
    --#TYPE "Battery voltage is higher warninglevel"
    --#SUMMARY "Failure %d, Text: %s, No: %d."
    --#ARGUMENTS {0,1,2}
    --#SEVERITY MINOR
    --#TIMEINDEX 99
    --#STATE OPERATIONAL    
    ::= 31
    
-- 
-- source_mains_failure_removed NOTIFICATION-TYPE
--   STATUS    mandatory
--   DESCRIPTION "Error with Source mains, state is not active"
-- ::= { traps 33 }

trap_source_mains_failure_removed OBJECT-TYPE
  SYNTAX INTEGER(0..1) 
  ACCESS not-accessible
  STATUS mandatory
  DESCRIPTION "Error with Source mains, state is not active"
::= { traps 33 }

source_mains_failure_removed TRAP-TYPE
    ENTERPRISE  convertronic
    VARIABLES   {
                  trap_source_mains_failure_removed,
    		          trapLastMessageStringTest,
    	  	        trapLastMessageNbrTest,
    	  	        trapSourceIPTest
    		        }
    DESCRIPTION
        "Error with Source mains, state is not active"
    -- NMS trap annotation
    --#TYPE "Error with Source mains, state is not active"
    --#SUMMARY "OK %d, Text: %s, No: %d."
    --#ARGUMENTS {0,1,2}
    --#SEVERITY INFORMATIONAL
    --#TIMEINDEX 99
    --#STATE OPERATIONAL    
    ::= 32
    
-- 
-- source_inverter_failure_removed NOTIFICATION-TYPE
--   STATUS    mandatory
--   DESCRIPTION "Error with Source inverter present, state is not active"
-- ::= { traps 34 }

trap_source_inverter_failure_removed OBJECT-TYPE
  SYNTAX INTEGER(0..1) 
  ACCESS not-accessible
  STATUS mandatory
  DESCRIPTION "Error with Source inverter present, state is not active"
::= { traps 34 }

source_inverter_failure_removed TRAP-TYPE
    ENTERPRISE  convertronic
    VARIABLES   {
                  trap_source_inverter_failure_removed,
    		          trapLastMessageStringTest,
    	  	        trapLastMessageNbrTest,
    	  	        trapSourceIPTest
    		        }
    DESCRIPTION
        "Error with Source inverter present, state is not active"
    -- NMS trap annotation
    --#TYPE "Error with Source inverter present, state is not active"
    --#SUMMARY "OK %d, Text: %s, No: %d."
    --#ARGUMENTS {0,1,2}
    --#SEVERITY INFORMATIONAL
    --#TIMEINDEX 99
    --#STATE OPERATIONAL    
    ::= 33
    
-- 
-- syncronisation_error_removed NOTIFICATION-TYPE
--   STATUS    mandatory
--   DESCRIPTION "Syncronisation between Source Mains and Source Inverter lost, state is not active"
-- ::= { traps 35 }

trap_syncronisation_error_removed OBJECT-TYPE
  SYNTAX INTEGER(0..1) 
  ACCESS not-accessible
  STATUS mandatory
  DESCRIPTION "Syncronisation between Source Mains and Source Inverter lost, state is not active"
::= { traps 35 }

syncronisation_error_removed TRAP-TYPE
    ENTERPRISE  convertronic
    VARIABLES   {
                  trap_syncronisation_error_removed,
    		          trapLastMessageStringTest,
    	  	        trapLastMessageNbrTest,
    	  	        trapSourceIPTest
    		        }
    DESCRIPTION
        "Syncronisation between Source Mains and Source Inverter lost, state is not active"
    -- NMS trap annotation
    --#TYPE "Syncronisation between Source Mains and Source Inverter lost, state is not active"
    --#SUMMARY "OK %d, Text: %s, No: %d."
    --#ARGUMENTS {0,1,2}
    --#SEVERITY INFORMATIONAL
    --#TIMEINDEX 99
    --#STATE OPERATIONAL    
    ::= 34
    
-- 
-- inverter_failure_removed NOTIFICATION-TYPE
--   STATUS    mandatory
--   DESCRIPTION "Inverter failure, state is not active"
-- ::= { traps 36 }

trap_inverter_failure_removed OBJECT-TYPE
  SYNTAX INTEGER(0..1) 
  ACCESS not-accessible
  STATUS mandatory
  DESCRIPTION "Inverter failure, state is not active"
::= { traps 36 }

inverter_failure_removed TRAP-TYPE
    ENTERPRISE  convertronic
    VARIABLES   {
                  trap_inverter_failure_removed,
    		          trapLastMessageStringTest,
    	  	        trapLastMessageNbrTest,
    	  	        trapSourceIPTest
    		        }
    DESCRIPTION
        "Inverter failure, state is not active"
    -- NMS trap annotation
    --#TYPE "Inverter failure, state is not active"
    --#SUMMARY "OK %d, Text: %s, No: %d."
    --#ARGUMENTS {0,1,2}
    --#SEVERITY INFORMATIONAL
    --#TIMEINDEX 99
    --#STATE OPERATIONAL    
    ::= 35
    
-- 
-- no_redundant_inverter_removed NOTIFICATION-TYPE
--   STATUS    mandatory
--   DESCRIPTION "No more redundant inverter present, state is not active"
-- ::= { traps 37 }

trap_no_redundant_inverter_removed OBJECT-TYPE
  SYNTAX INTEGER(0..1) 
  ACCESS not-accessible
  STATUS mandatory
  DESCRIPTION "No more redundant inverter present, state is not active"
::= { traps 37 }

no_redundant_inverter_removed TRAP-TYPE
    ENTERPRISE  convertronic
    VARIABLES   {
                  trap_no_redundant_inverter_removed,
    		          trapLastMessageStringTest,
    	  	        trapLastMessageNbrTest,
    	  	        trapSourceIPTest
    		        }
    DESCRIPTION
        "No more redundant inverter present, state is not active"
    -- NMS trap annotation
    --#TYPE "No more redundant inverter present, state is not active"
    --#SUMMARY "OK %d, Text: %s, No: %d."
    --#ARGUMENTS {0,1,2}
    --#SEVERITY INFORMATIONAL
    --#TIMEINDEX 99
    --#STATE OPERATIONAL    
    ::= 36

-- 
-- critical_inverter_quantity_removed NOTIFICATION-TYPE
--   STATUS    mandatory
--   DESCRIPTION "Inverter quantity is lower than needed, state is not active"
-- ::= { traps 38 }

trap_critical_inverter_quantity_removed OBJECT-TYPE
  SYNTAX INTEGER(0..1) 
  ACCESS not-accessible
  STATUS mandatory
  DESCRIPTION "Inverter quantity is lower than needed, state is not active"
::= { traps 38 }

critical_inverter_quantity_removed TRAP-TYPE
    ENTERPRISE  convertronic
    VARIABLES   {
                  trap_critical_inverter_quantity_removed,
    		          trapLastMessageStringTest,
    	  	        trapLastMessageNbrTest,
    	  	        trapSourceIPTest
    		        }
    DESCRIPTION
        "Inverter quantity is lower than needed, state is not active"
    -- NMS trap annotation
    --#TYPE "Inverter quantity is lower than needed, state is not active"
    --#SUMMARY "OK %d, Text: %s, No: %d."
    --#ARGUMENTS {0,1,2}
    --#SEVERITY INFORMATIONAL
    --#TIMEINDEX 99
    --#STATE OPERATIONAL    
    ::= 37
    
-- 
-- sts_overtemperature_removed NOTIFICATION-TYPE
--   STATUS    mandatory
--   DESCRIPTION "STS temperature warning is not active"
-- ::= { traps 39 }

trap_sts_overtemperature_removed OBJECT-TYPE
  SYNTAX INTEGER(0..1) 
  ACCESS not-accessible
  STATUS mandatory
  DESCRIPTION "STS temperature warning is not active"
::= { traps 39 }

sts_overtemperature_removed TRAP-TYPE
    ENTERPRISE  convertronic
    VARIABLES   {
                  trap_sts_overtemperature_removed,
    		          trapLastMessageStringTest,
    	  	        trapLastMessageNbrTest,
    	  	        trapSourceIPTest
    		        }
    DESCRIPTION
        "STS temperature warning is not active"
    -- NMS trap annotation
    --#TYPE "STS temperature warning is not active"
    --#SUMMARY "OK %d, Text: %s, No: %d."
    --#ARGUMENTS {0,1,2}
    --#SEVERITY INFORMATIONAL
    --#TIMEINDEX 99
    --#STATE OPERATIONAL    
    ::= 38
    
-- 
-- sts_overload_removed NOTIFICATION-TYPE
--   STATUS    mandatory
--   DESCRIPTION "STS overload is not active"
-- ::= { traps 40 }

trap_sts_overload_removed OBJECT-TYPE
  SYNTAX INTEGER(0..1) 
  ACCESS not-accessible
  STATUS mandatory
  DESCRIPTION "STS temperature warning is not active"
::= { traps 40 }

sts_overload_removed TRAP-TYPE
    ENTERPRISE  convertronic
    VARIABLES   {
                  trap_sts_overload_removed,
    		          trapLastMessageStringTest,
    	  	        trapLastMessageNbrTest,
    	  	        trapSourceIPTest
    		        }
    DESCRIPTION
        "STS overload is not active"
    -- NMS trap annotation
    --#TYPE "STS overload is not active"
    --#SUMMARY "OK %d, Text: %s, No: %d."
    --#ARGUMENTS {0,1,2}
    --#SEVERITY INFORMATIONAL
    --#TIMEINDEX 99
    --#STATE OPERATIONAL    
    ::= 39
    
-- 
-- inverter_overload_removed NOTIFICATION-TYPE
--   STATUS    mandatory
--   DESCRIPTION "Inverter overload is not active"
-- ::= { traps 41 }

trap_inverter_overload_removed OBJECT-TYPE
  SYNTAX INTEGER(0..1) 
  ACCESS not-accessible
  STATUS mandatory
  DESCRIPTION "Inverter overload is not active"
::= { traps 41 }

inverter_overload_removed TRAP-TYPE
    ENTERPRISE  convertronic
    VARIABLES   {
                  trap_inverter_overload_removed,
    		          trapLastMessageStringTest,
    	  	        trapLastMessageNbrTest,
    	  	        trapSourceIPTest
    		        }
    DESCRIPTION
        "Inverter overload is not active"
    -- NMS trap annotation
    --#TYPE "Inverter overload is not active"
    --#SUMMARY "OK %d, Text: %s, No: %d."
    --#ARGUMENTS {0,1,2}
    --#SEVERITY INFORMATIONAL
    --#TIMEINDEX 99
    --#STATE OPERATIONAL    
    ::= 40
    
-- 
-- sts_current_need_redandancy_removed NOTIFICATION-TYPE
--   STATUS    mandatory
--   DESCRIPTION "STS actual current do not need an redundant inverter"
-- ::= { traps 42 }

trap_sts_current_need_redandancy_removed OBJECT-TYPE
  SYNTAX INTEGER(0..1) 
  ACCESS not-accessible
  STATUS mandatory
  DESCRIPTION "STS actual current do not need an redundant inverter"
::= { traps 42 }

sts_current_need_redandancy_removed TRAP-TYPE
    ENTERPRISE  convertronic
    VARIABLES   {
                  trap_sts_current_need_redandancy_removed,
    		          trapLastMessageStringTest,
    	  	        trapLastMessageNbrTest,
    	  	        trapSourceIPTest
    		        }
    DESCRIPTION
        "STS actual current do not need an redundant inverter"
    -- NMS trap annotation
    --#TYPE "STS actual current do not need an redundant inverter"
    --#SUMMARY "OK %d, Text: %s, No: %d."
    --#ARGUMENTS {0,1,2}
    --#SEVERITY INFORMATIONAL
    --#TIMEINDEX 99
    --#STATE OPERATIONAL    
    ::= 41
    
-- 
-- dc_voltage_low_removed NOTIFICATION-TYPE
--   STATUS    mandatory
--   DESCRIPTION "DC voltage is low, state is not active"
-- ::= { traps 43 }

trap_dc_voltage_low_removed OBJECT-TYPE
  SYNTAX INTEGER(0..1) 
  ACCESS not-accessible
  STATUS mandatory
  DESCRIPTION "DC voltage is low, state is not active"
::= { traps 43 }

dc_voltage_low_removed TRAP-TYPE
    ENTERPRISE  convertronic
    VARIABLES   {
                  trap_dc_voltage_low_removed,
    		          trapLastMessageStringTest,
    	  	        trapLastMessageNbrTest,
    	  	        trapSourceIPTest
    		        }
    DESCRIPTION
        "DC voltage is low, state is not active"
    -- NMS trap annotation
    --#TYPE "DC voltage is low, state is not active"
    --#SUMMARY "OK %d, Text: %s, No: %d."
    --#ARGUMENTS {0,1,2}
    --#SEVERITY INFORMATIONAL
    --#TIMEINDEX 99
    --#STATE OPERATIONAL    
    ::= 42
    
-- 
-- dc_voltage_high_added_removed NOTIFICATION-TYPE
--   STATUS    mandatory
--   DESCRIPTION "DC voltage is high, state is not active"
-- ::= { traps 44 }

trap_dc_voltage_high_added_removed OBJECT-TYPE
  SYNTAX INTEGER(0..1) 
  ACCESS not-accessible
  STATUS mandatory
  DESCRIPTION "DC voltage is high, state is not active"
::= { traps 44 }

dc_voltage_high_added_removed TRAP-TYPE
    ENTERPRISE  convertronic
    VARIABLES   {
                  trap_dc_voltage_high_added_removed,
    		          trapLastMessageStringTest,
    	  	        trapLastMessageNbrTest,
    	  	        trapSourceIPTest
    		        }
    DESCRIPTION
        "DC voltage is high, state is not active"
    -- NMS trap annotation
    --#TYPE "DC voltage is high, state is not active"
    --#SUMMARY "OK %d, Text: %s, No: %d."
    --#ARGUMENTS {0,1,2}
    --#SEVERITY INFORMATIONAL
    --#TIMEINDEX 99
    --#STATE OPERATIONAL    
    ::= 43
    
-- 
-- fan_error_removed NOTIFICATION-TYPE
--   STATUS    mandatory
--   DESCRIPTION "Fan is not in error-state"
-- ::= { traps 45 }

trap_fan_error_removed OBJECT-TYPE
  SYNTAX INTEGER(0..1) 
  ACCESS not-accessible
  STATUS mandatory
  DESCRIPTION "Fan is not in error-state"
::= { traps 45 }

fan_error_removed TRAP-TYPE
    ENTERPRISE  convertronic
    VARIABLES   {
                  trap_fan_error_removed,
    		          trapLastMessageStringTest,
    	  	        trapLastMessageNbrTest,
    	  	        trapSourceIPTest
    		        }
    DESCRIPTION
        "Fan is not in error-state"
    -- NMS trap annotation
    --#TYPE "Fan is not in error-state"
    --#SUMMARY "OK %d, Text: %s, No: %d."
    --#ARGUMENTS {0,1,2}
    --#SEVERITY INFORMATIONAL
    --#TIMEINDEX 99
    --#STATE OPERATIONAL    
    ::= 44
    
-- 
-- uout_low_removed NOTIFICATION-TYPE
--   STATUS    mandatory
--   DESCRIPTION "STS outputvoltage is low, state is not active"
-- ::= { traps 46 }

trap_uout_low_removed OBJECT-TYPE
  SYNTAX INTEGER(0..1) 
  ACCESS not-accessible
  STATUS mandatory
  DESCRIPTION "STS outputvoltage is low, state is not active"
::= { traps 46 }

uout_low_removed TRAP-TYPE
    ENTERPRISE  convertronic
    VARIABLES   {
                  trap_uout_low_removed,
    		          trapLastMessageStringTest,
    	  	        trapLastMessageNbrTest,
    	  	        trapSourceIPTest
    		        }
    DESCRIPTION
        "STS outputvoltage is low, state is not active"
    -- NMS trap annotation
    --#TYPE "STS outputvoltage is low, state is not active"
    --#SUMMARY "OK %d, Text: %s, No: %d."
    --#ARGUMENTS {0,1,2}
    --#SEVERITY INFORMATIONAL
    --#TIMEINDEX 99
    --#STATE OPERATIONAL    
    ::= 45
    
-- 
-- u_batterie_lower_warning_removed NOTIFICATION-TYPE
--   STATUS    mandatory
--   DESCRIPTION "Battery voltage is lower warninglevel, state is not active"
-- ::= { traps 47 }

trap_u_batterie_lower_warning_removed OBJECT-TYPE
  SYNTAX INTEGER(0..1) 
  ACCESS not-accessible
  STATUS mandatory
  DESCRIPTION "Battery voltage is lower warninglevel, state is not active"
::= { traps 47 }

u_batterie_lower_warning_removed TRAP-TYPE
    ENTERPRISE  convertronic
    VARIABLES   {
                  trap_u_batterie_lower_warning_removed,
    		          trapLastMessageStringTest,
    	  	        trapLastMessageNbrTest,
    	  	        trapSourceIPTest
    		        }
    DESCRIPTION
        "Battery voltage is lower warninglevel, state is not active"
    -- NMS trap annotation
    --#TYPE "Battery voltage is lower warninglevel, state is not active"
    --#SUMMARY "OK %d, Text: %s, No: %d."
    --#ARGUMENTS {0,1,2}
    --#SEVERITY INFORMATIONAL
    --#TIMEINDEX 99
    --#STATE OPERATIONAL    
    ::= 46

-- 
-- u_batterie_higher_warning_removed NOTIFICATION-TYPE
--   STATUS    mandatory
--   DESCRIPTION "Battery voltage is higher warninglevel, state is not active"
-- ::= { traps 48 }

trap_u_batterie_higher_warning_removed OBJECT-TYPE
  SYNTAX INTEGER(0..1) 
  ACCESS not-accessible
  STATUS mandatory
  DESCRIPTION "Battery voltage is higher warninglevel, state is not active"
::= { traps 48 }

u_batterie_higher_warning_removed TRAP-TYPE
    ENTERPRISE  convertronic
    VARIABLES   {
                  trap_u_batterie_higher_warning_removed,
    		          trapLastMessageStringTest,
    	  	        trapLastMessageNbrTest,
    	  	        trapSourceIPTest
    		        }
    DESCRIPTION
        "Battery voltage is higher warninglevel, state is not active"
    -- NMS trap annotation
    --#TYPE "Battery voltage is higher warninglevel, state is not active"
    --#SUMMARY "OK %d, Text: %s, No: %d."
    --#ARGUMENTS {0,1,2}
    --#SEVERITY INFORMATIONAL
    --#TIMEINDEX 99
    --#STATE OPERATIONAL    
    ::= 47

-- ****************************************
-- ****************************************
-- ****************************************

inverter_Table OBJECT-TYPE
  SYNTAX  SEQUENCE OF Inverter_Entry
  ACCESS  not-accessible
  STATUS  mandatory
  DESCRIPTION "Table of CAN-nodes."
::= { inverter_measureValues 1 }

inverter_Entry OBJECT-TYPE
  SYNTAX  Inverter_Entry
  ACCESS  not-accessible
  STATUS  optional
  DESCRIPTION "CAN-node entries."
  INDEX   { inv_Index }
--  INDEX   { index }
::= { inverter_Table 1 }

Inverter_Entry ::=
  SEQUENCE {
inv_Index            INTEGER,
    inv_Nbr            INTEGER,
    inv_InCurrent      INTEGER,
    inv_OutCurrent     INTEGER,
    inv_Temperature    INTEGER,
    inv_InputVoltage   INTEGER,
    inv_STi_great      INTEGER,
    inv_Fan            INTEGER,
    inv_RemoteOffCan   INTEGER,
    inv_UoutOff        INTEGER,
    inv_Bit_ShortCircuit   INTEGER,
    inv_Bit_OutputVoltage  INTEGER,
    inv_Bit_InputVoltLow   INTEGER,
    inv_Bit_InputVoltHigh  INTEGER,
    inv_Bit_OutputVoltLow  INTEGER,
    inv_Bit_OutputVoltHigh INTEGER,
    inv_Bit_OutputCurrHigh INTEGER,
    inv_Bit_RemoteOff      INTEGER,
    inv_Bit_CentralAlarm   INTEGER,
    inv_Type           DisplayString,
    inv_Mat_CD         DisplayString,
    inv_SerialNo          DisplayString,
    inv_HardwareVersion DisplayString,
  inv_SoftwareVersion DisplayString
    }

    inv_Index OBJECT-TYPE
      SYNTAX    INTEGER (1..16)
      UNITS   "NA"
      MAX-ACCESS  not-accessible
      STATUS    current
      DESCRIPTION
          "NA"
      ::= { inverter_Entry 0 }

inv_Nbr OBJECT-TYPE
  SYNTAX  INTEGER (0..15)
  ACCESS  read-only
  STATUS  mandatory
  DESCRIPTION "Inverter Number,
  Value:
  1
  ...
  15"
::= { inverter_Entry 1 }

inv_InCurrent OBJECT-TYPE
  SYNTAX  INTEGER(0..65535)
  ACCESS  read-only
  STATUS  mandatory
  DESCRIPTION "In-Current of the Inverter,
  Value:
  todo"
::= { inverter_Entry 2 }

inv_OutCurrent OBJECT-TYPE
  SYNTAX  INTEGER (0..65535)
  ACCESS  read-only
  STATUS  mandatory
  DESCRIPTION "Out-Current of the Inverter,
    Value:
  todo"
::= { inverter_Entry 3 }

inv_Temperature OBJECT-TYPE
  SYNTAX  INTEGER (0..65535)
  ACCESS  read-only
  STATUS  mandatory
  DESCRIPTION "Temperature of the Inverter,
  Value:
  todo"
::= { inverter_Entry 4 }

inv_InputVoltage OBJECT-TYPE
  SYNTAX  INTEGER (0..65535)
  ACCESS  read-only
  STATUS  mandatory
  DESCRIPTION "Input Voltage of the Inverter,
  Value:
  todo"
::= { inverter_Entry 5 }

inv_STi_great OBJECT-TYPE
  SYNTAX  INTEGER (0..1)
  ACCESS  read-only
  STATUS  mandatory
  DESCRIPTION "Internal temperature high,
  Value:
  0= < limit
  1= > limit"
::= { inverter_Entry 6 }

inv_Fan  OBJECT-TYPE
  SYNTAX  INTEGER (0..1)
  ACCESS  read-only
  STATUS  mandatory
  DESCRIPTION "Fan error,
  Value:
  0= no Error
  1= error active"
::= { inverter_Entry 7 }

inv_RemoteOffCan OBJECT-TYPE
  SYNTAX  INTEGER (0..1)
  ACCESS  read-only
  STATUS  mandatory
  DESCRIPTION "Far off via can-controll,
  Value:
  0= not off
  1= far off is active"
::= { inverter_Entry 8 }

inv_UoutOff OBJECT-TYPE
  SYNTAX  INTEGER (0..1)
  ACCESS  read-only
  STATUS  mandatory
  DESCRIPTION "State of Output voltage,
  Value:
  0= voltage is on
  1= voltage shut down"
::= { inverter_Entry 9 }

inv_Bit_ShortCircuit OBJECT-TYPE
  SYNTAX  INTEGER (0..1)
  ACCESS  read-only
  STATUS  mandatory
  DESCRIPTION "Short circuit is present,
  Value:
  0= normal operation
  1= Short circuit"
::= { inverter_Entry 10 }

inv_Bit_OutputVoltage OBJECT-TYPE
  SYNTAX  INTEGER (0..1)
  ACCESS  read-only
  STATUS  mandatory
  DESCRIPTION "State of the output voltage,
  Value:
  0= voltage off, error state
  1= voltage ok,normal operation"
::= { inverter_Entry 11 }

inv_Bit_InputVoltLow OBJECT-TYPE
  SYNTAX  INTEGER (0..1)
  ACCESS  read-only
  STATUS  mandatory
  DESCRIPTION "Input voltage reached lover limit,
  Value:
  0= normal operation
  1= error present"
::= { inverter_Entry 12 }

inv_Bit_InputVoltHigh OBJECT-TYPE
  SYNTAX  INTEGER (0..1)
  ACCESS  read-only
  STATUS  mandatory
  DESCRIPTION "Input voltage reached upper limit,
  Value:
  0= normal operation
  1= error present"
::= { inverter_Entry 13 }

inv_Bit_OutputVoltLow OBJECT-TYPE
  SYNTAX  INTEGER (0..1)
  ACCESS  read-only
  STATUS  mandatory
  DESCRIPTION "Output voltage reached lower limit,
  Value:
  0= normal operation
  1= error present"
::= { inverter_Entry 14 }

inv_Bit_OutputVoltHigh OBJECT-TYPE
  SYNTAX  INTEGER (0..1)
  ACCESS  read-only
  STATUS  mandatory
  DESCRIPTION "Output voltage reached upper limit,
  Value:
  0= normal operation
  1= error present"
::= { inverter_Entry 15 }

inv_Bit_OutputCurrHigh OBJECT-TYPE
  SYNTAX  INTEGER (0..1)
  ACCESS  read-only
  STATUS  mandatory
  DESCRIPTION "Output current reached upper limit,
  Value:
  0= normal operation
  1= error present"
::= { inverter_Entry 16 }

inv_Bit_RemoteOff OBJECT-TYPE
  SYNTAX  INTEGER (0..1)
  ACCESS  read-only
  STATUS  mandatory
  DESCRIPTION "Inverter has shut-down,
  Value:
  0= normal operation
  1= shut-down"
::= { inverter_Entry 17 }

inv_Bit_CentralAlarm OBJECT-TYPE
  SYNTAX  INTEGER (0..1)
  ACCESS  read-only
  STATUS  mandatory
  DESCRIPTION "Central alarm has triggert,
  Value:
  0= normal operation
  1= error present"
::= { inverter_Entry 18 }

inv_Type OBJECT-TYPE
  SYNTAX  DisplayString (SIZE (0..16))
  ACCESS  read-only
  STATUS  mandatory
  DESCRIPTION "Type description"
::= { inverter_Entry 19 }

inv_Mat_CD OBJECT-TYPE
  SYNTAX  DisplayString (SIZE (0..16))
  ACCESS  read-only
  STATUS  mandatory
  DESCRIPTION "Order number"
::= { inverter_Entry 20 }

inv_SerialNo OBJECT-TYPE
  SYNTAX  DisplayString (SIZE (0..16))
  ACCESS  read-only
  STATUS  mandatory
  DESCRIPTION "Serial number"
::= { inverter_Entry 21 }

inv_HardwareVersion OBJECT-TYPE
  SYNTAX  DisplayString (SIZE (0..8))
  ACCESS  read-only
  STATUS  mandatory
  DESCRIPTION "Hardware version"
::= { inverter_Entry 22 }

inv_SoftwareVersion OBJECT-TYPE
  SYNTAX  DisplayString (SIZE (0..8))
  ACCESS  read-only
  STATUS  mandatory
  DESCRIPTION "Software Version"
::= { inverter_Entry 23 }
-- ****************************************
-- ****************************************
-- ****************************************
-- History

historyTable OBJECT-TYPE
  SYNTAX  SEQUENCE OF HistoryEntry
  ACCESS  not-accessible
  STATUS  mandatory
  DESCRIPTION "Table of last 20 history events."
::= { tables 1 }

historyEntry OBJECT-TYPE
  SYNTAX  HistoryEntry
  ACCESS  not-accessible
  STATUS  optional
  DESCRIPTION "History values entries."
  INDEX   { histIndex }
--  INDEX   { index }
::= { historyTable 1 }

HistoryEntry ::=
 SEQUENCE {
  histIndex    INTEGER,
  histInd      INTEGER,
  histDateTime INTEGER,
  histEvent    INTEGER,
  histDescription DisplayString
  }

histIndex OBJECT-TYPE
  SYNTAX  INTEGER (1..20)
  UNITS   "NA"
  MAX-ACCESS  not-accessible
  STATUS    current
  DESCRIPTION "Index"
::= { historyEntry 0 }

histInd OBJECT-TYPE
  SYNTAX  INTEGER (1..65535)
  ACCESS  read-only
  STATUS  mandatory
  DESCRIPTION "Index"
::= { historyEntry 1 }

histDateTime OBJECT-TYPE
  SYNTAX  INTEGER(0..400000000)
  ACCESS  read-only
  STATUS  mandatory
  DESCRIPTION "Date and time of event in UNIX notation"
::= { historyEntry 2 }

histEvent OBJECT-TYPE
  SYNTAX  INTEGER (1..65535)
  ACCESS  read-only
  STATUS  mandatory
  DESCRIPTION "History event"
::= { historyEntry 3 }

--histDescription OBJECT-TYPE
--  SYNTAX  DisplayString (SIZE (0..16))
--  ACCESS  read-only
--  STATUS  mandatory
--  DESCRIPTION "textual description of event"
--::= { historyEntry 4 }

END
