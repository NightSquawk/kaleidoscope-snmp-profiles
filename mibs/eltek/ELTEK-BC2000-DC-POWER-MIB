ELTEK-BC2000-DC-POWER-MIB DEFINITIONS ::= BEGIN

    IMPORTS
         MODULE-IDENTITY 
       , OBJECT-TYPE 
       , NOTIFICATION-TYPE
       , OBJECT-IDENTITY 
       , Counter32
       , Gauge32 
       , Integer32 
       , enterprises 
       , IpAddress 
       -- , Gauge
            FROM SNMPv2-SMI 
           
         Gauge 
            FROM RFC1155-SMI

         DisplayString 
       , TimeStamp 
--        , TimeInterval 
--        , TestAndIncr
       , AutonomousType 
       , TEXTUAL-CONVENTION
            FROM SNMPv2-TC
           
--          MODULE-COMPLIANCE 
--        , OBJECT-GROUP
--             FROM SNMPv2-CONF

--        sysUpTime
--            FROM RFC1213-MIB
        ;
           
    --
    -- date and time in UTC format YYYYMMDDHHmmZ
    --
       eltek    MODULE-IDENTITY
                        LAST-UPDATED "201403271038Z"
                        ORGANIZATION "Eltek Inc."
                        CONTACT-INFO
                             "Contact: Eltek Customer Support
                              Postal:  2925 E. Plano Pkwy
                                       Plano, TX-75074
                              Web:     http://www.eltek.com
                              email:   techsupport.us@eltek.com
                              Phone    800-435-4872
                             "
                        DESCRIPTION
                            "SNMP access to Eltek DC Power systems through the BC2000 controller."
                        REVISION     "201403271038Z"
                        DESCRIPTION
                        " Need History  here.
                        MIB Version 2.10
                          Final edits to PM (was TRIO) table (branch 17)
                        MIB Version 2.00
                            Synchronized with new release
                        MIB Version 0.97
                            Updated contact information
                        MIB Version 0.96
                            Changed LVD Timers to read-only. Write not supported in this release
                        MIB Version 0.95
                            Traps 70-72 added
                            Changed vpwrPMIndex variable to non negative integer
                        MIB Version 0.94
                            Fixed module inventory process
                            Removed unused module test groups
                            Removed unused thermal probe entries
                            Changed vpwrBoostDuration from Hours to Seconds
                            New traps 63-69 added, trap 99 unknown added
                            Corrected Ringer present MIB
                        MIB Version 0.93
                            Fixed spelling of vpwrBatteryCurrentCapacity
                            Fixed spelling of vpwrRingerAlarmAFailed
                            Fixed spelling of vpwrRingerAlarmBFailed
                            Fixed message with vpwrRingerAlarmBOverTemp
                            Fixed message with vpwrRingerAlarmBOverCurrent
                            Changed Centigrade to Celsius
                            Changed use of battety to battery throughout
                            Changed vpwrBDTDuration from 480 minutes to 1080
                            Updated settable ringer parameters
                            Spelling corrections
                        MIB Version 0.92
                            Fixed duplicate usage of  vpwrTrapsMsgString
                            Fixed spelling of Gauge data type
                        MIB Version 0.91
                            Version 2 Traps
                        MIB Version 0.9
                            Sept 1, 06
                                New Table- System Alarm History
                                New Table- for BDT Result History
                                New Table- for AVESTOR Battery

                                New Traps -
                                Aux Alarm Source
                                Distribution Alarm Source
                                Battery Capacity Alarm
                                Battery Alarm Source
                                Battery SOC Trap
                                Battery SOH Trap
                                AC Fail Duration Trap
                                Battery Operational mode change

                        MIB Version 0.8
                            Add table to retrieve module inventory info
                        MIB Version 0.7
                            Dec 1, 05        
                                Fixed HP Openview error
                                Fixed warnings generated by MG-SOFT
                                Add table to retrieve rectifier inventory info
                        MIB Version 0.6                
                            Feb 10, 2004  Added additional traps.
                                Defined Ringers and other modules.
                            Feb 08, 2003  Changed vpwrTrapDestinationTable to vpwrTrapTable
                                Corrected entry for vpwrTrapTable to be VpwrTrapTableEntry
                                This fixes errors generated by MG-SOFT mib compiler.
                            Oct 30, 2002  initial release - version 0.4
                        "

                        ::= {enterprises 13858}

PositiveInteger ::= TEXTUAL-CONVENTION
   DISPLAY-HINT "d"
   STATUS       current
   DESCRIPTION
           "This data type is a non-zero and non-negative value."
   SYNTAX       Integer32 (1..2147483647)

NonNegativeInteger ::= TEXTUAL-CONVENTION
   DISPLAY-HINT "d"
   STATUS       current
   DESCRIPTION
           "This data type is a non-negative value."
   SYNTAX       Integer32 (0..2147483647)

GenericEnableDisableTC ::= TEXTUAL-CONVENTION
    STATUS       current
    DESCRIPTION
      "The defines how was BDT started."
    SYNTAX       INTEGER {
                    disabled(0),
                    enabled(1)
                  }

SysInputValue ::= TEXTUAL-CONVENTION
    STATUS       current
    DESCRIPTION
      "These are the results of the system input value definitions."
    SYNTAX INTEGER {
        disabled(-127),
        removed(-126),
        shorted(-125),
        auxAlarm(-124),
        auxNormal(-123),
        distAlarm(-122),
        distNormal(-121),
        undefined(255)
        -- (0..127)
        }

-- BatteryOperModeTC ::= TEXTUAL-CONVENTION
--     STATUS       current
--     DESCRIPTION
--       "The defines operational mode enumerations for the battery."
--     SYNTAX INTEGER {
--                    batModeStandby (0),
--                    batModeCharging(1),
--                    batModeFloating(2),
--                    batModeDischarging(3),
--                    batModeNotAvailable(255)
--                   }

VpwrPMCnfgValue ::= TEXTUAL-CONVENTION
    STATUS       current
    DESCRIPTION
      "These are the results of the system input value definitions."
    SYNTAX INTEGER {
        disabled(0),
        tProbe(1),
        auxNO(2),
        auxNC(3),
        distNO(4),
        distNC(5),
        undefined(255)
        }


-- BatteryOperStatusTC ::= TEXTUAL-CONVENTION
--     STATUS       current
--     DESCRIPTION
--       "The defines operational mode 
--        enumerations for the battery."
--     SYNTAX       INTEGER {
--                    batStatusOk (0),
--                    batStatusMinorFault(1),
--                    batStatusMajorFault(2),
--                    batStatusNotAvailable(255)
--                   }


BDTStartSourceTC ::= TEXTUAL-CONVENTION
    STATUS       current
    DESCRIPTION
      "The defines how was BDT started."
    SYNTAX       INTEGER {
                    bdtInactive(0),
                    bdtManualStart(1),
                    bdtSched01Start1(2),
                    bdtSched02Start2(3),
                    bdtSched03Start3(4),
                    bdtSched04Start4(5),
                    bdtSched05Start5(6),
                    bdtSched06Start6(7),
                    bdtSched07Start7(8),
                    bdtSched08Start8(9),
                    bdtSched09Start9(10),
                    bdtSched10Start10(11),
                    bdtSched11Start11(12),
                    bdtSched12Start12(13),
                    bdtACFailStart(14)
                  }
BDTResultTC ::= TEXTUAL-CONVENTION
    STATUS       current
    DESCRIPTION
      "The defines how was BDT started."
    SYNTAX       INTEGER {
                    bdtResultCleared(0),
                    bdtResultPassed(1),
                    bdtResultFailed(2),
                    bdtResultStopped(3),
                    bdtResultAborted(4),
                    bdtResultInProgress(5)
                  }


--        vpwrDcPowerProducts         OBJECT IDENTIFIER ::=  { eltek 1 }
       vpwrDcPowerSystem           OBJECT IDENTIFIER ::=  { eltek 2 }
       vpwrDcPowerRectifier        OBJECT IDENTIFIER ::=  { eltek 3 }
       vpwrDcPowerLvd              OBJECT IDENTIFIER ::=  { eltek 4 }
--       vpwrDcPowerTest             OBJECT IDENTIFIER ::=  { eltek 5 }
       vpwrDcPowerModuleIdent      OBJECT IDENTIFIER ::=  { eltek 6 }
       vpwrDcPowerBatteryGroup     OBJECT IDENTIFIER ::=  { eltek 7 }
       vpwrDcPowerAlarmGroup       OBJECT IDENTIFIER ::=  { eltek 8 }
       vpwrDcPowerSnmpConfig       OBJECT IDENTIFIER ::=  { eltek 9 }
       vpwrDcPowerTraps            OBJECT IDENTIFIER ::=  { eltek 10 }
       vpwrDcPowerTrapVars         OBJECT IDENTIFIER ::=  { eltek 11 }

       vpwrDcPowerRinger           OBJECT IDENTIFIER ::=  { eltek 12 }
       vpwrDcPowerDcDcConverter    OBJECT IDENTIFIER ::=  { eltek 13 }
       vpwrDcPowerDcAcInverter     OBJECT IDENTIFIER ::=  { eltek 14 }
       vpwrDcPowerAcLineModule     OBJECT IDENTIFIER ::=  { eltek 15 }
       vpwrDcPowerIoModule         OBJECT IDENTIFIER ::=  { eltek 16 }

       vpwrDcPowerPMModule       OBJECT IDENTIFIER ::=  { eltek 17 }
       vpwrDcPowerDistModule       OBJECT IDENTIFIER ::=  { eltek 18 }
       vpwrDcPowerBattery          OBJECT IDENTIFIER ::=  { eltek 19 }
       vpwrDcPowerController       OBJECT IDENTIFIER ::=  { eltek 20 }
       vpwrDcPowerUnkModule        OBJECT IDENTIFIER ::=  { eltek 499 }
       thirdPartyProduct           OBJECT IDENTIFIER ::=  { eltek 500 }

--     vpwrDcPowerTraps            OBJECT IDENTIFIER ::=  { vpwrDcPowerTrapsRoot 0 }

       vpwrSystemIdentGroup        OBJECT IDENTIFIER ::=  { vpwrDcPowerSystem 1 }
       vpwrSystemConfigGroup       OBJECT IDENTIFIER ::=  { vpwrDcPowerSystem 2 }
       vpwrSystemParameterGroup    OBJECT IDENTIFIER ::=  { vpwrDcPowerSystem 3 }
       vpwrSystemPanelIdentGroup   OBJECT IDENTIFIER ::=  { vpwrDcPowerSystem 4 }
       vpwrSystemHistoryGroup      OBJECT IDENTIFIER ::=  { vpwrDcPowerSystem 5 }
       vpwrSystemAlarmGroup        OBJECT IDENTIFIER ::=  { vpwrDcPowerSystem 6 }

       vpwrLvdConfigGroup          OBJECT IDENTIFIER ::=  { vpwrDcPowerLvd 1 }
--        vpwrLvdAlarmGroup           OBJECT IDENTIFIER ::=  { vpwrDcPowerLvd 2 }
--       vpwrLvdTestGroup          OBJECT IDENTIFIER ::=  { vpwrDcPowerLvd 3 }

       vpwrRectifierConfigGroup    OBJECT IDENTIFIER ::=  { vpwrDcPowerRectifier 1 }
       vpwrRectifierAlarmGroup     OBJECT IDENTIFIER ::=  { vpwrDcPowerRectifier 2 }
--       vpwrRectifierTestGroup    OBJECT IDENTIFIER ::=  { vpwrDcPowerRectifier 3 }

       vpwrBatteryTempGroup        OBJECT IDENTIFIER ::=  { vpwrDcPowerBatteryGroup 1 }
       vpwrBatteryCurrentGroup     OBJECT IDENTIFIER ::=  { vpwrDcPowerBatteryGroup 2 }
       vpwrBatteryBoostGroup       OBJECT IDENTIFIER ::=  { vpwrDcPowerBatteryGroup 3 }
       vpwrBatteryDischargeTestGroup OBJECT IDENTIFIER ::=  { vpwrDcPowerBatteryGroup 4 }

--       vpwrTrapsMsgString        OBJECT IDENTIFIER ::=  { vpwrDcPowerTrapVars 1 }

       vpwrRingerConfigGroup       OBJECT IDENTIFIER ::=  { vpwrDcPowerRinger 1 }
       vpwrRingerAlarmGroup        OBJECT IDENTIFIER ::=  { vpwrDcPowerRinger 2 }
       vpwrRingerTestGroup         OBJECT IDENTIFIER ::=  { vpwrDcPowerRinger 3 }

       vpwrDcDcConverterConfigGroup  OBJECT IDENTIFIER ::=  { vpwrDcPowerDcDcConverter 1 }
       vpwrDcDcConverterAlarmGroup   OBJECT IDENTIFIER ::=  { vpwrDcPowerDcDcConverter 2 }
       vpwrDcDcConverterTestGroup    OBJECT IDENTIFIER ::=  { vpwrDcPowerDcDcConverter 3 }


       vpwrDcAcInverterConfigGroup   OBJECT IDENTIFIER ::=  { vpwrDcPowerDcAcInverter 1 }
       vpwrDcAcInverterAlarmGroup    OBJECT IDENTIFIER ::=  { vpwrDcPowerDcAcInverter 2 }
       vpwrDcAcInverterTestGroup     OBJECT IDENTIFIER ::=  { vpwrDcPowerDcAcInverter 3 }

       vpwrAcLineModuleConfigGroup   OBJECT IDENTIFIER ::=  { vpwrDcPowerAcLineModule 1 }
       vpwrAcLineModuleAlarmGroup    OBJECT IDENTIFIER ::=  { vpwrDcPowerAcLineModule 2 }
       vpwrAcLineModuleTestGroup     OBJECT IDENTIFIER ::=  { vpwrDcPowerAcLineModule 3 }

       vpwrIoModuleConfigGroup       OBJECT IDENTIFIER ::=  { vpwrDcPowerIoModule 1 }
       vpwrIoModuleAlarmGroup        OBJECT IDENTIFIER ::=  { vpwrDcPowerIoModule 2 }
       vpwrIoModuleTestGroup         OBJECT IDENTIFIER ::=  { vpwrDcPowerIoModule 3 }

--       vpwrTrioModuleConfigGroup     OBJECT IDENTIFIER ::=  { vpwrDcPowerTrioModule 1 }
       vpwrPMModuleAlarmGroup        OBJECT IDENTIFIER ::=  { vpwrDcPowerPMModule 4 }
       vpwrPMModuleTestGroup         OBJECT IDENTIFIER ::=  { vpwrDcPowerPMModule 5 }

--
--    PM variables
--

--
-- Trap variables
-- 

    vpwrTrapsMsgString  OBJECT-TYPE
                          SYNTAX     DisplayString(SIZE (0..127))
                          MAX-ACCESS read-only
                          STATUS     current
                          DESCRIPTION
                         " Place holder for trap notification message string"
                         ::= { vpwrDcPowerTrapVars 1 }

    vpwrTrapUserIpAddress   OBJECT-TYPE
                                SYNTAX        IpAddress
                                MAX-ACCESS    not-accessible
                                STATUS        current
                                DESCRIPTION
                                   "Place holder for IP address of the user accessing the system"
                           ::= { vpwrDcPowerTrapVars 2}

    vpwrTrapAcfDuration   OBJECT-TYPE
                                SYNTAX        NonNegativeInteger
                                MAX-ACCESS    read-only
                                STATUS        current
                                DESCRIPTION
                                   "Place holder for duration."
                           ::= { vpwrDcPowerTrapVars 3}

    vpwrAlarmingSubModuleBitMap         OBJECT-TYPE
               SYNTAX                  PositiveInteger
               MAX-ACCESS              read-only
               STATUS                  current
               DESCRIPTION
                 "indices of alarming sources are encoded as a bit-map 
                   e.g., 
                   source 1 and source 2 will be encoded as hex 3.
                   source 1 and 3  will be encoded as hex 5.
                 "
               ::= { vpwrDcPowerTrapVars 4 }

    vpwrBatteryCurrentCapacity  OBJECT-TYPE
                          SYNTAX     PositiveInteger
                          MAX-ACCESS read-only
                          STATUS     current
                          DESCRIPTION
                         " Place holder for total battery capacity"
                         ::= { vpwrDcPowerTrapVars 5 }

    vpwrAlarmingModuleIndex     OBJECT-TYPE
               SYNTAX                  PositiveInteger
               MAX-ACCESS              read-only
               STATUS                  current
               DESCRIPTION
                 "index of alarming module.
                 "
               ::= { vpwrDcPowerTrapVars 6 }
    vpwrAlarmingModuleOID        OBJECT-TYPE
               SYNTAX        OBJECT IDENTIFIER
               MAX-ACCESS    read-only
               STATUS        current
               DESCRIPTION
                 "It indicates the type of the module by specifiying its OID"
               ::= { vpwrDcPowerTrapVars 7}

    vpwrAlarmingModuleBitMap         OBJECT-TYPE
               SYNTAX                  PositiveInteger
               MAX-ACCESS              not-accessible
               STATUS                  current
               DESCRIPTION
                 "indices of alarming sources are encoded as a bit-map 
                   e.g., 
                   source 1 and source 2 will be encoded as hex 3.
                   source 1 and 3  will be encoded as hex 5.
                 "
               ::= { vpwrDcPowerTrapVars 8 }

    vpwrBatteryRemainingTime  OBJECT-TYPE
                          SYNTAX     PositiveInteger
                          MAX-ACCESS read-only
                          STATUS     current
                          DESCRIPTION
                         " Place holder for remaining battery
                           time at the current load
                         "
                         ::= { vpwrDcPowerTrapVars 9 }
    --
    -- The Identification group.
    --


    vpwrIdentManufacturer OBJECT-TYPE
       SYNTAX     DisplayString (SIZE (0..31))
       MAX-ACCESS read-only
       STATUS     current
       DESCRIPTION
               "The name of the DC Power manufacturer."
       ::= { vpwrSystemIdentGroup 1 }


    vpwrIdentModel OBJECT-TYPE
       SYNTAX     DisplayString (SIZE (0..15))
       MAX-ACCESS read-only
       STATUS     current
       DESCRIPTION
               "The DC Power Model designation."
       ::= { vpwrSystemIdentGroup 2 }

    vpwrIdentControllerVersion OBJECT-TYPE
       SYNTAX     DisplayString (SIZE (0..15))
       MAX-ACCESS read-only
       STATUS     current
       DESCRIPTION
               "The hardware/firmware version(s).  This variable
               may or may not have the same value as
               vpwrIdentAgentSoftwareVersion."
       ::= { vpwrSystemIdentGroup 3 }

    vpwrIdentAgentSoftwareVersion OBJECT-TYPE
       SYNTAX     DisplayString (SIZE (0..15))
       MAX-ACCESS read-only
       STATUS     current
       DESCRIPTION
               "The SNMP agent software version.  This variable may or
               may not have the same value as
               vpwrIdentControllerVersion."
       ::= { vpwrSystemIdentGroup 4 }

    vpwrIdentName OBJECT-TYPE
       SYNTAX     DisplayString (SIZE(0..31))
       MAX-ACCESS read-write
       STATUS     current
       DESCRIPTION
               "A string identifying the system.  This object should be
               set by the administrator."
       ::= { vpwrSystemIdentGroup 5 }

        --
    -- The System Identifier group.
    --      All objects in this group are read-only. It describes
    --      various modules (rectifiers, converters, ringers, LVDs, etc.) that make up
    --      the power system and are inserted into a shelf(.1) or panel(.2)
    --
    vpwrSystemIdentTable OBJECT-TYPE
       SYNTAX     SEQUENCE OF VpwrSystemIdentEntry
       MAX-ACCESS not-accessible
       STATUS     current
       DESCRIPTION
       " This table describes shelves and modules
         that make up the sysetm.
       "
       ::= { vpwrSystemIdentGroup 6 }

    --
    -- The System Identifier Entry.  Defines the sequence for module tables.
    --
   vpwrSystemIdentEntry OBJECT-TYPE
       SYNTAX     VpwrSystemIdentEntry
       MAX-ACCESS not-accessible
       STATUS     current
       DESCRIPTION
               "An entry containing information applicable to a
               particular alarm."
       INDEX { vpwrShelfIndex, vpwrModuleIndex }
       ::= { vpwrSystemIdentTable 1 }


    VpwrSystemIdentEntry ::= SEQUENCE {
       vpwrShelfIndex       PositiveInteger,
       vpwrModuleIndex      PositiveInteger,
       vpwrModuleOID        OBJECT IDENTIFIER  ,
       vpwrModuleCurrent    INTEGER ,
       vpwrModuleOperStatus INTEGER ,
       vpwrModuleCapacity   INTEGER 
    }

    --
    -- The System Shelf Identifier group.
    --
    --    vpwrShelfIdentEntry OBJECT-TYPE
    --       SYNTAX     VpwrSystemIdentEntry
    --       MAX-ACCESS not-accessible
    --       STATUS     current
    --       DESCRIPTION
    --         "An entry containing information applicable to a
    --          particular module making up the system."
    --       INDEX { vpwrShelfIndex, vpwrModuleIndex }
    --       ::= { vpwrSystemIdentTable 1 }
    --
       vpwrShelfIndex OBJECT-TYPE
               SYNTAX     PositiveInteger
               MAX-ACCESS read-only
               STATUS     current
               DESCRIPTION
                 "Identifies shelf number that this module belongs to.
                  The possible values are 1 through 16 limited by vpwrSystemShelfCapacity."
               ::= { vpwrSystemIdentEntry 1 }
       
       vpwrModuleIndex OBJECT-TYPE
               SYNTAX     PositiveInteger
               MAX-ACCESS read-only
               STATUS     current
               DESCRIPTION
                 "This object identifies the module by its position in the shelf.
                  Module numbering is left to right starting with module 1.  So, the
                  module in the first slot has an index of 1, the next module is 2 and
                  so on."
               ::= { vpwrSystemIdentEntry 2 }

       vpwrModuleOID        OBJECT-TYPE
               SYNTAX        OBJECT IDENTIFIER
               MAX-ACCESS    read-only
               STATUS        current
               DESCRIPTION
                                   "It indicates the type of the module by specifiying its OID"
               ::= { vpwrSystemIdentEntry 3}

       vpwrModuleCurrent     OBJECT-TYPE
               SYNTAX        INTEGER
               MAX-ACCESS    read-only
               STATUS        current
               DESCRIPTION
                                   "The meaning of this object depends upon the module type
                                    which is indicated by vpwrModuleOID as follows
                                      - Current for Rectifier module in centiamps.
                                      - Not Applicable for LVD module
                                   "
               ::= { vpwrSystemIdentEntry 4}

       vpwrModuleOperStatus   OBJECT-TYPE
               SYNTAX        INTEGER {
                                  moduleStatusOK(0),
                                  moduleStatusAlarm(1),
                                  moduleStatusDisabled(2),
                                  moduleStatusRingerAOn(3),
                                  moduleStatusRingerBOn(4),
                                  moduleStatusUnknown(5)
                             }
               MAX-ACCESS    read-only
               STATUS        current
               DESCRIPTION
                                   "This object indicates current over all status of the module."
               ::= { vpwrSystemIdentEntry 5}

       vpwrModuleCapacity   OBJECT-TYPE
               SYNTAX        INTEGER
               MAX-ACCESS    read-only
               STATUS        current
               DESCRIPTION
                                   "The meaning of this object depends upon the module type
                                    which is indicated by vpwrModuleOID as follows
                                      - Capacity for Rectifier module.
                                      - Not Applicable for LVD module
                                   "
               ::= { vpwrSystemIdentEntry 6}



    --
    -- The System Panel Identifier group.
    --

    vpwrPanelStatusTable OBJECT-TYPE
       SYNTAX     SEQUENCE OF VpwrPanelStatusEntrySEQ
       MAX-ACCESS not-accessible
       STATUS     current
       DESCRIPTION
       " This table describes shelves and modules
         that make up the panels.
       "
       ::= { vpwrSystemPanelIdentGroup 1 }

    vpwrPanelStatus OBJECT-TYPE
       SYNTAX     VpwrPanelStatusEntrySEQ
       MAX-ACCESS not-accessible
       STATUS     current
       DESCRIPTION
         "An entry containing information applicable to a
          particular panel making up the system."
       INDEX { vpwrPanelStatusIndex, vpwrPanelStatusModuleIndex }
       ::= { vpwrPanelStatusTable 1 }

    VpwrPanelStatusEntrySEQ ::= SEQUENCE {
       vpwrPanelStatusIndex        PositiveInteger,
       vpwrPanelStatusModuleIndex      PositiveInteger,
       vpwrPanelStatusModuleOID        OBJECT IDENTIFIER  ,
       vpwrPanelStatusModuleCurrent    INTEGER ,
       vpwrpanelStatusModuleOperStatus INTEGER ,
       vpwrPanelStatusModuleCapacity   INTEGER 
    }

    vpwrPanelStatusIndex OBJECT-TYPE
               SYNTAX     PositiveInteger
               MAX-ACCESS read-only
               STATUS     current
               DESCRIPTION
                 "Identifies panel number that this module belongs to.
                  The possible values are 1 through 8, starting from the top."
               ::= { vpwrPanelStatus 1 }
       
    vpwrPanelStatusModuleIndex OBJECT-TYPE
               SYNTAX     PositiveInteger
               MAX-ACCESS read-only
               STATUS     current
               DESCRIPTION
                 "This object identifies the module within the panel.
                  The orentation of modules within the panel is mappable."
               ::= { vpwrPanelStatus 2 }

    vpwrPanelStatusModuleOID   OBJECT-TYPE
               SYNTAX        OBJECT IDENTIFIER
               MAX-ACCESS    read-only
               STATUS        current
               DESCRIPTION
                 "The module OID."
               ::= { vpwrPanelStatus 3}

    vpwrPanelStatusModuleCurrent    OBJECT-TYPE
               SYNTAX        INTEGER
               MAX-ACCESS    read-only
               STATUS        current
               DESCRIPTION
                 "The current measured by the device (if applicable).  LVD current reported in deciAmps.
                 "
               ::= { vpwrPanelStatus 4}

    vpwrpanelStatusModuleOperStatus   OBJECT-TYPE
               SYNTAX        INTEGER {
                                  moduleStatusOK(0),
                                  moduleStatusAlarm(1),
                                  moduleStatusDisabled(2),
                                  moduleStatusRingerAOn(3),
                                  moduleStatusRingerBOn(4),
                                  moduleStatusUnknown(5)
                             }
               MAX-ACCESS    read-only
               STATUS        current
               DESCRIPTION
                 "This object indicates current over all status of the module."
               ::= { vpwrPanelStatus 5}

    vpwrPanelStatusModuleCapacity   OBJECT-TYPE
               SYNTAX        INTEGER
               MAX-ACCESS    read-only
               STATUS        current
               DESCRIPTION
                 "The maximum capacity of the module (if applicable)."
               ::= { vpwrPanelStatus 6}


    vpwrPanelIdentTable OBJECT-TYPE
       SYNTAX     SEQUENCE OF VpwrPanelIdentEntrySEQ
       MAX-ACCESS not-accessible
       STATUS     current
       DESCRIPTION
       " This table describes shelves and modules
         that make up the panels.
       "
       ::= { vpwrSystemPanelIdentGroup 2 }



    vpwrPanelIdentEntry OBJECT-TYPE
       SYNTAX     VpwrPanelIdentEntrySEQ
       MAX-ACCESS not-accessible
       STATUS     current
       DESCRIPTION
         "An entry containing information applicable to a
          particular panel making up the system."
       INDEX { vpwrPanelIndex, vpwrPanelModuleIndex }
       ::= { vpwrPanelIdentTable 1 }




    VpwrPanelIdentEntrySEQ ::= SEQUENCE {
       vpwrPanelIndex               PositiveInteger,
       vpwrPanelModuleIndex         PositiveInteger,
       vpwrPanelModuleSerNum        OBJECT IDENTIFIER  ,
       vpwrPanelModuleModelName     OBJECT IDENTIFIER ,
       vpwrPanelModuleFWVer         OBJECT IDENTIFIER ,
       vpwrPanelModuleTestDate      INTEGER 
    }

    vpwrPanelIndex OBJECT-TYPE
               SYNTAX     PositiveInteger
               MAX-ACCESS read-only
               STATUS     current
               DESCRIPTION
                 "Identifies panel number that this module belongs to.
                  The possible values are 1 through 8, starting from the top."
               ::= { vpwrPanelIdentEntry 1 }
    
    vpwrPanelModuleIndex OBJECT-TYPE
               SYNTAX     PositiveInteger
               MAX-ACCESS read-only
               STATUS     current
               DESCRIPTION
                 "This object identifies the module within the panel.
                  The orentation of modules within the panel is mappable."
               ::= { vpwrPanelIdentEntry 2 }

    vpwrPanelModuleSerNum   OBJECT-TYPE
               SYNTAX        OBJECT IDENTIFIER
               MAX-ACCESS    read-only
               STATUS        current
               DESCRIPTION
                 "The module serial number."
               ::= { vpwrPanelIdentEntry 3}

    vpwrPanelModuleModelName    OBJECT-TYPE
               SYNTAX        OBJECT IDENTIFIER
               MAX-ACCESS    read-only
               STATUS        current
               DESCRIPTION
                 "The model name of the device."
               ::= { vpwrPanelIdentEntry 4}

    vpwrPanelModuleFWVer   OBJECT-TYPE
               SYNTAX        OBJECT IDENTIFIER
               MAX-ACCESS    read-only
               STATUS        current
               DESCRIPTION
                 "The module firmware version."
               ::= { vpwrPanelIdentEntry 5}

    vpwrPanelModuleTestDate   OBJECT-TYPE
               SYNTAX        INTEGER
               MAX-ACCESS    read-only
               STATUS        current
               DESCRIPTION
                 "The manufacturing test date."
               ::= { vpwrPanelIdentEntry 6}

--
-- Power Module inventory info
--
    vpwrDcPowerModuleIdentTable OBJECT-TYPE
       SYNTAX     SEQUENCE OF DCPowerModuleIdentEntrySEQ
       MAX-ACCESS not-accessible
       STATUS     current
       DESCRIPTION
       " This table describes power modules
         that make up the system.
       "
       ::= { vpwrDcPowerModuleIdent 1 }

    --
    -- The Module Identifier Entry.  Defines the sequence for module tables.
    --

   vpwrDcPowerModuleIdentEntry OBJECT-TYPE
       SYNTAX     DCPowerModuleIdentEntrySEQ
       MAX-ACCESS not-accessible
       STATUS     current
       DESCRIPTION
               "An entry containing information applicable to a
               power module."
       INDEX { vpwrShelfIndex1, vpwrDCModuleIndex }       
       ::= { vpwrDcPowerModuleIdentTable 1 }


    DCPowerModuleIdentEntrySEQ ::= SEQUENCE {
       vpwrShelfIndex1          PositiveInteger,
       vpwrDCModuleIndex       PositiveInteger,
       vpwrModuleSerialNumber  DisplayString  ,
       vpwrModuleModelNumber   DisplayString ,
       vpwrModuleFwVersion     DisplayString ,
       vpwrModuleTestDate      DisplayString ,
       vpwrModuleOperHours     Counter32
    }

    vpwrShelfIndex1 OBJECT-TYPE
               SYNTAX     PositiveInteger
               MAX-ACCESS read-only
               STATUS     current
               DESCRIPTION
                 "Identifies shelf number that this module belongs to.
                  The possible values are 1 through 2, starting from the top."
               ::= { vpwrDcPowerModuleIdentEntry 1 }
       
    vpwrDCModuleIndex OBJECT-TYPE
              SYNTAX     PositiveInteger
               MAX-ACCESS read-only
               STATUS     current
               DESCRIPTION
                 "This object identifies the module within the shelf."
               ::= { vpwrDcPowerModuleIdentEntry 2 }


       vpwrModuleSerialNumber        OBJECT-TYPE
               SYNTAX        DisplayString
               MAX-ACCESS    read-only
               STATUS        current
               DESCRIPTION
                                   "Serial Number of the module"
               ::= { vpwrDcPowerModuleIdentEntry 3}

       vpwrModuleModelNumber     OBJECT-TYPE
               SYNTAX        DisplayString
               MAX-ACCESS    read-only
               STATUS        current
               DESCRIPTION
                                   "Model Number of the module."
               ::= { vpwrDcPowerModuleIdentEntry 4}

       vpwrModuleFwVersion   OBJECT-TYPE
               SYNTAX        DisplayString 
               MAX-ACCESS    read-only
               STATUS        current
               DESCRIPTION
                                   "Firmware version of the module."
               ::= { vpwrDcPowerModuleIdentEntry 5}

       vpwrModuleTestDate   OBJECT-TYPE
               SYNTAX        DisplayString
               MAX-ACCESS    read-only
               STATUS        current
               DESCRIPTION
                                   "Date when the module was last tested."
               ::= { vpwrDcPowerModuleIdentEntry 6}

       vpwrModuleOperHours   OBJECT-TYPE
               SYNTAX        Counter32
               MAX-ACCESS    read-only
               STATUS        current
               DESCRIPTION
                                   "Cumulative Operating Hours."
               ::= { vpwrDcPowerModuleIdentEntry 7}




--
    --
    -- The System History group.
    --
    vpwrSysHistAlarmTable OBJECT-TYPE
       SYNTAX     SEQUENCE OF VpwrSysHistAlarmEntry
       MAX-ACCESS not-accessible
       STATUS     current
       DESCRIPTION
       " This table provides a list of most recent alarms.
       "
       ::= { vpwrSystemHistoryGroup 1 }


    vpwrSysHistAlarmEntry OBJECT-TYPE
       SYNTAX     VpwrSysHistAlarmEntry
       MAX-ACCESS not-accessible
       STATUS     current
       DESCRIPTION
         "An entry describing an alarm."
       INDEX { vpwrSysHistAlarmIndex}
       ::= { vpwrSysHistAlarmTable 1 }

    VpwrSysHistAlarmEntry ::= SEQUENCE {
       vpwrSysHistAlarmIndex               PositiveInteger,
       vpwrSysHistAlarmDescription         DisplayString
    }

    vpwrSysHistAlarmIndex OBJECT-TYPE
               SYNTAX     PositiveInteger
               MAX-ACCESS read-only
               STATUS     current
               DESCRIPTION
                 "Alarm index."
               ::= { vpwrSysHistAlarmEntry 1 }
       
    vpwrSysHistAlarmDescription OBJECT-TYPE
               SYNTAX     DisplayString
               MAX-ACCESS read-only
               STATUS     current
               DESCRIPTION
                 "Alarm description including time stamp."
               ::= { vpwrSysHistAlarmEntry 2 }



--
--    --
--The System Configuration Parameters group.
--    --

    vpwrSystemTempCompensation OBJECT-TYPE
                         SYNTAX INTEGER {
                                tempCompDisabled(0),
                                tempCompEnabled(1)
                         }
                         MAX-ACCESS read-write
                         STATUS current
                         DESCRIPTION
                         "  This parameter enables/disables temperature compensation.
                         "
                         REFERENCE " "

                         ::= {vpwrSystemConfigGroup 1}

              vpwrSystemTempCompStartTemperature OBJECT-TYPE
                         SYNTAX INTEGER (25..60)
                         UNITS  "degrees Centigrade"
                         MAX-ACCESS read-write
                         STATUS current
                         DESCRIPTION
                         "  The temperature at which temperature compensation becomes
                            active.
                         "
                         REFERENCE " "
                         ::= {vpwrSystemConfigGroup 2}

               vpwrSystemTempCompStopVoltage OBJECT-TYPE
                         SYNTAX INTEGER 
                         UNITS  " *.01 Volts"
                         MAX-ACCESS read-write
                         STATUS current
                         DESCRIPTION
                         "  When temperature compensation is active, vpwrSystemTempCompStopVoltage is the
                            limit to which float voltage will be reduced.
                    For example, to set this voltage to 51.75 volts enter a value of 5175.
                         "
                         REFERENCE " "
                         ::= {vpwrSystemConfigGroup 3}

               vpwrSystemTempCompensationSlope OBJECT-TYPE
                         SYNTAX INTEGER (0..250)
                         UNITS  " milli-Volts per degrees Centigrade"
                         MAX-ACCESS read-write
                         STATUS current
                         DESCRIPTION
                         "  The rate at which float voltage is changed, within the specified limits,
                            when temperature compensation is active.
                         "
                         REFERENCE " "
                         ::= {vpwrSystemConfigGroup 4}

              vpwrSystemThermalSenseType OBJECT-TYPE
                         SYNTAX INTEGER {
                                internal(0),
                                external(1)
                         }
                         MAX-ACCESS read-write
                         STATUS current
                         DESCRIPTION
                         "  This parameter selects the temperature sensing point for temperature
                            compensation (in)activation.
                         "
                         REFERENCE " "
                         ::= {vpwrSystemConfigGroup 5}

         vpwrSystemHVAlarmSetpoint   OBJECT-TYPE
                                SYNTAX        INTEGER
                                UNITS  " *.01 Volts"
                                MAX-ACCESS    read-write
                                STATUS        current
                                DESCRIPTION
                                   "System High voltage alarm voltage setting.
                                   "
                           ::= { vpwrSystemConfigGroup 6}
         vpwrSystemBDAlarmSetpoint   OBJECT-TYPE
                                SYNTAX        INTEGER
                                UNITS  " *.01 Volts"
                                MAX-ACCESS    read-write
                                STATUS        current
                                DESCRIPTION
                                   "System Battery Discharge voltage setting."
                           ::= { vpwrSystemConfigGroup 7}

--
-- Threshold for Internal Temperature Trap
--
         vpwrSystemInternalTempLThreshold   OBJECT-TYPE
                                SYNTAX        INTEGER
                                UNITS         "degrees Centigrade"
                                MAX-ACCESS    read-write
                                STATUS        current
                                DESCRIPTION
                                   "Temperature value at which temperature compensation inactive (clear)
                                    trap would be sent if temperature compensation was active when this 
                                    value is reached.
                                    "
                           ::= { vpwrSystemConfigGroup 8}

          vpwrSystemInternalTempUThreshold   OBJECT-TYPE
                                SYNTAX        INTEGER
                                UNITS         "degrees Centigrade"
                                MAX-ACCESS    read-write
                                STATUS        current
                                DESCRIPTION
                                   "Temperature value at which temperature compensation active (set) trap 
                                    would be sent.
                                   "
                           ::= { vpwrSystemConfigGroup 9}

    --
    -- The System Current Operating Parameters group.
    --


        vpwrSystemShelfCapacity OBJECT-TYPE
                         SYNTAX INTEGER (1..16)
                         MAX-ACCESS read-only
                         STATUS current
                         DESCRIPTION
                         "  It describes the maximum number of shelves that can/are controlled
                            by the controller. Each shelf is uniquely numbered in the range
                            from 1 to  vpwrShelfCapacity.
                         "
                         REFERENCE " "
                         ::= {vpwrSystemParameterGroup 1}
                         
         vpwrSystemVoltage OBJECT-TYPE
                         SYNTAX INTEGER 
                          UNITS  " *.01 Volts"
                          MAX-ACCESS read-only
                         STATUS current
                         DESCRIPTION
                         "  The current system voltage.
                         "
                         REFERENCE " "
                         ::= {vpwrSystemParameterGroup 2}
                         
          vpwrSystemCurrent OBJECT-TYPE
                         SYNTAX INTEGER
                         UNITS  " Amperes"
                         MAX-ACCESS read-only
                         STATUS current
                         DESCRIPTION
                         "  The current system current.
                         "
                         REFERENCE " "
                         ::= {vpwrSystemParameterGroup 3}
                         
           vpwrSystemControllerState OBJECT-TYPE
                         SYNTAX INTEGER {
                                systemControllerStateUnknown(0),
                                systemControllerStateNormal(1),
                                systemControllerStateChange(2) ,
                                systemControllerStateAlarm(3),
                                systemControllerStateMenu(4 ),
                                systemControllerStateIrActive(5)
                         }
                         MAX-ACCESS read-only
                         STATUS current
                         DESCRIPTION
                         "  Current System state as shown on the enhanced display.
                         "
                         REFERENCE " "
                         ::= {vpwrSystemParameterGroup 4}


                vpwrSystemInternalTemperature OBJECT-TYPE
                         SYNTAX INTEGER 
                         UNITS  "degrees Centigrade"
                         MAX-ACCESS read-only
                         STATUS current
                         DESCRIPTION
                         "  The current controller internal temperature.
                         "
                         REFERENCE " "
                         ::= {vpwrSystemParameterGroup 5}
                         
                 vpwrSystemTempCompensationState OBJECT-TYPE
                         SYNTAX INTEGER {
                                systemTempCompInactive(0),
                                systemTempCompActive(1)
                         }
                         MAX-ACCESS read-only
                         STATUS current
                         DESCRIPTION
                         "  Active or Inactive. Applicable only if temperature compensation is enabled.
                            This means that the controller is temperature compensating the float voltage.
                         "
                         REFERENCE " "
                         ::= {vpwrSystemParameterGroup 6}

             vpwrSystemType OBJECT-TYPE
                         SYNTAX     INTEGER {
                           sysType48V (0),
                           sysType24V(1)  ,
                            sysType12V(2)
                        }
                         MAX-ACCESS read-only
                         STATUS     current
                         DESCRIPTION
                         "This parameter describes the type of the system being managed.
                          This object is set by Eltek Valere Inc.
                         "
                         ::= { vpwrSystemParameterGroup 7 }

             vpwrSystemCumulativeUpTime OBJECT-TYPE
                         SYNTAX     Gauge 
                         MAX-ACCESS read-only
                         STATUS     current
                         DESCRIPTION
                         "This parameter describes the cumulative runtime in seconds
                         of the Eltek Valere controller.
                         "
                         ::= { vpwrSystemParameterGroup 8 }

             vpwrSystemBatteryRemainingTime OBJECT-TYPE
                         SYNTAX     PositiveInteger
                         UNITS      "Hours"
                         MAX-ACCESS read-only
                         STATUS     current
                         DESCRIPTION
                         "This parameter describes the remaining battery capacity
                          based upon installed battery capacity and 
                          plant load. This number would change as the SOC
                          parameters of the batteries changes.
                         "
                         ::= { vpwrSystemParameterGroup 9 }

    --
    -- The System Alarm group.
    --


        vpwrSystemAlarmMajor OBJECT-TYPE
                         SYNTAX INTEGER
                         MAX-ACCESS read-only
                         STATUS current
                         DESCRIPTION
                         "  Indicates a Major Alarm exists on the system.
                         "
                         REFERENCE " "
                         ::= {vpwrSystemAlarmGroup 1}
                         
         vpwrSystemAlarmMinor OBJECT-TYPE
                         SYNTAX INTEGER 
                         MAX-ACCESS read-only
                         STATUS current
                         DESCRIPTION
                         "  Indicates a Minor Alarm exists on the system.
                         "
                         REFERENCE " "
                         ::= {vpwrSystemAlarmGroup 2}
                         
          vpwrSystemACFailAlarm OBJECT-TYPE
                         SYNTAX INTEGER
                         MAX-ACCESS read-only
                         STATUS current
                         DESCRIPTION
                         "  One or more rectifiers have reported AC failure.  If system
                            is configured to report rectifier communication failure as AC fail
                            this alarm will report.
                         "
                         REFERENCE " "
                         ::= {vpwrSystemAlarmGroup 3}
                         
           vpwrSystemHighVoltageWarningAlarm OBJECT-TYPE
                         SYNTAX INTEGER
			 MAX-ACCESS read-only
                         STATUS current
                         DESCRIPTION
                         "  System has exceeded High Voltage Warning Setpoint.  Check for high voltage on system bus.
                         "
                         REFERENCE " "
                         ::= {vpwrSystemAlarmGroup 4}


                vpwrSystemHighVoltageShutdownAlarm OBJECT-TYPE
                         SYNTAX INTEGER 
                         MAX-ACCESS read-only
                         STATUS current
                         DESCRIPTION
                         "  One or more rectifiers have shut down due to high voltage present on output.  Check bus voltage
                         and reseat rectifiers that have indicated this problem.
                         "
                         REFERENCE " "
                         ::= {vpwrSystemAlarmGroup 5}
                         
                 vpwrSystemBatteryonDischargeAlarm OBJECT-TYPE
                         SYNTAX INTEGER {
                                systemTempCompInactive(0),
                                systemTempCompActive(1)
                         }
                         MAX-ACCESS read-only
                         STATUS current
                         DESCRIPTION
                         "  System voltage has currently dropped below the alarm setpoint.  This may be due to battery testing or AC failure.
                         "
                         REFERENCE " "
                         ::= {vpwrSystemAlarmGroup 6}

             vpwrSystemLowVoltageWarningAlarm OBJECT-TYPE
                         SYNTAX     INTEGER {
                           sysType48V (0),
                           sysType24V(1)  ,
                            sysType12V(2)
                        }
                         MAX-ACCESS read-only
                         STATUS     current
                         DESCRIPTION
                         "System Voltage has dropped below setpoint for Low Voltage Alarm.  This may occur during battery testing or AC failure
                         "
                         ::= { vpwrSystemAlarmGroup 7 }

             vpwrSystemLVDOpenAlarm OBJECT-TYPE
                         SYNTAX     Gauge 
                         MAX-ACCESS read-only
                         STATUS     current
                         DESCRIPTION
                         "One or more contactors have opened.  This occurs normally during system power on.  If it occurs during operation this may
                         indicate system is operating below LVD disconnect voltage.
                         "
                         ::= { vpwrSystemAlarmGroup 8 }

             vpwrSystemDistributionAlarm OBJECT-TYPE
                         SYNTAX     PositiveInteger
                         MAX-ACCESS read-only
                         STATUS     current
                         DESCRIPTION
                         "One or more distribution alarm inputs are reporting an error condition.  Check source of alarm and correct issue.
                         "
                         ::= { vpwrSystemAlarmGroup 9 }

             vpwrSystemAuxiliaryAlarm OBJECT-TYPE
                         SYNTAX     PositiveInteger
                         MAX-ACCESS read-only
                         STATUS     current
                         DESCRIPTION
                         "One or more Auxliary alarm inputs are reporting an error condition.  Check source of alarm and correct issue.
                         "
                         ::= { vpwrSystemAlarmGroup 10 }

             vpwrSystemRedundantCapAlarm OBJECT-TYPE
                         SYNTAX     PositiveInteger
                         MAX-ACCESS read-only
                         STATUS     current
                         DESCRIPTION
                         "The system load has exceeded the requirements for redundancy.  This may be a temporary system overload condition or caused by a rectifier alarm.
                         "
                         ::= { vpwrSystemAlarmGroup 11 }

             vpwrSystemRectIShareAlarm OBJECT-TYPE
                         SYNTAX     PositiveInteger
                         MAX-ACCESS read-only
                         STATUS     current
                         DESCRIPTION
                         "One or more rectifiers are reporting a mismatch in current.  This may be due to mismatched rectifier models or one or more rectifiers not current sharing
                         "
                         ::= { vpwrSystemAlarmGroup 12 }

             vpwrSystemSnglRectAlarm OBJECT-TYPE
                         SYNTAX     PositiveInteger
                         MAX-ACCESS read-only
                         STATUS     current
                         DESCRIPTION
                         "
                         "
                         ::= { vpwrSystemAlarmGroup 13 }

             vpwrSystemMultRectAlarm OBJECT-TYPE
                         SYNTAX     PositiveInteger
                         MAX-ACCESS read-only
                         STATUS     current
                         DESCRIPTION
                         "
                         "
                         ::= { vpwrSystemAlarmGroup 14 }

             vpwrSystemModlCommAlarm OBJECT-TYPE
                         SYNTAX     PositiveInteger
                         MAX-ACCESS read-only
                         STATUS     current
                         DESCRIPTION
                         "
                         "
                         ::= { vpwrSystemAlarmGroup 15 }

             vpwrSystemOverTempAlarm OBJECT-TYPE
                         SYNTAX     PositiveInteger
                         MAX-ACCESS read-only
                         STATUS     current
                         DESCRIPTION
                         "
                         "
                         ::= { vpwrSystemAlarmGroup 16 }
                         
             vpwrSystemThermRAAlarm OBJECT-TYPE
                         SYNTAX     PositiveInteger
                         MAX-ACCESS read-only
                         STATUS     current
                         DESCRIPTION
                         "Thermal Runaway has occurred on system.  Check temperature inputs.
                         "
                         ::= { vpwrSystemAlarmGroup 17 }
                         
             vpwrSystemBDTAlarm OBJECT-TYPE
                         SYNTAX     PositiveInteger
                         MAX-ACCESS read-only
                         STATUS     current
                         DESCRIPTION
                         "System has entered Battery Discharge Test mode
                         "
                         ::= { vpwrSystemAlarmGroup 18 }
                         
             vpwrSystemRectUVAlarm OBJECT-TYPE
                         SYNTAX     PositiveInteger
                         MAX-ACCESS read-only
                         STATUS     current
                         DESCRIPTION
                         "Rectifier output has dropped 1V below Low Voltage Alarm setpoint
                         "
                         ::= { vpwrSystemAlarmGroup 19 }
                         
             vpwrSystemMultRectUVAlarm OBJECT-TYPE
                         SYNTAX     PositiveInteger
                         MAX-ACCESS read-only
                         STATUS     current
                         DESCRIPTION
                         "
                         "
                         ::= { vpwrSystemAlarmGroup 20 }
                         
             vpwrSystemSnglRngrAlarm OBJECT-TYPE
                         SYNTAX     PositiveInteger
                         MAX-ACCESS read-only
                         STATUS     current
                         DESCRIPTION
                         "
                         "
                         ::= { vpwrSystemAlarmGroup 21 }
                         
             vpwrSystemMultRngrAlarm OBJECT-TYPE
                         SYNTAX     PositiveInteger
                         MAX-ACCESS read-only
                         STATUS     current
                         DESCRIPTION
                         "
                         "
                         ::= { vpwrSystemAlarmGroup 22 }
                         
             vpwrSystemTempProbeAlarm OBJECT-TYPE
                         SYNTAX     PositiveInteger
                         MAX-ACCESS read-only
                         STATUS     current
                         DESCRIPTION
                         "Temp probe input missing or failed
                         "
                         ::= { vpwrSystemAlarmGroup 23 }
             
             vpwrSystemRngrCommAlarm OBJECT-TYPE
                         SYNTAX     PositiveInteger
                         MAX-ACCESS read-only
                         STATUS     current
                         DESCRIPTION
                         "Ringer Module has stopped communicating with Controller.
                         "
                         ::= { vpwrSystemAlarmGroup 24 }
             
             vpwrSystemDistPMCommAlarm OBJECT-TYPE
                         SYNTAX     PositiveInteger
                         MAX-ACCESS read-only
                         STATUS     current
                         DESCRIPTION
                         "One or more distribution alarm modules, TRIOs, or PM modules has stopped communicating with Controller.
                         "
                         ::= { vpwrSystemAlarmGroup 25 }
             
             vpwrSystemRectILimitAlarm OBJECT-TYPE
                         SYNTAX     PositiveInteger
                         MAX-ACCESS read-only
                         STATUS     current
                         DESCRIPTION
                         "Rectifier has reached current limit setpoint.
                         "
                         ::= { vpwrSystemAlarmGroup 26 }
                         
             vpwrSystemMultRectILimitAlarm OBJECT-TYPE
                         SYNTAX     PositiveInteger
                         MAX-ACCESS read-only
                         STATUS     current
                         DESCRIPTION
                         "
                         "
                         ::= { vpwrSystemAlarmGroup 27 }
             
             vpwrSystemUnmappedI2CCANAlarm OBJECT-TYPE
                         SYNTAX     PositiveInteger
                         MAX-ACCESS read-only
                         STATUS     current
                         DESCRIPTION
                         "Recheck all I2C and CAN dip switch settings.  One or more devices in conflict.
                         "
                         ::= { vpwrSystemAlarmGroup 28 }
                         
             vpwrSystemConfigErrAlarm OBJECT-TYPE
                         SYNTAX     PositiveInteger
                         MAX-ACCESS read-only
                         STATUS     current
                         DESCRIPTION
                         "Recheck all I2C and CAN dip switch settings.  One or more devices in conflict.
                         "
                         ::= { vpwrSystemAlarmGroup 29 }
                         
             vpwrSystemDispFWAlarm OBJECT-TYPE
                         SYNTAX     PositiveInteger
                         MAX-ACCESS read-only
                         STATUS     current
                         DESCRIPTION
                         "
                         "
                         ::= { vpwrSystemAlarmGroup 30 }
                         
             vpwrSystemUndefinedAlarm OBJECT-TYPE
                         SYNTAX     PositiveInteger
                         MAX-ACCESS read-only
                         STATUS     current
                         DESCRIPTION
                         "
                         "
                         ::= { vpwrSystemAlarmGroup 31 }
                         
  --           vpwrSystemModlCommAlarm OBJECT-TYPE
  --                       SYNTAX     PositiveInteger
  --                       MAX-ACCESS read-only
  --                       STATUS     current
  --                       DESCRIPTION
  --                       "
  --                       "
  --                       ::= { vpwrSystemAlarmGroup 32 }

    --
    -- The System LVD Operating Setpoints group.
    --      

         vpwrLvdWarningSetpoint   OBJECT-TYPE
                                SYNTAX        INTEGER
                                UNITS  " * .01 Volts"
                                MAX-ACCESS    read-write
                                STATUS        current
                                DESCRIPTION
                                   "LVD Warning voltage setpoint."
                           ::= { vpwrLvdConfigGroup 1}

          vpwrLvdDisconnectSetpoint   OBJECT-TYPE
                                SYNTAX        INTEGER
                                UNITS  " *.01 Volts"
                                MAX-ACCESS    read-write
                                STATUS        current
                                DESCRIPTION
                                   "LVD disconnect voltage setpoint."
                           ::= { vpwrLvdConfigGroup 2}
         vpwrLvdReconnectSetpoint   OBJECT-TYPE
                                SYNTAX        INTEGER
                                UNITS  " *.01 Volts"
                                MAX-ACCESS    read-write
                                STATUS        current
                                DESCRIPTION
                                   "LVD Reconnect voltage setpoint."
                           ::= { vpwrLvdConfigGroup 3}
         vpwrLvdReconnectDelayTimer   OBJECT-TYPE
                                SYNTAX        INTEGER (20..240)
                                UNITS  " Seconds"
                                MAX-ACCESS    read-only
                                STATUS        current
                                DESCRIPTION
                                   "The delay time, in seconds, before LVD is reconnected"
                           ::= { vpwrLvdConfigGroup 4}
    --
    -- The System LVD Operating Setpoints group.
    --      

          vpwrLvd2DisconnectSetpoint   OBJECT-TYPE
                                SYNTAX        INTEGER
                                UNITS  " *.01 Volts"
                                MAX-ACCESS    read-write
                                STATUS        current
                                DESCRIPTION
                                   "LVD disconnect voltage setpoint."
                           ::= { vpwrLvdConfigGroup 7}
       vpwrLvd2ReconnectSetpoint   OBJECT-TYPE
                                SYNTAX        INTEGER
                                UNITS  " *.01 Volts"
                                MAX-ACCESS    read-write
                                STATUS        current
                                DESCRIPTION
                                   "LVD Reconnect voltage setpoint."
                           ::= { vpwrLvdConfigGroup 8}
         vpwrLvd2ReconnectDelayTimer   OBJECT-TYPE
                                SYNTAX        INTEGER (20..240)
                                UNITS  " Seconds"
                                MAX-ACCESS    read-only
                                STATUS        current
                                DESCRIPTION
                                   "The delay time, in seconds, before LVD is reconnected"
                           ::= { vpwrLvdConfigGroup 9}
                           

    --
    -- The System LVD Operating Setpoints group.
    --      

          vpwrLvd3DisconnectSetpoint   OBJECT-TYPE
                                SYNTAX        INTEGER
                                UNITS  " *.01 Volts"
                                MAX-ACCESS    read-write
                                STATUS        current
                                DESCRIPTION
                                   "LVD disconnect voltage setpoint."
                           ::= { vpwrLvdConfigGroup 11}
         vpwrLvd3ReconnectSetpoint   OBJECT-TYPE
                                SYNTAX        INTEGER
                                UNITS  " *.01 Volts"
                                MAX-ACCESS    read-write
                                STATUS        current
                                DESCRIPTION
                                   "LVD Reconnect voltage setpoint."
                           ::= { vpwrLvdConfigGroup 12}
         vpwrLvd3ReconnectDelayTimer   OBJECT-TYPE
                                SYNTAX        INTEGER (20..240)
                                UNITS  " Seconds"
                                MAX-ACCESS    read-only
                                STATUS        current
                                DESCRIPTION
                                   "The delay time, in seconds, before LVD is reconnected"
                           ::= { vpwrLvdConfigGroup 13}
                           
    --
    -- The System LVD Operating Setpoints group.
    --      


          vpwrLvd4DisconnectSetpoint   OBJECT-TYPE
                                SYNTAX        INTEGER
                                UNITS  " *.01 Volts"
                                MAX-ACCESS    read-write
                                STATUS        current
                                DESCRIPTION
                                   "LVD disconnect voltage setpoint."
                           ::= { vpwrLvdConfigGroup 15}
         vpwrLvd4ReconnectSetpoint   OBJECT-TYPE
                                SYNTAX        INTEGER
                                UNITS  " *.01 Volts"
                                MAX-ACCESS    read-write
                                STATUS        current
                                DESCRIPTION
                                   "LVD Reconnect voltage setpoint."
                           ::= { vpwrLvdConfigGroup 16}
         vpwrLvd4ReconnectDelayTimer   OBJECT-TYPE
                                SYNTAX        INTEGER (20..240)
                                UNITS  " Seconds"
                                MAX-ACCESS    read-only
                                STATUS        current
                                DESCRIPTION
                                   "The delay time, in seconds, before LVD is reconnected"
                           ::= { vpwrLvdConfigGroup 17}
                           
--         vpwrLvd4DisconnectDelayTimer   OBJECT-TYPE
--                                SYNTAX        INTEGER (20..240)
--                                UNITS  " Seconds"
--                                MAX-ACCESS    read-only
--                                STATUS        current
--                                DESCRIPTION
--                                   "The delay time, in seconds, before LVD is reconnected"
--                           ::= { vpwrLvdConfigGroup 18}
    --
    -- The Rectifier Operating Parameters group.
    --

         vpwrRectifierFVSetpoint   OBJECT-TYPE
                                SYNTAX        INTEGER
                                 UNITS  " *.01 Volts"
                               MAX-ACCESS    read-write
                                STATUS        current
                                DESCRIPTION
                                   "System Float Voltage setting"
                           ::= { vpwrRectifierConfigGroup 1}
           vpwrRectifierHVSDSetpoint   OBJECT-TYPE
                                SYNTAX        INTEGER
                                UNITS  " *.01 Volts"
                                MAX-ACCESS    read-write
                                STATUS        current
                                DESCRIPTION
                                   "System High Voltage Shutdown voltage setting"
                           ::= { vpwrRectifierConfigGroup 2}

    vpwrRectifierCurrentLimitAdminState OBJECT-TYPE
                         SYNTAX INTEGER {
                                rectCurrentLimitDisabled(0),
                                rectCurrentLimitEnabled(1)
                        }
                         MAX-ACCESS read-write
                         STATUS current
                         DESCRIPTION
                         "  This parameter allows enabling or rectifier current limit"
                         REFERENCE " "

                         ::= {vpwrRectifierConfigGroup 3}

            vpwrRectifierCurrentLimit   OBJECT-TYPE
                                SYNTAX        INTEGER (5..220)
                                UNITS  "Amperes"
                                MAX-ACCESS    read-write
                                STATUS        current
                                DESCRIPTION
                                   "Rectifier current limit setpoint"
                           ::= { vpwrRectifierConfigGroup 4}

            vpwrRectifierFallbackAdminState   OBJECT-TYPE
                                SYNTAX        GenericEnableDisableTC
                                MAX-ACCESS    read-write
                                STATUS        current
                                DESCRIPTION
                                   "Enables Rectifier to use
                                    Fallback Voltage when it loses
                                    communication with the controller.
                                    This applies to all rectifiers."
                           ::= { vpwrRectifierConfigGroup 5}

            vpwrRectifierFallbackVoltage   OBJECT-TYPE
                                SYNTAX      INTEGER  
                                 UNITS      " *.01 Volts"
                                MAX-ACCESS    read-write
                                STATUS        current
                                DESCRIPTION
                                   "Fallback Voltage setpoint to use 
                                    when rectifier loses
                                    communication with the controller.
                                    This applies to all rectifiers."
                           ::= { vpwrRectifierConfigGroup 6}

    --
    -- The Alarm group.
    --


    vpwrAlarmsPresent OBJECT-TYPE
       SYNTAX     Gauge32
       MAX-ACCESS read-only
       STATUS     current
       DESCRIPTION
               "The present number of active alarm conditions."
       ::= { vpwrDcPowerAlarmGroup 1 }

    vpwrAlarmTable OBJECT-TYPE
       SYNTAX     SEQUENCE OF VpwrAlarmEntrySEQ
       MAX-ACCESS not-accessible
       STATUS     current
       DESCRIPTION
               "A list of alarm table entries.  The table contains
               zero, one, or multiple rows at any time depending upon
               the number of alarm conditions in effect.  The table
               is initially empty at agent startup.  The agent
               creates a row in the table each time a condition is
               detected and deletes that row when that condition no
               longer exists.
               The vpwrAlarmIndex, for each type of module starts at 1
               and is limited by the total number of alarms that can be
               generated by the module.

               Alarms are named by an AutonomousType (OBJECT
               IDENTIFIER), vpwrAlarmDescr, to allow a single table to
               reflect alarms for different types of modules.

               The number of rows in the table at any given time is
               reflected by the value of vpwrAlarmsPresent."
               
       ::= { vpwrDcPowerAlarmGroup 2 }

    vpwrAlarmEntry OBJECT-TYPE
       SYNTAX     VpwrAlarmEntrySEQ
       MAX-ACCESS not-accessible
       STATUS     current
       DESCRIPTION
               "An entry containing information applicable to a
               particular alarm."
       INDEX { vpwrShelfIndex, vpwrModuleIndex, vpwrAlarmIndex }
       ::= { vpwrAlarmTable 1 }

    VpwrAlarmEntrySEQ ::= SEQUENCE {
       vpwrAlarmIndex       PositiveInteger,
       vpwrAlarmDescr       AutonomousType,
       vpwrAlarmTime        TimeStamp
    }

      vpwrAlarmIndex OBJECT-TYPE
       SYNTAX     PositiveInteger
       MAX-ACCESS read-only
       STATUS     current
       DESCRIPTION
               "Identifies the alarm associated with the module. 
                It is unique on per module type basis. For example,
                multiple rectifiers can have the same alarm and therefore same
                vpwrAlarmIndex active at any one time.
               "
       ::= { vpwrAlarmEntry 1 }
       

    vpwrAlarmDescr OBJECT-TYPE
       SYNTAX     AutonomousType
       MAX-ACCESS read-only
       STATUS     current
       DESCRIPTION
               "A reference to an alarm description object.  The
               object referenced should not be accessible, but rather
               be used to provide a unique description of the alarm
               condition."
       ::= { vpwrAlarmEntry 2 }

    vpwrAlarmTime OBJECT-TYPE
       SYNTAX     TimeStamp
       MAX-ACCESS read-only
       STATUS     current
       DESCRIPTION
               "The value of sysUpTime when the alarm condition was
               detected."

       ::= { vpwrAlarmEntry 3 }



    --
    -- The Battery Group
    --



    vpwrBatteryTempTable OBJECT-TYPE
       SYNTAX     SEQUENCE OF VpwrBatteryTempEntry
       MAX-ACCESS not-accessible
       STATUS     current
       DESCRIPTION
       "This table describes battery temperature probes.
       "
       ::= { vpwrBatteryTempGroup 1 }

    vpwrBatteryTempEntry OBJECT-TYPE
       SYNTAX     VpwrBatteryTempEntry
       MAX-ACCESS not-accessible
       STATUS     current
       DESCRIPTION
               "An entry containing information applicable to a
               particular temperature probe."
       INDEX { vpwrBatteryTempIndex }
       ::= { vpwrBatteryTempTable 1 }

    VpwrBatteryTempEntry ::= SEQUENCE {
       vpwrBatteryTempIndex        INTEGER,
       vpwrBatteryTempName        DisplayString,
       vpwrBatteryTemp            SysInputValue
        }

         vpwrBatteryTempIndex   OBJECT-TYPE
                                SYNTAX        INTEGER (0..255)
                                MAX-ACCESS    read-only
                                STATUS        current
                                DESCRIPTION
                                   "Index into temperature table"
                           ::= { vpwrBatteryTempEntry 1}

         vpwrBatteryTempName   OBJECT-TYPE
                                SYNTAX        DisplayString (SIZE (1..8))
                                MAX-ACCESS    read-write
                                STATUS        current
                                DESCRIPTION
                                   "A string identifying probe location."
                           ::= { vpwrBatteryTempEntry 2}

         vpwrBatteryTemp   OBJECT-TYPE
                                SYNTAX        SysInputValue
                                UNITS         "degrees Celsius"
                                MAX-ACCESS    read-only
                                STATUS        current
                                DESCRIPTION
                                   "Current temperature as recorded by the probe."
                           ::= { vpwrBatteryTempEntry 3}


-- Threshold for Battery Temperature Trap

         vpwrBatteryTempLThreshold   OBJECT-TYPE
                                SYNTAX        INTEGER
                                UNITS         "degrees Celsius"
                                MAX-ACCESS    read-write
                                STATUS        current
                                DESCRIPTION
                                   "Temperature value at which a clear trap would be sent.
                                    All three battery temperature must be at or below this value
                                    to trigger this trap.
                                    "
                           ::= { vpwrBatteryTempGroup 2}

          vpwrBatteryTempUThreshold   OBJECT-TYPE
                                SYNTAX        INTEGER
                                UNITS         "degrees Celsius"
                                MAX-ACCESS    read-write
                                STATUS        current
                                DESCRIPTION
                                   "Temperature value at which a set trap would be sent.
                                   Any one of the three battery temperatures at or exceeding this limit
                                   would trigger the trap.
                                   "
                           ::= { vpwrBatteryTempGroup 3}

            batteryTempCompensation OBJECT-TYPE
                         SYNTAX INTEGER {
                                tempCompDisabled(0),
                                tempCompEnabled(1)
                         }
                         MAX-ACCESS read-write
                         STATUS current
                         DESCRIPTION
                         "  This parameter enables/disables temperature compensation.
                         "
                         REFERENCE " "

                         ::= {vpwrBatteryTempGroup 4}

              batteryTempCompHighStartTemperature OBJECT-TYPE
                         SYNTAX INTEGER (25..60)
                         UNITS  "degrees Celsius"
                         MAX-ACCESS read-write
                         STATUS current
                         DESCRIPTION
                         "  The temperature at which temperature compensation becomes
                            active.
                         "
                         REFERENCE " "
                         ::= {vpwrBatteryTempGroup 5}

               batteryTempCompHighStopVoltage OBJECT-TYPE
                         SYNTAX INTEGER 
                         UNITS  " *.01 Volts"
                         MAX-ACCESS read-write
                         STATUS current
                         DESCRIPTION
                         "  When temperature compensation is active, batteryTempCompHighStopVoltage is the
                            limit to which float voltage will be reduced.
                    For example, to set this voltage to 51.75 volts enter a value of 5175.
                         "
                         REFERENCE " "
                         ::= {vpwrBatteryTempGroup 6}

               batteryTempCompHighSlope OBJECT-TYPE
                         SYNTAX INTEGER (0..250)
                         UNITS  " milli-Volts per degrees Celsius"
                         MAX-ACCESS read-write
                         STATUS current
                         DESCRIPTION
                         "  The rate at which float voltage is changed, within the specified limits,
                            when temperature compensation is active.
                         "
                         REFERENCE " "
                         ::= {vpwrBatteryTempGroup 7}


              batteryTempCompLowStartTemperature OBJECT-TYPE
                         SYNTAX INTEGER
                         UNITS  "degrees Celsius"
                         MAX-ACCESS read-write
                         STATUS current
                         DESCRIPTION
                         "  The temperature at which temperature compensation becomes
                            active.
                         "
                         REFERENCE " "
                         ::= {vpwrBatteryTempGroup 8}

               batteryTempCompLowStopVoltage OBJECT-TYPE
                         SYNTAX INTEGER
                         UNITS  " *.01 Volts"
                         MAX-ACCESS read-write
                         STATUS current
                         DESCRIPTION
                         "  When temperature compensation is active, batteryTempCompLowStopVoltage is the
                            limit to which float voltage will be reduced.
                    For example, to set this voltage to 51.75 volts enter a value of 5175.
                         "
                         REFERENCE " "
                         ::= {vpwrBatteryTempGroup 9}

               batteryTempCompLowSlope OBJECT-TYPE
                         SYNTAX INTEGER (0..250)
                         UNITS  " milli-Volts per degrees Celsius"
                         MAX-ACCESS read-write
                         STATUS current
                         DESCRIPTION
                         "  The rate at which float voltage is changed, within the specified limits,
                            when temperature compensation is active.
                         "
                         REFERENCE " "
                         ::= {vpwrBatteryTempGroup 10}

                batteryTempCompRunawayTemperature OBJECT-TYPE
                         SYNTAX INTEGER (25..60)
                         UNITS  "degrees Celsius"
                         MAX-ACCESS read-write
                         STATUS current
                         DESCRIPTION
                         "  The temperature at which system voltage will be set to 
                             batteryTempCompRunawayStopVoltage.
                         "
                       REFERENCE " "
                         ::= {vpwrBatteryTempGroup 11}

               batteryTempCompRunawayStopVoltage OBJECT-TYPE
                         SYNTAX INTEGER
                         UNITS  " *.01 Volts"
                         MAX-ACCESS read-write
                         STATUS current
                         DESCRIPTION
                         "  When temperature compensation is enabled, float voltage will be reduced to
                             batteryTempCompRunawayStopVoltage if temperature
                             reaches batteryTempCompRunawayTemperature.
                         "
                         REFERENCE " "
                         ::= {vpwrBatteryTempGroup 12}

              batteryTempCompSenseSource OBJECT-TYPE
                         SYNTAX INTEGER {
                                internal(0),
                                external(1)
                         }
                         MAX-ACCESS read-write
                         STATUS current
                         DESCRIPTION
                         "  This parameter selects the temperature sensing point for temperature
                            compensation (in)activation.
                         "
                         REFERENCE " "
                         ::= {vpwrBatteryTempGroup 13}
                           
              batteryTempCompRunawayState OBJECT-TYPE
                         SYNTAX INTEGER {
                                inactive(0),
                                active(1)
                         }
                         MAX-ACCESS read-only
                         STATUS current
                         DESCRIPTION
                         "  This parameter selects the temperature sensing point for temperature
                            compensation (in)activation.
                         "
                         REFERENCE " "
                         ::= {vpwrBatteryTempGroup 14}
                         
--    thermalProbeTable OBJECT-TYPE
--       SYNTAX     SEQUENCE OF ThermalProbeEntry
--       MAX-ACCESS not-accessible
--       STATUS     current
--       DESCRIPTION
--       "This table describes battery temperature probes.
--       "
--       ::= { vpwrBatteryTempGroup 15 }
--
--    thermalProbeEntry OBJECT-TYPE
--       SYNTAX     ThermalProbeEntry
--       MAX-ACCESS not-accessible
--       STATUS     current
--       DESCRIPTION
--               "An entry containing information applicable to a
--               particular temperature probe."
--       INDEX { vpwrBatteryTempIndex }
--         AUGMENTS {vpwrBatteryTempEntry}
--       ::= { thermalProbeTable 1 }
--
--    ThermalProbeEntry ::= SEQUENCE {
--       thermalProbeState        INTEGER
--    }
--
--         thermalProbeState   OBJECT-TYPE
--                                SYNTAX        INTEGER {
--                                      notPresent(0),
--                                      present(1),
--                                      removed(2),
--                                      shorted(3)
--                                }
--                                MAX-ACCESS    read-only
--                                STATUS        current
--                                DESCRIPTION
--                                   "State of thermal probe."
--                           ::= { thermalProbeEntry 1}


--
-- The SNMP Configuration Parameters
--

    vpwrTrapTable OBJECT-TYPE
       SYNTAX     SEQUENCE OF VpwrTrapEntry
       MAX-ACCESS not-accessible
       STATUS     current
       DESCRIPTION
       "A list of possible trap destinations depending upon
        the criticality of the trap.
       "
       ::= { vpwrDcPowerSnmpConfig 1 }

    vpwrTrapEntry OBJECT-TYPE
       SYNTAX     VpwrTrapEntry
       MAX-ACCESS not-accessible
       STATUS     current
       DESCRIPTION
               "An entry containing information applicable to a
               particular trap destination."
       INDEX { vpwrTrapIpIndex }
       ::= { vpwrTrapTable 1 }

    VpwrTrapEntry ::= SEQUENCE {
       vpwrTrapIpIndex         INTEGER,
       vpwrTrapIpAddress       IpAddress,
       vpwrTrapCriticality      INTEGER
    }
           vpwrTrapIpIndex   OBJECT-TYPE
                                SYNTAX          INTEGER (0..255)
                                MAX-ACCESS    read-only
                                STATUS        current
                                DESCRIPTION
                                   "Trap Entry Index "
                           ::= { vpwrTrapEntry 1}

         vpwrTrapIpAddress   OBJECT-TYPE
                                SYNTAX        IpAddress
                                MAX-ACCESS    read-write
                                STATUS        current
                                DESCRIPTION
                                   "Trap destination IP Address"
                           ::= { vpwrTrapEntry 2}

         vpwrTrapCriticality   OBJECT-TYPE
                                SYNTAX          INTEGER
                                MAX-ACCESS    read-write
                                STATUS        current
                                DESCRIPTION
                                   "Criticality of traps sent to this IP Address"
                           ::= { vpwrTrapEntry 3}


        vpwrReadCommunityString OBJECT-TYPE
                          SYNTAX     DisplayString(SIZE (3..8))
                          MAX-ACCESS read-write
                          STATUS     current
                          DESCRIPTION
                         " This allows setting password to be able to do Get operations"
                         ::= { vpwrDcPowerSnmpConfig 2 }

       vpwrWriteCommunityString OBJECT-TYPE
                          SYNTAX     DisplayString(SIZE (3..8))
                          MAX-ACCESS read-write
                          STATUS     current
                          DESCRIPTION
                          " This allows setting password to be able to do Get and Set
                            operations.
                            The read-access is not allowed in the actual implementation.
                          "
                          ::= { vpwrDcPowerSnmpConfig 3 }

           vpwrTrapCommunityString OBJECT-TYPE
                           SYNTAX     DisplayString(SIZE (3..8))
                           MAX-ACCESS read-write
                           STATUS     current
                           DESCRIPTION
                          " This allows setting community string required for the
                            trap to be accepted at the destination.
                          "
                           ::= { vpwrDcPowerSnmpConfig 4 }

           vpwrTrapVersion   OBJECT-TYPE
                               SYNTAX     INTEGER
                               MAX-ACCESS read-write
                               STATUS     current
                               DESCRIPTION
                              " This allows setting the version of trap message sent from the system" 
                               ::= { vpwrDcPowerSnmpConfig 5 }



--
--    LVD Alarm Group
--

--      vpwrLvdAlarmContactorOpen    OBJECT-IDENTITY
--             STATUS  current
--             DESCRIPTION
--             "Contactor open"
--             ::= {vpwrLvdAlarmGroup 1   }


--      vpwrLvdAlarmCBOpen    OBJECT-IDENTITY
--             STATUS  current
--             DESCRIPTION
--             "Circuit Breaker open"
--             ::= {vpwrLvdAlarmGroup 2   }

--      vpwrTrapLvdFuseOpen    OBJECT-IDENTITY
--             STATUS  current
--             DESCRIPTION
--             "Fuse open"
--             ::= {vpwrLvdAlarmGroup 3   }
   
--      vpwrLvdAlarmWarning    OBJECT-IDENTITY
--             STATUS  current
--             DESCRIPTION
--             "Plant Voltage below warning threshold"
--             ::= {vpwrLvdAlarmGroup 4   }

--
--    Rectifier Alarm Group
--

    vpwrRectAlarmDCFail   OBJECT-IDENTITY
           STATUS          current
           DESCRIPTION
           "
           "
           ::= {vpwrRectifierAlarmGroup   1}

    vpwrRectAlarmBoostFail   OBJECT-IDENTITY
           STATUS          current
           DESCRIPTION
           "
           "
           ::= {vpwrRectifierAlarmGroup   2}

    vpwrRectAlarmACFail   OBJECT-IDENTITY
           STATUS          current
           DESCRIPTION
           "
           "
           ::= {vpwrRectifierAlarmGroup   3}

    vpwrRectAlarmHVSD   OBJECT-IDENTITY
           STATUS          current
           DESCRIPTION
           "
           "
           ::= {vpwrRectifierAlarmGroup   4}

    vpwrRectAlarmFanFail   OBJECT-IDENTITY
           STATUS          current
           DESCRIPTION
           "
           "
           ::= {vpwrRectifierAlarmGroup   5}

    vpwrRectAlarmAmbTemp   OBJECT-IDENTITY
           STATUS          current
           DESCRIPTION
           "
           "
           ::= {vpwrRectifierAlarmGroup   6}
    vpwrRectAlarmIntTemp   OBJECT-IDENTITY
           STATUS          current
           DESCRIPTION
           "
           "
           ::= {vpwrRectifierAlarmGroup   7}

    vpwrRectAlarmIShare   OBJECT-IDENTITY
           STATUS          current
           DESCRIPTION
           "
           "
           ::= {vpwrRectifierAlarmGroup   8}

    vpwrRectAlarmUV   OBJECT-IDENTITY
           STATUS          current
           DESCRIPTION
           "
           "
           ::= {vpwrRectifierAlarmGroup   9}

    vpwrRectAlarmLowVoltage   OBJECT-IDENTITY
           STATUS          current
           DESCRIPTION
           "
           "
           ::= {vpwrRectifierAlarmGroup   10}

    vpwrRectAlarmReserved   OBJECT-IDENTITY
           STATUS          current
           DESCRIPTION
           "
           "
           ::= {vpwrRectifierAlarmGroup   11}

    vpwrRectAlarmDCEnable   OBJECT-IDENTITY
           STATUS          current
           DESCRIPTION
           "
           "
           ::= {vpwrRectifierAlarmGroup   12}

    vpwrRectAlarmRemoteShutdown   OBJECT-IDENTITY
           STATUS          current
           DESCRIPTION
           "
           "
           ::= {vpwrRectifierAlarmGroup   13}

    vpwrRectAlarmModDisableShutdown   OBJECT-IDENTITY
           STATUS          current
           DESCRIPTION
           "
           "
           ::= {vpwrRectifierAlarmGroup   14}

    vpwrRectAlarmShortPinShutdown   OBJECT-IDENTITY
           STATUS          current
           DESCRIPTION
           "
           "
           ::= {vpwrRectifierAlarmGroup   15}

    vpwrRectAlarmBoostComm   OBJECT-IDENTITY
           STATUS          current
           DESCRIPTION
           "
           "
           ::= {vpwrRectifierAlarmGroup   16}





    sysAlarmConfigTable OBJECT-TYPE
       SYNTAX     SEQUENCE OF SysAlarmConfigEntry
       MAX-ACCESS not-accessible
       STATUS     current
       DESCRIPTION
       "This table describes system alarm configuration and current
        status.
       "
       ::= { vpwrDcPowerAlarmGroup 3  }

    sysAlarmConfigEntry OBJECT-TYPE
       SYNTAX     SysAlarmConfigEntry
       MAX-ACCESS not-accessible
       STATUS     current
       DESCRIPTION
               "An entry containing information applicable to a
               particular system alarm."
       INDEX { sysAlarmIndex }
       ::= { sysAlarmConfigTable 1 }

    SysAlarmConfigEntry ::= SEQUENCE {
       sysAlarmIndex           INTEGER,
       sysAlarmDefaultName     DisplayString,
       sysAlarmCustomName      DisplayString,
       sysAlarmSeverity        INTEGER   ,
       sysAlarmToRelayMapping  DisplayString  ,
       sysAlarmOperStatus      INTEGER
    }

         sysAlarmIndex    OBJECT-TYPE
                                SYNTAX        INTEGER (0..255)
                                MAX-ACCESS    read-only
                                STATUS        current
                                DESCRIPTION
                                   "Index into system alarm table"
                           ::= { sysAlarmConfigEntry 1}

         sysAlarmDefaultName   OBJECT-TYPE
                                SYNTAX        DisplayString (SIZE (1..8))
                                MAX-ACCESS    read-only
                                STATUS        current
                                DESCRIPTION
                                   "Default alarm name."
                           ::= { sysAlarmConfigEntry 2}

         sysAlarmCustomName   OBJECT-TYPE
                                SYNTAX        DisplayString (SIZE (1..8))
                                MAX-ACCESS    read-write
                                STATUS        current
                                DESCRIPTION
                                   "A custom alarm name."
                           ::= { sysAlarmConfigEntry 3}

         sysAlarmSeverity   OBJECT-TYPE
                              SYNTAX INTEGER {
                                     none(0),
                                     major(1),
                                     minor(2),
                                     majorAndMinor(3)
                                     }
                                MAX-ACCESS    read-write
                                STATUS        current
                                DESCRIPTION
                                   "Alarm Severity as denoted by Major and Minor Alarm Mask"
                           ::= { sysAlarmConfigEntry 4}

           sysAlarmToRelayMapping   OBJECT-TYPE
                                SYNTAX DisplayString (SIZE (1..8))
                                MAX-ACCESS    read-write
                                STATUS        current
                                DESCRIPTION
                                   "No additional mapping = 0
                                    Map to Relay A  = 1
                                    Map to Relay B  = 2
                                    Map to Relay C  = 4
                                    Map to Relay D  = 8
                                    Map to Relay E  = 16
                                    Map to Relay F  = 32
                                    Map to Relay A and B  = (1 + 2) and so on
                                    The major/minor classification of alarms automatically
                                    associates it with Major/Minor relay. Assigning a null
                                    mapping here does not override vpwrPMRelayAlarmSeverity for
                                    the alarm.
                                    It should be used to define mapping to additional relays.
                                   "
                           ::= { sysAlarmConfigEntry 5}

         sysAlarmOperStatus   OBJECT-TYPE
                              SYNTAX INTEGER {
                                     inactive(0),
                                     active(1)
                                    }
                                MAX-ACCESS    read-only
                                STATUS        current
                                DESCRIPTION
                                   "Indicates current alarm status"
                           ::= { sysAlarmConfigEntry 6}




         sysAlarmComFailState   OBJECT-TYPE
                              SYNTAX INTEGER {
                                     disabled(0),
                                     enabled(1),
                                     other(2)
                                     }
                                MAX-ACCESS    read-write
                                STATUS        current
                                DESCRIPTION
                                   "Enable/Disable generation of comm fail alarm."
                           ::= { vpwrDcPowerAlarmGroup 4 }

         sysAlarmIShareState   OBJECT-TYPE
                              SYNTAX INTEGER {
                                     disabled(0),
                                     enabled(1),
                                     other(2)
                                     }
                                MAX-ACCESS    read-write
                                STATUS        current
                                DESCRIPTION
                                   "Enable/Disable generation of current share alarm."
                           ::= { vpwrDcPowerAlarmGroup 5}

         sysAlarmRedundancyState   OBJECT-TYPE
                              SYNTAX INTEGER {
                                     disabled(0),
                                     nPlus1(1),
                                     nPlus2(2)
                                     }
                                MAX-ACCESS    read-write
                                STATUS        current
                                DESCRIPTION
                                   "Enable/Disable generation of redundancy alarm."
                           ::= { vpwrDcPowerAlarmGroup 6}

         sysAlarmComFailToACFailState   OBJECT-TYPE
                              SYNTAX INTEGER {
                                     disabled(0),
                                     enabled(1)
                                     }
                                MAX-ACCESS    read-write
                                STATUS        current
                                DESCRIPTION
                                "Enable/Disable generation of ACF upon Com Fail"
                           ::= { vpwrDcPowerAlarmGroup 7}

-------------------------------------------------------------------------------------------

    vpwrDCPowerLampTest OBJECT-TYPE
       SYNTAX     INTEGER{
                  disabled(0),
                  enabled(1)
                  }
       MAX-ACCESS read-write
       STATUS     current
       DESCRIPTION
               "Lamp Test for modules"
       ::= { eltek 5 }

        vpwrPMCnfgTable    OBJECT-TYPE
                SYNTAX     SEQUENCE OF VpwrPMCnfgEntry
                MAX-ACCESS not-accessible
                STATUS     current
                DESCRIPTION
                    "This table shows the current configuration of the TRIO/PM86000/Controller inputs."
            ::=  { vpwrDcPowerPMModule 1 }

            vpwrPMCnfgEntry OBJECT-TYPE
                    SYNTAX     VpwrPMCnfgEntry
                    MAX-ACCESS not-accessible
                    STATUS     current
                    DESCRIPTION
                        "An entry containing current configuration of the TRIO/PM86000/Controller inputs."
                    INDEX         { vpwrPMIndex }
                ::= { vpwrPMCnfgTable 1 }

            VpwrPMCnfgEntry ::= SEQUENCE {
                vpwrPMIndex            NonNegativeInteger,
                vpwrPMDescription    DisplayString,
                vpwrPMCnfg1            VpwrPMCnfgValue,
                vpwrPMCnfg2            VpwrPMCnfgValue,
                vpwrPMCnfg3            VpwrPMCnfgValue,
                vpwrPMCnfg4            VpwrPMCnfgValue,
                vpwrPMCnfg5            VpwrPMCnfgValue,
                vpwrPMCnfg6            VpwrPMCnfgValue,
                vpwrPMCnfg7            VpwrPMCnfgValue,
                vpwrPMCnfg8            VpwrPMCnfgValue
                }

            vpwrPMIndex    OBJECT-TYPE
                    SYNTAX         NonNegativeInteger
                    MAX-ACCESS     read-only
                    STATUS         current
                    DESCRIPTION
                        "  This parameter describes which TRIO/PM86000 device is being accessed."
                ::= {vpwrPMCnfgEntry 1}

            vpwrPMDescription OBJECT-TYPE
                    SYNTAX         DisplayString
                    MAX-ACCESS     read-only
                    STATUS         current
                    DESCRIPTION
                        "  This parameter describes the configuration of the TRIO/PM86000 device."
                ::= {vpwrPMCnfgEntry 2}

            vpwrPMCnfg1    OBJECT-TYPE
                    SYNTAX         VpwrPMCnfgValue
                    MAX-ACCESS     read-write
                    STATUS         current
                    DESCRIPTION
                        "  This parameter gets the current configuration of the TRIO/PM86000, input 1"
                ::= {vpwrPMCnfgEntry 3}

            vpwrPMCnfg2    OBJECT-TYPE
                    SYNTAX         VpwrPMCnfgValue
                    MAX-ACCESS     read-write
                    STATUS         current
                    DESCRIPTION
                        "  This parameter gets the current configuration of the TRIO/PM86000, input 2"
                ::= {vpwrPMCnfgEntry 4}

            vpwrPMCnfg3    OBJECT-TYPE
                    SYNTAX         VpwrPMCnfgValue
                    MAX-ACCESS     read-write
                    STATUS         current
                    DESCRIPTION
                        "  This parameter gets the current configuration of the TRIO/PM86000, input 3"
                ::= {vpwrPMCnfgEntry 5}

            vpwrPMCnfg4    OBJECT-TYPE
                    SYNTAX         VpwrPMCnfgValue
                    MAX-ACCESS     read-write
                    STATUS         current
                    DESCRIPTION
                        "  This parameter gets the current configuration of the TRIO/PM86000, input 4"
                ::= {vpwrPMCnfgEntry 6}

            vpwrPMCnfg5    OBJECT-TYPE
                    SYNTAX         VpwrPMCnfgValue
                    MAX-ACCESS     read-write
                    STATUS         current
                    DESCRIPTION
                        "  This parameter gets the current configuration of the TRIO/PM86000, input 5"
                ::= {vpwrPMCnfgEntry 7}

            vpwrPMCnfg6    OBJECT-TYPE
                    SYNTAX         VpwrPMCnfgValue
                    MAX-ACCESS     read-write
                    STATUS         current
                    DESCRIPTION
                        "  This parameter gets the current configuration of the TRIO/PM86000, input 6"
                ::= {vpwrPMCnfgEntry 8}

            vpwrPMCnfg7    OBJECT-TYPE
                    SYNTAX         VpwrPMCnfgValue
                    MAX-ACCESS     read-write
                    STATUS         current
                    DESCRIPTION
                        "  This parameter gets the current configuration of the TRIO (PM86000), input 7"
                ::= {vpwrPMCnfgEntry 9}

            vpwrPMCnfg8    OBJECT-TYPE
                    SYNTAX         VpwrPMCnfgValue
                    MAX-ACCESS     read-write
                    STATUS         current
                    DESCRIPTION
                        "  This parameter gets the current configuration of the TRIO/PM86000, input 8"
                ::= {vpwrPMCnfgEntry 10}

-------------------------------------------------------------------------------------------

        vpwrPMInputStatusTable OBJECT-TYPE
                SYNTAX     SEQUENCE OF VpwrPMInputStatusEntry
                MAX-ACCESS not-accessible
                STATUS     current
                DESCRIPTION
                    "This table shows the current values of the TRIO/PM86000/Controller inputs."
            ::= { vpwrDcPowerPMModule 2  }

            vpwrPMInputStatusEntry OBJECT-TYPE
                    SYNTAX     VpwrPMInputStatusEntry
                    MAX-ACCESS not-accessible
                    STATUS     current
                    DESCRIPTION
                        "An entry containing current state of the TRIO/PM86000/Controller inputs."
                    INDEX { vpwrPMIndex1 }
                ::= { vpwrPMInputStatusTable 1 }

            VpwrPMInputStatusEntry ::= SEQUENCE {
                vpwrPMIndex1            NonNegativeInteger,
                vpwrPMDescription1    DisplayString,
                vpwrPMInput1State        SysInputValue,
                vpwrPMInput2State        SysInputValue,
                vpwrPMInput3State        SysInputValue,
                vpwrPMInput4State        SysInputValue,
                vpwrPMInput5State        SysInputValue,
                vpwrPMInput6State        SysInputValue,
                vpwrPMInput7State        SysInputValue,
                vpwrPMInput8State        SysInputValue
                }

           vpwrPMIndex1    OBJECT-TYPE
                 SYNTAX NonNegativeInteger
                 MAX-ACCESS read-only
                 STATUS current
                  DESCRIPTION
                  "  This parameter describes which TRIO/PM86000 device is being accessed."
                ::= {vpwrPMInputStatusEntry 1}

            vpwrPMDescription1 OBJECT-TYPE
                    SYNTAX DisplayString
                    MAX-ACCESS read-only
                    STATUS current
                    DESCRIPTION
                        "  This parameter describes the input values of the TRIO/PM86000 device."
                ::= {vpwrPMInputStatusEntry 2}

            vpwrPMInput1State    OBJECT-TYPE
                    SYNTAX SysInputValue
                    MAX-ACCESS read-only
                    STATUS current
                    DESCRIPTION
                        "  This parameter gets the current state of input 1"
                ::= {vpwrPMInputStatusEntry 3}

            vpwrPMInput2State    OBJECT-TYPE
                    SYNTAX SysInputValue
                    MAX-ACCESS read-only
                    STATUS current
                    DESCRIPTION
                        "  This parameter gets the current state of input 2"
                ::= {vpwrPMInputStatusEntry 4}

            vpwrPMInput3State    OBJECT-TYPE
                    SYNTAX SysInputValue
                    MAX-ACCESS read-only
                    STATUS current
                    DESCRIPTION
                        "  This parameter gets the current state of input 3"
                ::= {vpwrPMInputStatusEntry 5}

            vpwrPMInput4State    OBJECT-TYPE
                    SYNTAX SysInputValue
                    MAX-ACCESS read-only
                    STATUS current
                    DESCRIPTION
                        "  This parameter gets the current state of input 4"
                ::= {vpwrPMInputStatusEntry 6}

            vpwrPMInput5State    OBJECT-TYPE
                    SYNTAX SysInputValue
                    MAX-ACCESS read-only
                    STATUS current
                    DESCRIPTION
                        "  This parameter gets the current state of input 5"
                ::= {vpwrPMInputStatusEntry 7}

            vpwrPMInput6State    OBJECT-TYPE
                    SYNTAX SysInputValue
                    MAX-ACCESS read-only
                    STATUS current
                    DESCRIPTION
                        "  This parameter gets the current state of input 6"
                ::= {vpwrPMInputStatusEntry 8}

            vpwrPMInput7State    OBJECT-TYPE
                    SYNTAX SysInputValue
                    MAX-ACCESS read-only
                    STATUS current
                    DESCRIPTION
                        "  This parameter gets the current state of input 7"
                ::= {vpwrPMInputStatusEntry 9}

            vpwrPMInput8State    OBJECT-TYPE
                    SYNTAX SysInputValue
                    MAX-ACCESS read-only
                    STATUS current
                    DESCRIPTION
                        "  This parameter gets the current state of input 8"
                ::= {vpwrPMInputStatusEntry 10}

-------------------------------------------------------------------------------------------
        vpwrPMRelayCtrlTable OBJECT-TYPE
                SYNTAX     SEQUENCE OF VpwrPMRelayCtrlEntry
                MAX-ACCESS not-accessible
                STATUS     current
                DESCRIPTION
                    "This table describes/controls system relays."
            ::= { vpwrDcPowerPMModule 3 }

            vpwrPMRelayCtrlEntry OBJECT-TYPE
                    SYNTAX     VpwrPMRelayCtrlEntry
                    MAX-ACCESS not-accessible
                    STATUS     current
                    DESCRIPTION
                        "An entry containing current state of the relays."
                    INDEX { vpwrPMIndex2 }
                ::= { vpwrPMRelayCtrlTable 1 }

            VpwrPMRelayCtrlEntry ::= SEQUENCE {
                vpwrPMIndex2            NonNegativeInteger,
                vpwrPMDescription2    DisplayString,
                vpwrPMRelay1State        INTEGER,
                vpwrPMRelay2State        INTEGER,
                vpwrPMRelay3State        INTEGER,
                vpwrPMRelay4State        INTEGER,
                vpwrPMRelay5State        INTEGER,
                vpwrPMRelay6State        INTEGER
                }

            vpwrPMIndex2          OBJECT-TYPE
                    SYNTAX NonNegativeInteger
                    MAX-ACCESS read-only
                    STATUS current
                    DESCRIPTION
                        "  This parameter describes the TRIO/PM device"
                ::= {vpwrPMRelayCtrlEntry 1}

            vpwrPMDescription2 OBJECT-TYPE
                    SYNTAX DisplayString
                    MAX-ACCESS read-only
                    STATUS current
                    DESCRIPTION
                        "  This parameter describes the TRIO/PM device"
                ::= {vpwrPMRelayCtrlEntry 2}

            vpwrPMRelay1State    OBJECT-TYPE
                    SYNTAX INTEGER {
                        vpwrPMRelayOff(0),
                        vpwrPMRelayOn(1),
                        undefined(255)
                        }
                    MAX-ACCESS read-write
                    STATUS current
                    DESCRIPTION
                        "  This parameter sets the current state of relay 1"
                ::= {vpwrPMRelayCtrlEntry 3}

            vpwrPMRelay2State    OBJECT-TYPE
                    SYNTAX INTEGER {
                        vpwrPMRelayOff(0),
                        vpwrPMRelayOn(1),
                        undefined(255)
                        }
                    MAX-ACCESS read-write
                    STATUS current
                    DESCRIPTION
                        "  This parameter sets the current state of relay 2"
                ::= {vpwrPMRelayCtrlEntry 4}

            vpwrPMRelay3State    OBJECT-TYPE
                    SYNTAX INTEGER {
                        vpwrPMRelayOff(0),
                        vpwrPMRelayOn(1),
                        undefined(255)
                        }
                    MAX-ACCESS read-write
                    STATUS current
                    DESCRIPTION
                        "  This parameter sets the current state of relay 3"
                ::= {vpwrPMRelayCtrlEntry 5}

            vpwrPMRelay4State    OBJECT-TYPE
                    SYNTAX INTEGER {
                        vpwrPMRelayOff(0),
                        vpwrPMRelayOn(1),
                        undefined(255)
                        }
                    MAX-ACCESS read-write
                    STATUS current
                    DESCRIPTION
                        "  This parameter sets the current state of relay 4"
                ::= {vpwrPMRelayCtrlEntry 6}

            vpwrPMRelay5State    OBJECT-TYPE
                    SYNTAX INTEGER {
                        vpwrPMRelayOff(0),
                        vpwrPMRelayOn(1),
                        undefined(255)
                        }
                    MAX-ACCESS read-write
                    STATUS current
                    DESCRIPTION
                        "  This parameter sets the current state of relay 5"
                ::= {vpwrPMRelayCtrlEntry 7}

            vpwrPMRelay6State    OBJECT-TYPE
                    SYNTAX INTEGER {
                        vpwrPMRelayOff(0),
                        vpwrPMRelayOn(1),
                        undefined(255)
                        }
                    MAX-ACCESS read-write
                    STATUS current
                    DESCRIPTION
                        "  This parameter sets the current state of relay 6"
                ::= {vpwrPMRelayCtrlEntry 8}



    --
    -- The Ringer Configuration Parameters group.
    --


       vpwrRingerIndex   OBJECT-TYPE
                         SYNTAX INTEGER (0..2)
                         MAX-ACCESS read-write
                         STATUS current
                         DESCRIPTION
                         "  This parameter allows selecting ringer A or Ringer B as the active ringer.
                         "
                         ::= {vpwrRingerConfigGroup 1}

            vpwrRingerParameterAdminState OBJECT-TYPE
                         SYNTAX INTEGER {
                                ringerDisabled(0),
                                ringerAOn(1) ,
                                ringerBOn(2)
                        }
                         MAX-ACCESS read-write
                         STATUS current
                         DESCRIPTION
                         "  This parameter allows selecting ringer A or Ringer B as the active ringer.
                         "
                         ::= {vpwrRingerConfigGroup 2}

              vpwrRingerParameterAcVoltage OBJECT-TYPE
                         SYNTAX INTEGER (7000..10000)
                         UNITS  " *.01 Volts"
                         MAX-ACCESS read-write
                         STATUS current
                         DESCRIPTION
                         " This parameter sets the output AC voltage of the ringer.
                         "
                         ::= {vpwrRingerConfigGroup 3}

               vpwrRingerParameterDcVoltage OBJECT-TYPE
                         SYNTAX INTEGER (0..5500 )
                         UNITS  " *.01 Volts"
                         MAX-ACCESS read-write
                         STATUS current
                         DESCRIPTION
                         " This parameter sets the DC offset value of the ringer.
                         "
                         ::= {vpwrRingerConfigGroup 4}

               vpwrRingerParameterFrequency OBJECT-TYPE
                         SYNTAX INTEGER (17..50)
                         UNITS  " Hz"
                         MAX-ACCESS read-write
                         STATUS current
                         DESCRIPTION
                         " This parameter sets the ringer AC frequency.
                         "
                         ::= {vpwrRingerConfigGroup 5}

                            vpwrRingerNumberPresent OBJECT-TYPE
                                           SYNTAX     Gauge32
                                           MAX-ACCESS read-only
                                           STATUS     current
                                           DESCRIPTION
                                                   "The present number of ringer modules."
                                           ::= { vpwrRingerConfigGroup 6 }


--
--    ringer Alarm Group
--

     vpwrRingerAlarmAFailed    OBJECT-IDENTITY
                        STATUS  current
            DESCRIPTION
            "Ringer A Failed"
            ::= {vpwrRingerAlarmGroup 1   }

     vpwrRingerAlarmAOverTemp    OBJECT-IDENTITY
                        STATUS  current
            DESCRIPTION
            "Ringer A Heatsink Over-Temperature"
            ::= {vpwrRingerAlarmGroup 2   }

     vpwrRingerAlarmAOverCurrent    OBJECT-IDENTITY
                        STATUS  current
            DESCRIPTION
            "Ringer A Over-Current protection"
            ::= {vpwrRingerAlarmGroup 3   }

      vpwrRingerAlarmBFailed    OBJECT-IDENTITY
                        STATUS  current
            DESCRIPTION
            "Ringer B Failed"
            ::= {vpwrRingerAlarmGroup 4   }

     vpwrRingerAlarmBOverTemp    OBJECT-IDENTITY
                        STATUS  current
            DESCRIPTION
            "Ringer B Heatsink Over-Temperature"
            ::= {vpwrRingerAlarmGroup 5   }

     vpwrRingerAlarmBOverCurrent    OBJECT-IDENTITY
                        STATUS  current
            DESCRIPTION
            "Ringer B Over-Current protection"
            ::= {vpwrRingerAlarmGroup 6   }



    vpwrBoostAdminState OBJECT-TYPE
                         SYNTAX INTEGER {
                                boostDisabled(0),
                                boostEnabled(1)
                        }
                         MAX-ACCESS read-write
                         STATUS current
                         DESCRIPTION
                         "  This parameter allows enabling or disabling boost.
                         "
                         REFERENCE " "

                         ::= {vpwrBatteryBoostGroup 1}

      vpwrBoostVoltage OBJECT-TYPE
                         SYNTAX INTEGER 
                         UNITS  " *.01 Volts"
                         MAX-ACCESS read-write
                         STATUS current
                         DESCRIPTION
                         "
                         "
                         REFERENCE " "
                         ::= {vpwrBatteryBoostGroup 2}

      vpwrBoostDuration OBJECT-TYPE
                         SYNTAX INTEGER (1..921599)
                         UNITS  "Seconds"
                         MAX-ACCESS read-write
                         STATUS current
                         DESCRIPTION
                         " Number of seconds for boost.
                         "
                         REFERENCE " "
                         ::= {vpwrBatteryBoostGroup 3}

    vpwrBoostOperState OBJECT-TYPE
                         SYNTAX INTEGER {
                                boostInactive(0),
                                boostActive(1)
                        }
                         MAX-ACCESS read-write
                         STATUS current
                         DESCRIPTION
                         "  This parameter allows starting or stopping boost if it is enabled.
                         "
                         REFERENCE " "

                         ::= {vpwrBatteryBoostGroup 4}


    vpwrBatteryCurrentLimitAdminState OBJECT-TYPE
                         SYNTAX INTEGER {
                                batteryCurrentLimitDisabled(0),
                                batteryCurrentLimitEnabled(1)
                        }
                         MAX-ACCESS read-write
                         STATUS current
                         DESCRIPTION
                         "  This parameter allows enabling or disabling battery current limit.
                         "
                         REFERENCE " "

                         ::= {vpwrBatteryCurrentGroup 1}

      vpwrBatteryCurrentLimit OBJECT-TYPE
                         SYNTAX INTEGER (5..600)
                         UNITS  "Ampere"
                         MAX-ACCESS read-write
                         STATUS current
                         DESCRIPTION
                         "
                         "
                         REFERENCE " "
                         ::= {vpwrBatteryCurrentGroup 2}

       vpwrBatteryCurrent OBJECT-TYPE
                         SYNTAX INTEGER
                         UNITS  "Ampere"
                         MAX-ACCESS read-only
                         STATUS current
                         DESCRIPTION
                         "Battery current
                         "
                         REFERENCE " "
                         ::= {vpwrBatteryCurrentGroup 3}



    vpwrBDTAdminState OBJECT-TYPE
                         SYNTAX INTEGER {
                                bdtManualDisabled(0),
                                bdtManualEnabled(1) 
                        }
                         MAX-ACCESS read-write
                         STATUS current
                         DESCRIPTION
                         "  Enable / Disable Battery Discharge Test execution.
                         "
                         REFERENCE " "

                         ::= {vpwrBatteryDischargeTestGroup 1}

    vpwrBDTDuration OBJECT-TYPE
                         SYNTAX INTEGER (0..64799)
                         UNITS  "Seconds"
                         MAX-ACCESS read-only
                         STATUS current
                         DESCRIPTION
                         "BDT Duration Setpoint.
                         "
                         REFERENCE " "
                         ::= {vpwrBatteryDischargeTestGroup 2}
     vpwrBDTAlarmVoltage OBJECT-TYPE
                         SYNTAX INTEGER 
                         UNITS  " *.01 Volts"
                         MAX-ACCESS read-write
                         STATUS current
                         DESCRIPTION
                         "BDT Alarm Voltage Setpoint.
                         "
                         REFERENCE " "
                         ::= {vpwrBatteryDischargeTestGroup 3}

     vpwrBDTAbortVoltage OBJECT-TYPE
                         SYNTAX INTEGER 
                         UNITS  " *.01 Volts"
                         MAX-ACCESS read-write
                         STATUS current
                         DESCRIPTION
                         "BDT Abort Voltage Setpoint.
                         "
                         REFERENCE " "
                         ::= {vpwrBatteryDischargeTestGroup 4}

     vpwrBDTAlarmCoefficient OBJECT-TYPE
                         SYNTAX INTEGER
                         UNITS  "None"
                         MAX-ACCESS read-only
                         STATUS current
                         DESCRIPTION
                         "Deprecated.  Always returns 1
                         "
                         REFERENCE " "
                         ::= {vpwrBatteryDischargeTestGroup 5}

     vpwrBDTOperState OBJECT-TYPE
                         SYNTAX INTEGER {
                                bdtInactive(0),
                                bdtManualStart(1),
                                bdtACFailStart(14)

                        }
                         MAX-ACCESS read-only
                         STATUS current
                         DESCRIPTION
                         "  Start/Stop Battery Discharge Test execution.
                         "
                         REFERENCE " "

                         ::= {vpwrBatteryDischargeTestGroup 6}

     vpwrBDTClearAlarm OBJECT-TYPE
                         SYNTAX INTEGER {
                                bdtNoAlarm(0),
                                bdtAlarmPresent(1)
                        }
                         MAX-ACCESS read-only
                         STATUS current
                         DESCRIPTION
                         "  Clears any active BDT alarm.
                         "
                         REFERENCE " "

                         ::= {vpwrBatteryDischargeTestGroup 7}

     vpwrBDTActualTime OBJECT-TYPE
                         SYNTAX INTEGER
                         UNITS  "minutes" 
                         MAX-ACCESS read-only
                         STATUS current
                         DESCRIPTION
                         "  Actual BDT runtime in minutes.
                         "
                         REFERENCE " "

                         ::= {vpwrBatteryDischargeTestGroup 8}

      vpwrBDTAlarmDelay OBJECT-TYPE
                         SYNTAX INTEGER
                         UNITS  "minutes" 
                         MAX-ACCESS read-only
                         STATUS current
                         DESCRIPTION
                         "  Delay, in minutes, before checking and raising 
                            BDT alarm.
                            Test: Plant Voltage <= BDTAlarmVoltage
                         "
                         REFERENCE " "

                         ::= {vpwrBatteryDischargeTestGroup 9}
      vpwrBDTResult OBJECT-TYPE
                         SYNTAX BDTResultTC
                         MAX-ACCESS read-only
                         STATUS current
                         DESCRIPTION
                         "  Results of BDT.
                         "
                         REFERENCE " "

                         ::= {vpwrBatteryDischargeTestGroup 10}

    vpwrBDTAutoAdminState OBJECT-TYPE
                         SYNTAX INTEGER {
                                bdtAutoDisabled(0),
                                bdtAutoEnabled(1) 
                        }
                         MAX-ACCESS read-write
                         STATUS current
                         DESCRIPTION
                         "  Enable /Disable Battery Discharge Test data collection
                           upon detecting AC Fail condition.
                         "
                         REFERENCE " "

                         ::= {vpwrBatteryDischargeTestGroup 11}

--
-- BDT History Start
    --
    -- The System History group.
    --
    vpwrBDTHistTable OBJECT-TYPE
       SYNTAX     SEQUENCE OF VpwrBDTHistEntry
       MAX-ACCESS not-accessible
       STATUS     current
       DESCRIPTION
       " This table provides results of past BDT test.
       "
       ::= { vpwrBatteryDischargeTestGroup 12 }


    vpwrBDTHistEntry OBJECT-TYPE
       SYNTAX     VpwrBDTHistEntry
       MAX-ACCESS not-accessible
       STATUS     current
       DESCRIPTION
               "An entry containing information applicable to a
               particular BDT History."

       INDEX { vpwrBDTHistIndex }

       ::= { vpwrBDTHistTable 1 }
    VpwrBDTHistEntry ::= SEQUENCE {
        vpwrBDTHistIndex            PositiveInteger,
        vpwrBDTHistDateTime         DisplayString,
        vpwrBDTHistDuration         PositiveInteger,
        vpwrBDTHistAlarmVoltage     PositiveInteger,
        vpwrBDTHistAbortVoltage     PositiveInteger,
        vpwrBDTHistStartMethod      BDTStartSourceTC,
        vpwrBDTHistResult           BDTResultTC,
        vpwrBDTHistActualTime       PositiveInteger,
        vpwrBDTHistStartVoltage     PositiveInteger,
        vpwrBDTHistEndVoltage       PositiveInteger
    }

       vpwrBDTHistIndex OBJECT-TYPE
               SYNTAX     PositiveInteger
               MAX-ACCESS read-only
               STATUS     current
               DESCRIPTION
                 "BDT History index."
               ::= { vpwrBDTHistEntry 1 }
       
    vpwrBDTHistDateTime OBJECT-TYPE
                         SYNTAX DisplayString
                         MAX-ACCESS read-only
                         STATUS current
                         DESCRIPTION
                         " BDT run date as
                           yr-mm-dd hh:mm
                         "
                         REFERENCE " "
                         ::= {vpwrBDTHistEntry 2}
    vpwrBDTHistDuration OBJECT-TYPE
                         SYNTAX PositiveInteger
                         UNITS  "Minutes"
                         MAX-ACCESS read-only
                         STATUS current
                         DESCRIPTION
                         "BDT duration at the time
                          this test was run.
                         "
                         REFERENCE " "
                         ::= {vpwrBDTHistEntry 3}

     vpwrBDTHistAlarmVoltage OBJECT-TYPE
                         SYNTAX PositiveInteger 
                         UNITS  " *.01 Volts"
                         MAX-ACCESS read-write
                         STATUS current
                         DESCRIPTION
                         "BDT Alarm Voltage setpoint when
                          this test was run.
                         "
                         REFERENCE " "
                         ::= {vpwrBDTHistEntry 4}

       vpwrBDTHistAbortVoltage OBJECT-TYPE
                         SYNTAX PositiveInteger
                         UNITS  " *.01 Volts"
                         MAX-ACCESS read-only
                         STATUS current
                         DESCRIPTION
                         "BDT Abort Voltage setpoint when
                          this test was run.
                         "
                         REFERENCE " "
                         ::= {vpwrBDTHistEntry 5}


     vpwrBDTHistStartMethod OBJECT-TYPE
                         SYNTAX BDTStartSourceTC 
                         MAX-ACCESS read-only
                         STATUS current
                         DESCRIPTION
                         "How Battery Discharge Test 
                         was started.
                         "
                         REFERENCE " "

                         ::= {vpwrBDTHistEntry 6}

      vpwrBDTHistResult OBJECT-TYPE
                         SYNTAX BDTResultTC
                         MAX-ACCESS read-only
                         STATUS current
                         DESCRIPTION
                         "  Results of BDT. 
                         "
                         REFERENCE " "

                         ::= {vpwrBDTHistEntry 7}

      vpwrBDTHistActualTime OBJECT-TYPE
                         SYNTAX PositiveInteger
                         UNITS  "minutes" 
                         MAX-ACCESS read-only
                         STATUS current
                         DESCRIPTION
                         "  Actual BDT runtime in minutes.
                         "
                         REFERENCE " "

                         ::= {vpwrBDTHistEntry 8}

      vpwrBDTHistStartVoltage OBJECT-TYPE
                         SYNTAX PositiveInteger                        
                         UNITS  " *.01 Volts"
                         MAX-ACCESS read-only
                         STATUS current
                         DESCRIPTION
                         "Plant Voltage at the time 
                         the BDT was started.
                         "
                         REFERENCE " "

                         ::= {vpwrBDTHistEntry 9}
      vpwrBDTHistEndVoltage OBJECT-TYPE
                         SYNTAX PositiveInteger    
                         UNITS  " *.01 Volts"
                         MAX-ACCESS read-only
                         STATUS current
                         DESCRIPTION
                         "Plant Voltage at the time
                         the BDT was completed.
                         "
                         REFERENCE " "

                         ::= {vpwrBDTHistEntry 10}

-- BDT History End

-- BDT scheduled Start
    --
    -- The System History group.
    --
    vpwrBDTSchedTable OBJECT-TYPE
       SYNTAX     SEQUENCE OF VpwrBDTSchedEntry
       MAX-ACCESS not-accessible
       STATUS     current
       DESCRIPTION
       " This table provides the list of the 12 BDTs  that can be
         scheduled.    Need to set date(month and day) and 
         time (hh and minutes) when the test should be 
         started.
       "
       ::= { vpwrBatteryDischargeTestGroup 13 }


    vpwrBDTSchedEntry OBJECT-TYPE
       SYNTAX     VpwrBDTSchedEntry
       MAX-ACCESS not-accessible
       STATUS     current
       DESCRIPTION
         "An entry describing an alarm."
       INDEX { vpwrBDTSchedIndex}
       ::= { vpwrBDTSchedTable 1 }

    VpwrBDTSchedEntry ::= SEQUENCE {
        vpwrBDTSchedIndex          PositiveInteger,
        vpwrBDTSchedMonth          PositiveInteger,
        vpwrBDTSchedDay            PositiveInteger,
        vpwrBDTSchedHour           PositiveInteger,
        vpwrBDTSchedMinute         PositiveInteger
    }

       vpwrBDTSchedIndex OBJECT-TYPE
               SYNTAX     PositiveInteger
               MAX-ACCESS read-only
               STATUS     current
               DESCRIPTION
                 "BDT Sched index."
               ::= { vpwrBDTSchedEntry 1 }
       
    vpwrBDTSchedDay OBJECT-TYPE
          SYNTAX         PositiveInteger
          MAX-ACCESS     read-write
          STATUS         current
          DESCRIPTION
                         " 1  to 28,29,30 or 31 depending upon the month
                         "
                         REFERENCE " "
                         ::= {vpwrBDTSchedEntry 2}

     vpwrBDTSchedMonth OBJECT-TYPE
          SYNTAX         PositiveInteger
          MAX-ACCESS     read-write
          STATUS         current
          DESCRIPTION
                         "  range 1 to 12
                         "
                         REFERENCE " "
                         ::= {vpwrBDTSchedEntry 3}

     vpwrBDTSchedHour OBJECT-TYPE
          SYNTAX         PositiveInteger
          MAX-ACCESS     read-write
          STATUS         current
          DESCRIPTION
                         "  range 0 to 23
                         "
                         REFERENCE " "
                         ::= {vpwrBDTSchedEntry 4}

       vpwrBDTSchedMinute OBJECT-TYPE
          SYNTAX         PositiveInteger
          MAX-ACCESS     read-write
          STATUS         current
          DESCRIPTION
                         " range 0 to 59
                         "
                         REFERENCE " "
                         ::= {vpwrBDTSchedEntry 5}


-- BDT Scheduled End

--
--  traps
--
-- New Rules for trap numbering
-- Rules are even number = trap set
--           odd number  = trap clear

vpwrTrapPowerMajorAlarm NOTIFICATION-TYPE
                        OBJECTS { vpwrTrapsMsgString }
                           STATUS          current
                        DESCRIPTION "Major Alarm"
                        ::= {vpwrDcPowerTraps 1}

    vpwrTrapPowerMinorAlarm   NOTIFICATION-TYPE
                        OBJECTS { vpwrTrapsMsgString }
                           STATUS          current
                        DESCRIPTION "Minor Alarm"
                        ::= {vpwrDcPowerTraps 2}

     vpwrTrapACFAlarm   NOTIFICATION-TYPE
                        OBJECTS { vpwrTrapsMsgString }
                           STATUS          current
                        DESCRIPTION "AC Fail Alarm"
                        ::= {vpwrDcPowerTraps 3}

    vpwrTrapHVAlarm   NOTIFICATION-TYPE
                        OBJECTS { vpwrTrapsMsgString }
                           STATUS          current
                        DESCRIPTION "High Voltage Warning Alarm"
                        ::= {vpwrDcPowerTraps 4}

    vpwrTrapHVSDAlarm   NOTIFICATION-TYPE
                        OBJECTS { vpwrTrapsMsgString }
                           STATUS          current
                        DESCRIPTION "High Voltage Shutdown Alarm"
                        ::= {vpwrDcPowerTraps 5}

    vpwrTrapBDAlarm   NOTIFICATION-TYPE
                        OBJECTS { vpwrTrapsMsgString }
                           STATUS          current
                        DESCRIPTION "Battery on Discharge Alarm"
                        ::= {vpwrDcPowerTraps 6}

     vpwrTrapLVDWarningAlarm   NOTIFICATION-TYPE
                        OBJECTS { vpwrTrapsMsgString }
                           STATUS          current
                        DESCRIPTION "LVD Warning Alarm"
                        ::= {vpwrDcPowerTraps 7}

      vpwrTrapLVDOpenAlarm   NOTIFICATION-TYPE
                        OBJECTS { vpwrTrapsMsgString }
                           STATUS          current
                        DESCRIPTION "LVD Open Alarm"
                        ::= {vpwrDcPowerTraps 8}

     vpwrTrapDistAlarm   NOTIFICATION-TYPE
                        OBJECTS { vpwrTrapsMsgString }
                           STATUS          current
                        DESCRIPTION "Distribution Open Alarm"
                        ::= {vpwrDcPowerTraps 9}

     vpwrTrapAuxAlarm   NOTIFICATION-TYPE
                        OBJECTS { vpwrTrapsMsgString }
                           STATUS          current
                        DESCRIPTION "Auxiliary System Alarm"
                        ::= {vpwrDcPowerTraps 10}

     vpwrTrapSystemRedundancyAlarm   NOTIFICATION-TYPE
                        OBJECTS { vpwrTrapsMsgString }
                           STATUS          current
                        DESCRIPTION "System Redundant Capacity Alarm"
                        ::= {vpwrDcPowerTraps 11}

     vpwrTrapIShareAlarm   NOTIFICATION-TYPE
                        OBJECTS { vpwrTrapsMsgString }
                           STATUS          current
                        DESCRIPTION "Rectifier Current Share Alarm"
                        ::= {vpwrDcPowerTraps 12}

     vpwrTrapModuleFailAlarm   NOTIFICATION-TYPE
                        OBJECTS { vpwrTrapsMsgString }
                           STATUS          current
                        DESCRIPTION "Single Rectifier Fail Alarm"
                        ::= {vpwrDcPowerTraps 13}

     vpwrTrapMultipleModuleFailAlarm   NOTIFICATION-TYPE
                        OBJECTS { vpwrTrapsMsgString }
                           STATUS          current
                        DESCRIPTION "Multiple Rectifier Fail Alarm"
                        ::= {vpwrDcPowerTraps 14}

     vpwrTrapModuleCommAlarm   NOTIFICATION-TYPE
                        OBJECTS { vpwrTrapsMsgString }
                           STATUS          current
                        DESCRIPTION "Power Module Communication Alarm"
                        ::= {vpwrDcPowerTraps 15}

     vpwrTrapSystemOverTemperatureAlarm   NOTIFICATION-TYPE
                        OBJECTS { vpwrTrapsMsgString }
                           STATUS          current
                        DESCRIPTION "System Over Temperature Alarm"
                        ::= {vpwrDcPowerTraps 16}

     vpwrTrapSystemOK   NOTIFICATION-TYPE
                        OBJECTS { vpwrTrapsMsgString }
                           STATUS          current
                        DESCRIPTION "SYSTEM OK - No Active Alarms"
                        ::= {vpwrDcPowerTraps 17}

    vpwrTrapModuleInserted NOTIFICATION-TYPE
                        OBJECTS { vpwrTrapsMsgString, vpwrShelfIndex, vpwrModuleIndex }
                           STATUS          current
                           DESCRIPTION "A new module has been inserted into the system"
                        ::= {vpwrDcPowerTraps 18}

    vpwrTrapModuleRemoved NOTIFICATION-TYPE
                        OBJECTS { vpwrTrapsMsgString,vpwrShelfIndex, vpwrModuleIndex }
                           STATUS          current
                           DESCRIPTION "A module has been removed from the system"
                        ::= {vpwrDcPowerTraps 19}

    vpwrTrapThermalCompActive   NOTIFICATION-TYPE
                        OBJECTS { vpwrTrapsMsgString }
                           STATUS          current
                        DESCRIPTION "Thermal compensation has become active"
                        ::= {vpwrDcPowerTraps 20}

    vpwrTrapThermalCompInactive   NOTIFICATION-TYPE
                        OBJECTS { vpwrTrapsMsgString }
                        STATUS          current
                        DESCRIPTION "Thermal compensation has been de-activated"
                        ::= {vpwrDcPowerTraps 21}

    vpwrTrapInternalTempAlarmSet   NOTIFICATION-TYPE
                        OBJECTS { vpwrTrapsMsgString }
                        STATUS          current
                        DESCRIPTION "!!! NOT VALID FOR BC2000 CONTROLLER !!!
                            Internal Temperature upper threshold exceeded"
                        ::= {vpwrDcPowerTraps 22}

    vpwrTrapInternalTempAlarmCleared   NOTIFICATION-TYPE
                        OBJECTS { vpwrTrapsMsgString }
                        STATUS          current
                        DESCRIPTION "!!! NOT VALID FOR BC2000 CONTROLLER !!!
                            Internal Temperature within limits"
                        ::= {vpwrDcPowerTraps 23}

    vpwrTrapBatteryTempAlarmSet   NOTIFICATION-TYPE
                        OBJECTS { vpwrTrapsMsgString }
                        STATUS          current
                        DESCRIPTION "!!! NOT VALID FOR BC2000 CONTROLLER !!!
                            At least one Battery Temperature exceeded upper threshold"
                        ::= {vpwrDcPowerTraps 24}

    vpwrTrapBatteryTempAlarmCleared   NOTIFICATION-TYPE
                        OBJECTS { vpwrTrapsMsgString }
                        STATUS          current
                        DESCRIPTION "!!! NOT VALID FOR BC2000 CONTROLLER !!!
                            All Battery Temperatures within limits"
                        ::= {vpwrDcPowerTraps 25}

    vpwrTrapLoginFail   NOTIFICATION-TYPE
                        OBJECTS { vpwrTrapsMsgString }
                        STATUS          current
                        DESCRIPTION "!!! NOT VALID FOR BC2000 CONTROLLER !!!
                            Admin login failed due to wrong username/password"
                        ::= {vpwrDcPowerTraps 26}

    vpwrTrapLoginSuccess   NOTIFICATION-TYPE
                        OBJECTS { vpwrTrapsMsgString }
                        STATUS          current
                        DESCRIPTION "!!! NOT VALID FOR BC2000 CONTROLLER !!!
                            Admin login successful"
                        ::= {vpwrDcPowerTraps 27}

    vpwrTrapLogout   NOTIFICATION-TYPE
                        OBJECTS { vpwrTrapsMsgString }
                        STATUS          current
                        DESCRIPTION "!!! NOT VALID FOR BC2000 CONTROLLER !!!
                            Admin logout"
                        ::= {vpwrDcPowerTraps 28}
                              
    vpwrTrapAdminPwdChange   NOTIFICATION-TYPE
                        OBJECTS { vpwrTrapsMsgString }
                        STATUS          current
                        DESCRIPTION "!!! NOT VALID FOR BC2000 CONTROLLER !!!
                            Config change submitted with invalid access"
                        ::= {vpwrDcPowerTraps 29}

    vpwrTrapIllegalConfigSubmit   NOTIFICATION-TYPE
                        OBJECTS { vpwrTrapsMsgString }
                        STATUS          current
                        DESCRIPTION "!!! NOT VALID FOR BC2000 CONTROLLER !!!
                            Config change submitted with invalid access"
                        ::= {vpwrDcPowerTraps 30}

    vpwrTrapCfgChange   NOTIFICATION-TYPE
                        OBJECTS { vpwrTrapsMsgString }
                        STATUS          current
                        DESCRIPTION "!!! NOT VALID FOR BC2000 CONTROLLER !!!
                            Config change submitted"
                        ::= {vpwrDcPowerTraps 31}

    vpwrTrapClearEventHistory    NOTIFICATION-TYPE
                        OBJECTS { vpwrTrapsMsgString }
                        STATUS          current
                        DESCRIPTION "!!! NOT VALID FOR BC2000 CONTROLLER !!!
                            Clear Event history buffer clear request"
                        ::= {vpwrDcPowerTraps 32}

    vpwrTrapSwDownloadNoReboot    NOTIFICATION-TYPE
                        OBJECTS { vpwrTrapsMsgString }
                        STATUS          current
                        DESCRIPTION "!!! NOT VALID FOR BC2000 CONTROLLER !!!
                            System software upgrade without reboot"
                        ::= {vpwrDcPowerTraps 33}

    vpwrTrapSwDownloadAndReboot    NOTIFICATION-TYPE
                        OBJECTS { vpwrTrapsMsgString }
                        STATUS          current
                        DESCRIPTION "!!! NOT VALID FOR BC2000 CONTROLLER !!!
                            System reboot due to software upgrade"
                        ::= {vpwrDcPowerTraps 34}

    vpwrTrapSystemClockChange    NOTIFICATION-TYPE
                        OBJECTS { vpwrTrapsMsgString }
                        STATUS          current
                        DESCRIPTION "!!! NOT VALID FOR BC2000 CONTROLLER !!!
                            System clock updated"
                        ::= {vpwrDcPowerTraps 35}

    vpwrTrapModuleAlarm    NOTIFICATION-TYPE
                        OBJECTS { vpwrTrapsMsgString }
                        STATUS          current
                        DESCRIPTION "!!! NOT VALID FOR BC2000 CONTROLLER !!!
                            Module Alarm"
                        ::= {vpwrDcPowerTraps 36}

    vpwrTrapOIDChange    NOTIFICATION-TYPE
                        OBJECTS { vpwrTrapsMsgString }
                        STATUS          current
                        DESCRIPTION "!!! NOT VALID FOR BC2000 CONTROLLER !!!
                            Change in OID"
                        ::= {vpwrDcPowerTraps 37}

    vpwrTrapThermalRunaway    NOTIFICATION-TYPE
                        OBJECTS { vpwrTrapsMsgString }
                        STATUS          current
                        DESCRIPTION "Thermal Runaway Alarm"
                        ::= {vpwrDcPowerTraps 38}

    vpwrTrapBatteryDischargeTestAlarm    NOTIFICATION-TYPE
                        OBJECTS { vpwrTrapsMsgString }
                        STATUS          current
                        DESCRIPTION "System Voltage dropped to BDT Alarm Setpoint"
                        ::= {vpwrDcPowerTraps 39}

    vpwrTrapBayUnnameAlarm    NOTIFICATION-TYPE
                        OBJECTS { vpwrTrapsMsgString }
                        STATUS          current
                        DESCRIPTION "!!! NOT VALID FOR BC2000 CONTROLLER !!!
                            Unassigned Bay Fail Alarm"
                        ::= {vpwrDcPowerTraps 40}

    vpwrTrapPMComFailAlarm    NOTIFICATION-TYPE
                        OBJECTS { vpwrTrapsMsgString }
                        STATUS          current
                        DESCRIPTION "!!! NOT VALID FOR BC2000 CONTROLLER !!!
                            PM Communication Fail Alarm"
                        ::= {vpwrDcPowerTraps 41}

    vpwrTrapFuseOverloadAlarm    NOTIFICATION-TYPE
                        OBJECTS { vpwrTrapsMsgString }
                        STATUS          current
                        DESCRIPTION "!!! NOT VALID FOR BC2000 CONTROLLER !!!
                            Fuse Overload Alarm"
                        ::= {vpwrDcPowerTraps 42}

    vpwrTrapPeripheralAlarm    NOTIFICATION-TYPE
                        OBJECTS { vpwrTrapsMsgString }
                        STATUS          current
                        DESCRIPTION "!!! NOT VALID FOR BC2000 CONTROLLER !!!
                            Peripheral Alarm."
                        ::= {vpwrDcPowerTraps 43}

    vpwrTrapThermalProbeAlarm    NOTIFICATION-TYPE
                        OBJECTS { vpwrTrapsMsgString }
                        STATUS          current
                        DESCRIPTION "Thermal Probe Missing Alarm"
                        ::= {vpwrDcPowerTraps 44}

    vpwrTrapBayCommAlarm    NOTIFICATION-TYPE
                        OBJECTS { vpwrTrapsMsgString }
                        STATUS          current
                        DESCRIPTION "!!! NOT VALID FOR BC2000 CONTROLLER !!!
                            Bay Communication Alarm"
                        ::= {vpwrDcPowerTraps 45}

    vpwrTrapDistributionCommAlarm    NOTIFICATION-TYPE
                        OBJECTS { vpwrTrapsMsgString }
                        STATUS          current
                        DESCRIPTION "Distribution Communication Alarm"
                        ::= {vpwrDcPowerTraps 46}

    vpwrTrapConverterAlarm    NOTIFICATION-TYPE
                        OBJECTS { vpwrTrapsMsgString }
                        STATUS          current
                        DESCRIPTION "!!! NOT VALID FOR BC2000 CONTROLLER !!!
                            Single Converter Fail Alarm"
                        ::= {vpwrDcPowerTraps 47}

    vpwrTrapMultipleConvFailAlarm    NOTIFICATION-TYPE
                        OBJECTS { vpwrTrapsMsgString }
                        STATUS          current
                        DESCRIPTION "!!! NOT VALID FOR BC2000 CONTROLLER !!!
                            Multiple Converter Fail Alarm"
                        ::= {vpwrDcPowerTraps 48}

    vpwrTrapDGUAlarm    NOTIFICATION-TYPE
                        OBJECTS { vpwrTrapsMsgString }
                        STATUS          current
                        DESCRIPTION "!!! For Future Use. !!!
				     DGU Alarm"
                        ::= {vpwrDcPowerTraps 49}

    vpwrTrapConfigErrorAlarm    NOTIFICATION-TYPE
                        OBJECTS { vpwrTrapsMsgString }
                        STATUS          current
                        DESCRIPTION "Configuration Error"
                        ::= {vpwrDcPowerTraps 50}

    vpwrTrapDisplayFirmwareMismatchAlarm    NOTIFICATION-TYPE
                        OBJECTS { vpwrTrapsMsgString }
                        STATUS          current
                        DESCRIPTION "!!! NOT VALID FOR BC2000 CONTROLLER !!!
				     Display Firmware Mismatch"
                        ::= {vpwrDcPowerTraps 51}

    vpwrTrapConverterInputFailAlarm    NOTIFICATION-TYPE
                        OBJECTS { vpwrTrapsMsgString }
                        STATUS          current
                        DESCRIPTION "!!! NOT VALID FOR BC2000 CONTROLLER !!!
                            Converter Input Fail Alarm"
                        ::= {vpwrDcPowerTraps 52}

    vpwrTrapBatteryRechgIlimitFailAlarm    NOTIFICATION-TYPE
                        OBJECTS { vpwrTrapsMsgString }
                        STATUS          current
                        DESCRIPTION "!!! NOT VALID FOR BC2000 CONTROLLER !!!
				     Battery Recharge Current Limit Fail"
                        ::= {vpwrDcPowerTraps 53}

    vpwrTrapSystemAlive    NOTIFICATION-TYPE
                        OBJECTS { vpwrTrapsMsgString }
                           STATUS          current
                        DESCRIPTION "Periodic Keepalive trap"
                        ::= {vpwrDcPowerTraps 54}

    vpwrTrapSystemAuxAlmSource    NOTIFICATION-TYPE
                        OBJECTS { vpwrTrapsMsgString, 
                          vpwrAlarmingModuleOID, 
                      vpwrAlarmingModuleIndex, 
                      vpwrAlarmingSubModuleBitMap }
                      STATUS          current
                  DESCRIPTION
                     "Source of Auxilary Alarms.
                     Indicates the module and the aux within
                     the module causing alarms"
                      ::= {vpwrDcPowerTraps 55}

    vpwrTrapSystemDistAlmSource   NOTIFICATION-TYPE
                   OBJECTS{     vpwrTrapsMsgString,
                        vpwrAlarmingModuleOID,
                        vpwrAlarmingModuleIndex,
                        vpwrAlarmingSubModuleBitMap }
                      STATUS          current
                  DESCRIPTION
                     "Source of Distribution Alarms.
                     Indicates the module and the dist within
                     the module causing alarms"
                      ::= {vpwrDcPowerTraps 56}

    vpwrTrapSystemBatCapacityAlarm   NOTIFICATION-TYPE
                   OBJECTS {     vpwrTrapsMsgString,
                        vpwrSystemCurrent,
                        vpwrBatteryCurrentCapacity }
                      STATUS          current
                  DESCRIPTION
                     "Plant Load exceeds Plant Battery Current Capacity.
                     Useful for batteries that limit maximum discharge current 
                     It will not be sent out for VRLA batteries, eg"

                     ::= {vpwrDcPowerTraps 58}

    vpwrTrapSystemACFClearAlarm   NOTIFICATION-TYPE
                 OBJECTS {     vpwrTrapsMsgString,
                        vpwrTrapAcfDuration}
                    STATUS          current
                DESCRIPTION
                     "AC Fail (ACF) Conditioned Cleared Alarm.
                      Duration is in minutes.
                     "
                     ::=  {vpwrDcPowerTraps 61}

    vpwrTrapSystemACFSetAlarm   NOTIFICATION-TYPE
                  OBJECTS {     vpwrTrapsMsgString,
                                vpwrTrapAcfDuration}
                    STATUS      current
                    DESCRIPTION
                     "ACF Conditioned detected Alarm.
                      The duration would always be zero.
                      Msg String: ACF Alarm    Set
                      "
                     ::= {vpwrDcPowerTraps 62}

 vpwrTrapSystemBatCapacityLeft   NOTIFICATION-TYPE
                    OBJECTS {   vpwrTrapsMsgString,
                                vpwrBatteryRemainingTime }
                    STATUS      current
                    DESCRIPTION
                     "!!!   For Future Use.   !!!
                     Battery Useful Capacity Remaining"
                     ::= {vpwrDcPowerTraps 64}

 vpwrTrapRectifierUVAlarm    NOTIFICATION-TYPE
            OBJECTS {    vpwrTrapsMsgString, vpwrShelfIndex, vpwrModuleIndex }
            STATUS       current
            DESCRIPTION  "Rectifier Under Voltage Alarm"
            ::= {vpwrDcPowerTraps 65}

 vpwrTrapMultRectifierUVAlarm    NOTIFICATION-TYPE
            OBJECTS {   vpwrTrapsMsgString }
            STATUS      current
            DESCRIPTION "!!!   For Future Use.   !!!
                        Multiple Rectifier Under Voltage Alarm"
            ::= {vpwrDcPowerTraps 66}

 vpwrTrapRingerAlarm    NOTIFICATION-TYPE
            OBJECTS {   vpwrTrapsMsgString }
            STATUS      current
            DESCRIPTION "Ringer Alarm"
            ::= {vpwrDcPowerTraps 67}

 vpwrTrapMultRingerAlarm    NOTIFICATION-TYPE
            OBJECTS {   vpwrTrapsMsgString}
            STATUS      current
            DESCRIPTION "!!!   For Future Use.   !!!
                        Multiple Ringer Alarm"
            ::= {vpwrDcPowerTraps 68}

 vpwrTrapI2CCANAlarm    NOTIFICATION-TYPE
            OBJECTS {   vpwrTrapsMsgString}
            STATUS      current
            DESCRIPTION "!!!   For Future Use.   !!!
                        Unmapped I2C/CAN Address Alarm
                        One of your I2C or CAN devices
                        has a duplicate or invalid address
                        and can not be mapped.  Please
                        recheck all device addresses."
            ::= {vpwrDcPowerTraps 69}

vpwrTrapRectifierIlimitAlarm    NOTIFICATION-TYPE
            OBJECTS {   vpwrTrapsMsgString, vpwrShelfIndex, vpwrModuleIndex }
            STATUS      current
            DESCRIPTION "Rectifier Current Limit Alarm"
            ::= {vpwrDcPowerTraps 70}

 vpwrTrapMultRectifierIlimitAlarm    NOTIFICATION-TYPE
            OBJECTS {   vpwrTrapsMsgString }
            STATUS      current
            DESCRIPTION "!!!   For Future Use.   !!!
                        Multiple Rectifier Current Limit Alarm"
            ::= {vpwrDcPowerTraps 71}

 vpwrTrapRingerCommAlarm    NOTIFICATION-TYPE
           OBJECTS { vpwrTrapsMsgString }
                       STATUS          current
           DESCRIPTION "Ringer Communication Alarm"
                        ::= {vpwrDcPowerTraps 72}

 vpwrTrapUnassignedAlarm    NOTIFICATION-TYPE
                        OBJECTS { vpwrTrapsMsgString}
                        STATUS          current
                        DESCRIPTION "!!! NOT VALID FOR BC2000 CONTROLLER !!!
                            Unassigned Alarm(Trap) - Check Web Page"
                        ::= {vpwrDcPowerTraps 99}

END
