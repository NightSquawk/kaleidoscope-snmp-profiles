-- ============================================================================
-- Copyright (c) 2004-2016 Hangzhou H3C Tech. Co., Ltd. All rights reserved.
--
-- Description: This MIB is used for configuration of SECP (security policies).
-- Reference:
-- Version: V1.0
-- History:
-- V1.0 created by xuedeng.
-- ============================================================================
H3C-SECP-MIB DEFINITIONS ::= BEGIN

IMPORTS
    h3cCommon
        FROM  HUAWEI-3COM-OID-MIB
    OBJECT-TYPE, MODULE-IDENTITY,
    Unsigned32, Counter64
        FROM SNMPv2-SMI;

--
-- Node definitions
--

h3cSecp MODULE-IDENTITY
    LAST-UPDATED "201612191605Z"        -- Dec 19, 2016 at 16:05 GMT
    ORGANIZATION
        "Hangzhou H3C Technologies Co., Ltd."
    CONTACT-INFO
        "Platform Team Hangzhou H3C Technologies Co., Ltd.
        Hai-Dian District Beijing P.R. China
        http://www.h3c.com
        Zip:100085
        "
    DESCRIPTION
        "Security policies management information base for managing devices
        that support security policies.
        "
    REVISION "201612191605Z"            -- Dec 19, 2016 at 16:05 GMT
    DESCRIPTION
        "The initial revision of this MIB module."
    ::= { h3cCommon 166 }

--
-- Nodes of h3cSecpObjects
--
h3cSecpObjects OBJECT IDENTIFIER ::= { h3cSecp 1 }

--
-- Nodes of h3cSecpRunningInfoTable
--
h3cSecpRunningInfoTable OBJECT-TYPE
    SYNTAX SEQUENCE OF H3cSecpRunningInfoEntry
    MAX-ACCESS not-accessible
    STATUS current
    DESCRIPTION
        "Security policies running information base."
    ::= { h3cSecpObjects 1 }

h3cSecpRunningInfoEntry OBJECT-TYPE
    SYNTAX H3cSecpRunningInfoEntry
    MAX-ACCESS not-accessible
    STATUS current
    DESCRIPTION
        "Security policies running information entry."
    INDEX
    {
        h3cSecpIPVersion,
        h3cSecpRuleID
    }
    ::= { h3cSecpRunningInfoTable 1 }

H3cSecpRunningInfoEntry ::=
    SEQUENCE
    {
        h3cSecpIPVersion
            INTEGER,
        h3cSecpRuleID
            Unsigned32,
        h3cSecpMatchPacketCount
            Counter64,
        h3cSecpLastMatchTime
            Unsigned32
    }

h3cSecpIPVersion OBJECT-TYPE
    SYNTAX INTEGER
    {
        ipv4(1),
        ipv6(2)
    }
    MAX-ACCESS not-accessible
    STATUS current
    DESCRIPTION
        "IP protocol version."
    ::= { h3cSecpRunningInfoEntry 1 }

h3cSecpRuleID OBJECT-TYPE
    SYNTAX Unsigned32 (0..65534)
    MAX-ACCESS not-accessible
    STATUS current
    DESCRIPTION
        "Rule ID of security policies."
    ::= { h3cSecpRunningInfoEntry 2 }

h3cSecpMatchPacketCount OBJECT-TYPE
    SYNTAX Counter64
    MAX-ACCESS read-only
    STATUS current
    DESCRIPTION
        "Number of packets matching the rule."
    ::= { h3cSecpRunningInfoEntry 3 }

h3cSecpLastMatchTime OBJECT-TYPE
    SYNTAX Unsigned32
    MAX-ACCESS read-only
    STATUS current
    DESCRIPTION
        "Interval in seconds between the last match and 1970/1/1 00:00:00."
    ::= { h3cSecpRunningInfoEntry 4 }

END
