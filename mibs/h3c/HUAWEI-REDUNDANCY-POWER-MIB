-- ==================================================================
-- Copyright (C) 2002 by  H3C TECHNOLOGIES. All rights reserved.
--
-- Description: This file describes the hw MIB implementation of
--              redundancy power and fan
-- Reference: 
-- Version: V2.0
-- History: 
-- V2.0 2004-10-12 updated by gaolong
--      Add MODULE-IDENTITY clause.
--      Re-write with SMIv2 syntax.
--      Re-write IMPORTS clause.
-- ==================================================================

HUAWEI-REDUNDANCY-POWER-MIB DEFINITIONS ::= BEGIN
-- From file: "redundancy_power.mib"

IMPORTS  
    NOTIFICATION-TYPE, OBJECT-TYPE, MODULE-IDENTITY
        FROM SNMPv2-SMI  
    mlsr
        FROM HUAWEI-3COM-OID-MIB;

    redundancyPower MODULE-IDENTITY
        LAST-UPDATED "200112200000Z"	
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION 
                " "
        ::= { mlsr 4 }

redundancyFan    OBJECT IDENTIFIER ::= { mlsr 5 }

redundancyPowerTable OBJECT-TYPE
    SYNTAX SEQUENCE OF RedundancyPowerEntry
    MAX-ACCESS not-accessible
    STATUS current
    DESCRIPTION
        "The table describles the attributes of every power unit.
        "
    ::= { redundancyPower 1 }

redundancyPowerEntry OBJECT-TYPE
    SYNTAX RedundancyPowerEntry
    MAX-ACCESS not-accessible
    STATUS current
    DESCRIPTION
        "Each entry contains the attributes 
        associated with a single power unit entity."
    INDEX { redundancyPowerID }
    ::= { redundancyPowerTable 1 }

RedundancyPowerEntry ::= SEQUENCE {
    redundancyPowerID 	        INTEGER,
    redundancyPowerStatus 	INTEGER,
    redundancyPowerPreviousStatus 	INTEGER
     }

redundancyPowerID OBJECT-TYPE
    SYNTAX INTEGER 
    MAX-ACCESS read-only
    STATUS current
    DESCRIPTION
        "The identify of power uinit.
        This is also the index of this table."
    ::= { redundancyPowerEntry 1 }

redundancyPowerStatus OBJECT-TYPE
    SYNTAX INTEGER{
                   space(1),
                   normal(2),
                   fail(3)
                  } 
    MAX-ACCESS read-only
    STATUS current
    DESCRIPTION
        "The status of every redundancy power unit.
        if power unit doesn't exists, take the value 'space';
        if power unit is present and normal, take the value 'narmal'
        if power unit is present but fail, take the value 'fail'"
    ::= { redundancyPowerEntry 2 }

redundancyPowerPreviousStatus OBJECT-TYPE
    SYNTAX INTEGER{
                   space(1),
                   normal(2),
                   fail(3)
                  } 
    MAX-ACCESS read-only
    STATUS current
    DESCRIPTION
        "The last status of every redundancy power unit "
    ::= { redundancyPowerEntry 3 }



redundancyFanTable OBJECT-TYPE
    SYNTAX SEQUENCE OF RedundancyFanEntry
    MAX-ACCESS not-accessible
    STATUS current
    DESCRIPTION
        "The table describles the attributes of every power unit.
        "
    ::= { redundancyFan 1 }

redundancyFanEntry OBJECT-TYPE
    SYNTAX RedundancyFanEntry
    MAX-ACCESS not-accessible
    STATUS current
    DESCRIPTION
        "Each entry contains the attributes 
        associated with a single power unit entity."
    INDEX { redundancyFanID }
    ::= { redundancyFanTable 1 }

RedundancyFanEntry ::= SEQUENCE {
    redundancyFanID 	        INTEGER,
    redundancyFanStatus 	INTEGER
     }

redundancyFanID OBJECT-TYPE
    SYNTAX INTEGER 
    MAX-ACCESS read-only
    STATUS current
    DESCRIPTION
        "The identify of power uinit.
        This is also the index of this table."
    ::= { redundancyFanEntry 1 }

redundancyFanStatus OBJECT-TYPE
    SYNTAX INTEGER{
                   normal(1),
                   fail(2)                   
                  } 
    MAX-ACCESS read-only
    STATUS current
    DESCRIPTION
        "The status of every redundancy power unit.
        if power unit doesn't exists, take the value 'space';
        if power unit is present and normal, take the value 'narmal'
        if power unit is present but fail, take the value 'fail'"
    ::= { redundancyFanEntry 2 }


powerTraps OBJECT IDENTIFIER ::= { redundancyPower 2 }

powerStatusChangedTrap NOTIFICATION-TYPE
     OBJECTS { redundancyPowerID,redundancyPowerStatus,redundancyPowerPreviousStatus}
     STATUS  current
     DESCRIPTION
	"This trap is generated when the satus of a power unit is changed."
    ::= { powerTraps 1 }


fanTraps OBJECT IDENTIFIER ::= { redundancyFan 2 }

fanStatusChangedTrap NOTIFICATION-TYPE
     OBJECTS { redundancyFanID,redundancyFanStatus}
     STATUS  current
     DESCRIPTION
	"This trap is generated when the satus of a power unit is changed."
    ::= { fanTraps 1 }


END
