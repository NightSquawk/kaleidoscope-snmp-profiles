-- =================================================================
-- Copyright (c) 2004-2014 Hangzhou H3C Tech. Co., Ltd. All rights reserved.
--
-- Description: Smart Link MIB
-- Reference:
-- Version: V1.0
-- History:
--   2014-07-23 created by Lei Gongwu
--     Initial version V1.0
-- =================================================================
-- =================================================================
--
-- Import and definition
--
-- =================================================================
H3C-SMLK-MIB DEFINITIONS ::= BEGIN

IMPORTS
    h3cCommon
        FROM HUAWEI-3COM-OID-MIB
    RowStatus, DateAndTime, MacAddress
        FROM SNMPv2-TC
    Integer32, Counter64, OBJECT-TYPE, MODULE-IDENTITY, NOTIFICATION-TYPE
        FROM SNMPv2-SMI
    InterfaceIndex
        FROM IF-MIB;

h3cSmlk MODULE-IDENTITY
    LAST-UPDATED
        "201407231503Z"
    ORGANIZATION
        "Hangzhou H3C Tech. Co., Ltd."
    CONTACT-INFO
        "Platform Team Hangzhou H3C Tech. Co., Ltd.
        Hai-Dian District Beijing P.R. China
        http://www.h3c.com
        Zip:100085"
    DESCRIPTION
        "This MIB defines objects for managing Smart Link.
        Smart Link is a feature developed to address the slow convergence
        issue with STP.
        It provides link redundancy and fast convergence in
        a dual uplink network, allowing the backup link to take over quickly
        when the primary link fails."
    REVISION
        "201407231503Z"
    DESCRIPTION
        "Initial revision of the Smart Link MIB module."
    ::= { h3cCommon  147 }

h3cSmlkObject OBJECT IDENTIFIER ::= { h3cSmlk 1 }

h3cSmlkGroupTable OBJECT-TYPE
    SYNTAX      SEQUENCE OF H3cSmlkGroupEntry
    MAX-ACCESS  not-accessible
    STATUS      current
    DESCRIPTION
        "A list of entries of a smart link group."
    ::= { h3cSmlkObject 1 }

h3cSmlkGroupEntry OBJECT-TYPE
    SYNTAX      H3cSmlkGroupEntry
    MAX-ACCESS  not-accessible
    STATUS      current
    DESCRIPTION
        "A list of parameters that describe a smart link group."
    INDEX
    {
        h3cSmlkGroupID
    }
  ::= { h3cSmlkGroupTable 1 }

H3cSmlkGroupEntry ::=
    SEQUENCE
    {
        h3cSmlkGroupID           Integer32,
        h3cSmlkDeviceID          MacAddress,
        h3cSmlkPreemptionMode    INTEGER,
        h3cSmlkSpeedThreshold    Integer32,
        h3cSmlkPreemptionDelay   Integer32,
        h3cSmlkControlVlanID     Integer32,
        h3cSmlkInstanceListLow   OCTET STRING,
        h3cSmlkInstanceListHigh  OCTET STRING,
        h3cSmlkGroupRowStatus    RowStatus
    }

h3cSmlkGroupID OBJECT-TYPE
    SYNTAX Integer32 (1..256)
    MAX-ACCESS  accessible-for-notify
    STATUS      current
    DESCRIPTION
        "An index that uniquely identifies an entry in the smart link
        group table."
    ::={ h3cSmlkGroupEntry 1 }

h3cSmlkDeviceID OBJECT-TYPE
    SYNTAX      MacAddress
    MAX-ACCESS  read-only
    STATUS      current
    DESCRIPTION
        "Device ID of a smart link group.
        The device ID is the bridge MAC of the device."
    ::={ h3cSmlkGroupEntry 2 }

h3cSmlkPreemptionMode OBJECT-TYPE
    SYNTAX      INTEGER
                {
                    none(1),
                    role(2),
                    speed(3)
                }
    MAX-ACCESS  read-create
    STATUS      current
    DESCRIPTION
        "Preemption mode of a smart link group."
    DEFVAL      { 1 }
    ::={ h3cSmlkGroupEntry 3 }

h3cSmlkSpeedThreshold OBJECT-TYPE
    SYNTAX      Integer32 (0..10000)
    MAX-ACCESS  read-create
    STATUS      current
    DESCRIPTION
        "Speed threshold for a smart link group in speed mode.
        This object is valid only when the value of h3cSmlkPreemptionMode
        is 'speed'."
    DEFVAL      { 0 }
    ::={ h3cSmlkGroupEntry 4 }

h3cSmlkPreemptionDelay OBJECT-TYPE
    SYNTAX      Integer32 (0..300)
    MAX-ACCESS  read-create
    STATUS      current
    DESCRIPTION
        "Preemption delay for a smart link group, in the range of 0 to 300
        seconds."
    DEFVAL      { 1 }
    ::={ h3cSmlkGroupEntry 5 }

h3cSmlkControlVlanID OBJECT-TYPE
    SYNTAX      Integer32 (1..4094|65535)
    MAX-ACCESS  read-create
    STATUS      current
    DESCRIPTION
        "Index of the control VLAN specified for a smart link group.
        The value 65535 indicates that the control VLAN has not been
        configured."
    DEFVAL      { 1 }
    ::={ h3cSmlkGroupEntry 6 }

h3cSmlkInstanceListLow OBJECT-TYPE
    SYNTAX      OCTET STRING(SIZE(256))
    MAX-ACCESS  read-create
    STATUS      current
    DESCRIPTION
        "Each octet contained in this value specifies an eight-instance
        group, with the first octet specifying instances 0 through 7,
        the second octet specifying instances 8 through 15, and so on.
        Within each octet, the most significant bit represents the
        highest numbered instance, and the least significant bit represents
        the lowest numbered instance.  Each instance to which the
        protected VLANs of a smart link group are mapped corresponds to a
        bit within the value of this object.  A bit with a value of '1'
        indicates that the VLANs mapped to the instance are protected
        VLANs of the smart link group.  The VLANs mapped to
        the instance are not protected VLANs if the corresponding bit has a
        value of '0'.  The value of this object must be set with
        h3cSmlkInstanceListHigh at the same time when a SET
        operation is performed."
    DEFVAL      { "" }
    ::= { h3cSmlkGroupEntry 7 }

h3cSmlkInstanceListHigh OBJECT-TYPE
    SYNTAX      OCTET STRING(SIZE(256))
    MAX-ACCESS  read-create
    STATUS      current
    DESCRIPTION
        "Each octet contained in this value specifies an eight-instance
        group, with the first octet specifying instances 2048 through
        2055, the second octet specifying instances 2056 through 2063,
        and so on.  Within each octet, the most significant bit represents
        the highest numbered instance, and the least significant bit
        represents the lowest numbered instance.  The most significant bit
        of the last octet is invalid.  Each instance to which the
        protected VLANs of a smart link group are mapped corresponds to a
        bit within the value of this object.  A bit with a value of '1'
        indicates that the VLANs mapped to the instance are protected VLANs
        of the smart link group.  The VLANs mapped to the
        instance are not protected VLANs if the corresponding bit has a
        value of '0'.  The value of this object must be set with
        h3cSmlkInstanceListLow at the same time when a SET operation
        is performed."
    DEFVAL      { "" }
    ::= { h3cSmlkGroupEntry 8 }

h3cSmlkGroupRowStatus OBJECT-TYPE
    SYNTAX      RowStatus
    MAX-ACCESS  read-create
    STATUS      current
    DESCRIPTION
        "This object is responsible for managing creation,
        deletion, and modification of rows.  The rows support active
        status, CreatAndGo, and destroy operations."
    ::={ h3cSmlkGroupEntry 9 }

h3cSmlkPortTable OBJECT-TYPE
    SYNTAX      SEQUENCE OF H3cSmlkPortEntry
    MAX-ACCESS  not-accessible
    STATUS      current
    DESCRIPTION
        "A list of port entries of a smart link group."
    ::= { h3cSmlkObject 2 }

h3cSmlkPortEntry OBJECT-TYPE
    SYNTAX      H3cSmlkPortEntry
    MAX-ACCESS  not-accessible
    STATUS      current
    DESCRIPTION
        "A list of parameters that describe a port to be added to a smart
        link group."
    INDEX
    {
        h3cSmlkGroupID,
        h3cSmlkPortIfIndex
    }
    ::= { h3cSmlkPortTable 1 }

H3cSmlkPortEntry ::=
    SEQUENCE
    {
        h3cSmlkPortIfIndex      InterfaceIndex,
        h3cSmlkPortRole         INTEGER,
        h3cSmlkPortStatus       INTEGER,
        h3cSmlkFlushCount       Counter64,
        h3cSmlkLastFlushTime    DateAndTime,
        h3cSmlkPortRowStatus    RowStatus
    }

h3cSmlkPortIfIndex OBJECT-TYPE
    SYNTAX      InterfaceIndex
    MAX-ACCESS  accessible-for-notify
    STATUS      current
    DESCRIPTION
        "IfIndex of a port in a smart link group."
    ::={ h3cSmlkPortEntry 1 }

h3cSmlkPortRole OBJECT-TYPE
    SYNTAX      INTEGER
                {
                    primary(1),
                    secondary(2)
                }
    MAX-ACCESS  read-create
    STATUS      current
    DESCRIPTION
        "Role of a port in a smart link group."
    ::={ h3cSmlkPortEntry 2 }

h3cSmlkPortStatus OBJECT-TYPE
    SYNTAX      INTEGER
                {
                    down(1),
                    active(2),
                    standby(3)
                }
    MAX-ACCESS  read-only
    STATUS      current
    DESCRIPTION
        "Status of a port in a smart link group."
    ::={ h3cSmlkPortEntry 3 }

h3cSmlkFlushCount OBJECT-TYPE
    SYNTAX      Counter64
    MAX-ACCESS  read-only
    STATUS      current
    DESCRIPTION
        "Number of transmitted flush messages."
    ::={ h3cSmlkPortEntry 4 }

h3cSmlkLastFlushTime OBJECT-TYPE
    SYNTAX      DateAndTime
    MAX-ACCESS  read-only
    STATUS      current
    DESCRIPTION
        "Time when the last flush message was transmitted."
    ::= { h3cSmlkPortEntry 5 }

h3cSmlkPortRowStatus OBJECT-TYPE
    SYNTAX      RowStatus
    MAX-ACCESS  read-create
    STATUS      current
    DESCRIPTION
        "This object is responsible for managing creation,
        deletion, and modification of rows.  The rows support active
        status, CreatAndGo, and destroy operations."
    ::={ h3cSmlkPortEntry 6 }

h3cSmlkFlushEnableTable OBJECT-TYPE
    SYNTAX      SEQUENCE OF H3cSmlkFlushEnableEntry
    MAX-ACCESS  not-accessible
    STATUS      current
    DESCRIPTION
        "A list of ports on which flush message receiving is enabled."
    ::= { h3cSmlkObject 3 }

h3cSmlkFlushEnableEntry OBJECT-TYPE
    SYNTAX      H3cSmlkFlushEnableEntry
    MAX-ACCESS  not-accessible
    STATUS      current
    DESCRIPTION
        "A list of parameters that describe a port on which flush message
        receiving is enabled."
    INDEX
    {
          h3cSmlkIfIndex
    }
    ::= { h3cSmlkFlushEnableTable 1 }

H3cSmlkFlushEnableEntry ::=
    SEQUENCE
    {
        h3cSmlkIfIndex               InterfaceIndex,
        h3cSmlkControlVlanListLow    OCTET STRING,
        h3cSmlkControlVlanListHigh   OCTET STRING
    }

h3cSmlkIfIndex OBJECT-TYPE
    SYNTAX      InterfaceIndex
    MAX-ACCESS  not-accessible
    STATUS      current
    DESCRIPTION
        "IfIndex of a port on which flush message receiving is enabled."
    ::={ h3cSmlkFlushEnableEntry 1 }

h3cSmlkControlVlanListLow OBJECT-TYPE
    SYNTAX      OCTET STRING(SIZE(256))
    MAX-ACCESS  read-write
    STATUS      current
    DESCRIPTION
        "Specifies the control VLANs used for receiving flush messages.
        The VLAN ID range, described by bitmap, is from 1 to
        2048.  The length of bitmap is 256 in bytes.  Each octet
        within this value specifies a set of eight VLANs, with
        the first octet specifying VLANs 1 through 8, the second
        octet specifying VLANs 9 through 16, and so on.  Within each
        octet, the most significant bit represents the highest
        numbered VLAN, and the least significant bit represents
        the lowest numbered VLAN."
    ::= { h3cSmlkFlushEnableEntry 2 }

h3cSmlkControlVlanListHigh OBJECT-TYPE
    SYNTAX      OCTET STRING(SIZE(256))
    MAX-ACCESS  read-write
    STATUS      current
    DESCRIPTION
        "Specifies the control VLANs used for receiving flush messages.
        The VLAN ID range, described by bitmap, is from 2049 to
        4094.  The length of bitmap is 256 in bytes.  Each octet
        within this value specifies a set of eight VLANs, with
        the first octet specifying VLANs 2049 through 2056, the
        second octet specifying VLANs 2057 through 2064, and so on.
        Within each octet, the most significant bit represents
        the highest numbered VLAN, and the least significant bit
        represents the lowest numbered VLAN."
    ::= { h3cSmlkFlushEnableEntry 3 }

h3cSmlkTrap            OBJECT IDENTIFIER ::= { h3cSmlk 2 }
h3cSmlkTrapPrefix      OBJECT IDENTIFIER ::= { h3cSmlkTrap 0 }
h3cSmlkGroupLinkActive NOTIFICATION-TYPE
    OBJECTS
        {
            h3cSmlkGroupID,
            h3cSmlkPortIfIndex
        }
    STATUS      current
    DESCRIPTION
        "A trap message is generated when the status of a port
        in a smart link group changes to active."
    ::= { h3cSmlkTrapPrefix 1 }

END
