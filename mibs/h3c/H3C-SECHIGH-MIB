-- ==========================================================================
-- Copyright (c) 2004-2017 Hangzhou H3C Tech. Co., Ltd.  All rights reserved.
--
-- Description: The MIB is designed to show information on high-end driver products.
-- Reference:
-- Version: V1.0
-- History:
-- V1.0  2017-09 Initial version created by meirongjun 14958.
-- ==========================================================================
H3C-SECHIGH-MIB DEFINITIONS ::= BEGIN

IMPORTS
    h3cCommon
        FROM HUAWEI-3COM-OID-MIB
    MODULE-IDENTITY, OBJECT-TYPE, Integer32, NOTIFICATION-TYPE
        FROM SNMPv2-SMI;         -- [RFC2578]

h3cSecHigh MODULE-IDENTITY
    LAST-UPDATED "201709162020Z"
    ORGANIZATION
        "Hangzhou H3C Technologies Co., Ltd."
    CONTACT-INFO
        "Platform Team Hangzhou H3C Tech. Co., Ltd.
        Hai-Dian District Beijing P.R. China
        http://www.h3c.com
        Zip:100085
        "
    DESCRIPTION
        "The private MIB file includes the information on high-end driver products."
    REVISION      "201709162020Z"
    DESCRIPTION
        "Initial revision of this MIB module."
    ::= { h3cCommon 171 }
--
-- Node definitions
--
h3cSecHighMonitor OBJECT IDENTIFIER ::= { h3cSecHigh 1 }


--
-- h3cSecHighHgMonitorAlarm context table definitions
--
h3cSecHighHgMonitorAlarmVar OBJECT IDENTIFIER   ::= { h3cSecHighMonitor 1 }

h3cSecHighHgMonitorAlarmType OBJECT-TYPE
    SYNTAX      Integer32
    MAX-ACCESS  accessible-for-notify
    STATUS      current
    DESCRIPTION
            "Type of the alarm,0 represent recovery normal,1 represent link status error,
            2 represent Some packets were dropped on the link."
    ::= { h3cSecHighHgMonitorAlarmVar 1 }

h3cSecHighHgMonitorAlarmSrcChassis OBJECT-TYPE
    SYNTAX      Integer32
    MAX-ACCESS  accessible-for-notify
    STATUS      current
    DESCRIPTION
            "Number of the chassis where the source end of the alarmed link resides."
    ::= { h3cSecHighHgMonitorAlarmVar 2 }

h3cSecHighHgMonitorAlarmSrcSlot OBJECT-TYPE
    SYNTAX      Integer32
    MAX-ACCESS  accessible-for-notify
    STATUS      current
    DESCRIPTION
            "Number of the slot where the source end of the alarmed link resides."
    ::= { h3cSecHighHgMonitorAlarmVar 3 }

h3cSecHighHgMonitorAlarmSrcChip OBJECT-TYPE
    SYNTAX      Integer32
    MAX-ACCESS  accessible-for-notify
    STATUS      current
    DESCRIPTION
            "Number of the chip where the source end of the alarmed link resides."
    ::= { h3cSecHighHgMonitorAlarmVar 4 }

h3cSecHighHgMonitorAlarmSrcPort OBJECT-TYPE
    SYNTAX      Integer32
    MAX-ACCESS  accessible-for-notify
    STATUS      current
    DESCRIPTION
            "Number of the port where the source end of the alarmed link resides."
    ::= { h3cSecHighHgMonitorAlarmVar 5 }

h3cSecHighHgMonitorAlarmDstChassis OBJECT-TYPE
    SYNTAX      Integer32
    MAX-ACCESS  accessible-for-notify
    STATUS      current
    DESCRIPTION
            "Number of the chassis where the destination end of the alarmed link resides."
    ::= { h3cSecHighHgMonitorAlarmVar 6 }

h3cSecHighHgMonitorAlarmDstSlot OBJECT-TYPE
    SYNTAX      Integer32
    MAX-ACCESS  accessible-for-notify
    STATUS      current
    DESCRIPTION
            "Number of the slot where the destination end of the alarmed link resides."
    ::= { h3cSecHighHgMonitorAlarmVar 7 }

h3cSecHighHgMonitorAlarmDstChip OBJECT-TYPE
    SYNTAX      Integer32
    MAX-ACCESS  accessible-for-notify
    STATUS      current
    DESCRIPTION
            "Number of the chip where the destination end of the alarmed link resides."
    ::= { h3cSecHighHgMonitorAlarmVar 8 }

h3cSecHighHgMonitorAlarmDstPort OBJECT-TYPE
    SYNTAX      Integer32
    MAX-ACCESS  accessible-for-notify
    STATUS      current
    DESCRIPTION
            "Number of the port where the destination end of the alarmed link resides."
    ::= { h3cSecHighHgMonitorAlarmVar 9 }

h3cSecHighHgMonitorAlarmReason OBJECT-TYPE
    SYNTAX      OCTET STRING(SIZE(0..512))
    MAX-ACCESS  accessible-for-notify
    STATUS      current
    DESCRIPTION
            "Cause of the alarm."
    ::= { h3cSecHighHgMonitorAlarmVar 10 }



-- ===============================================
-- Definition of traps.
-- ===============================================
h3cSecHighHgMonitorAlarmTrap OBJECT IDENTIFIER ::= { h3cSecHighMonitor 2 }
h3cSecHighHgMonitorAlarmNotifications OBJECT IDENTIFIER ::= { h3cSecHighHgMonitorAlarmTrap 0 }

h3cSecHighHgMonitorAlarmNotification NOTIFICATION-TYPE
    OBJECTS {
                h3cSecHighHgMonitorAlarmType,
                h3cSecHighHgMonitorAlarmSrcChassis,
                h3cSecHighHgMonitorAlarmSrcSlot,
                h3cSecHighHgMonitorAlarmSrcChip,
                h3cSecHighHgMonitorAlarmSrcPort,
                h3cSecHighHgMonitorAlarmDstChassis,
                h3cSecHighHgMonitorAlarmDstSlot,
                h3cSecHighHgMonitorAlarmDstChip,
                h3cSecHighHgMonitorAlarmDstPort,
                h3cSecHighHgMonitorAlarmReason
            }
    STATUS     current
    DESCRIPTION
           "This notification is generated when an HgMonitor alarm is generated."
    ::= { h3cSecHighHgMonitorAlarmNotifications 1 }
END
