-- ==========================================================================
-- Copyright (C) 2004 by H3C TECHNOLOGIES. All rights reserved.
--
-- Description: The purpose of this MIB file is to provide the definition of
--              voice call active record.
-- Reference:
-- Version: V1.0
-- History:
-- V1.0 2005-03-22 Initial version, created by Yang Youku
-- ==========================================================================
H3C-VOCALLACTIVE-MIB DEFINITIONS ::= BEGIN

IMPORTS
    OBJECT-TYPE, MODULE-IDENTITY, IpAddress, Integer32
        FROM SNMPv2-SMI
    CodecType
        FROM H3C-VO-TYPE-MIB
    InetAddressType, InetAddress 
        FROM INET-ADDRESS-MIB 
    h3cVoice
        FROM HUAWEI-3COM-OID-MIB;   
    
    
    h3cVoiceCallActive MODULE-IDENTITY 
        LAST-UPDATED "200503150000Z"
        ORGANIZATION                                   
            "Hangzhou H3C Tech. Co., Ltd."             
        CONTACT-INFO                                   
            "Platform Team Hangzhou H3C Tech. Co., Ltd.                              
            Hai-Dian District Beijing P.R. China       
            http://www.h3c.com                         
            Zip:100085                                 
            "                                          
        DESCRIPTION 
            "This MIB file is to provide the definition of voice call 
            active record."
        REVISION "200503150000Z"
        DESCRIPTION 
            "The initial version of this MIB file."
        ::= { h3cVoice 6 }

    
    h3cVoCallActiveObjects OBJECT IDENTIFIER ::= { h3cVoiceCallActive 1 }

--=======================================================================
--                    h3cVoCallActiveTable
--
--=======================================================================
    h3cVoCallActiveTable OBJECT-TYPE
        SYNTAX SEQUENCE OF H3CVoCallActiveEntry
        MAX-ACCESS not-accessible
        STATUS current
        DESCRIPTION
            "The table contains the voice active call information."
        ::= { h3cVoCallActiveObjects 1 }

    
    h3cVoCallActiveEntry OBJECT-TYPE
        SYNTAX H3CVoCallActiveEntry
        MAX-ACCESS not-accessible
        STATUS current
        DESCRIPTION
            "The entry of h3cVoCallActiveTable."
        INDEX { h3cVoCallActiveChannel }
        ::= { h3cVoCallActiveTable 1 }

    
    H3CVoCallActiveEntry ::=
        SEQUENCE { 
            h3cVoCallActiveChannel
                Integer32,
            h3cVoCallActiveCallerNumber
                OCTET STRING,
            h3cVoCallActiveCalledNumber
                OCTET STRING,
            h3cVoCallActiveEncodeType
                CodecType,
            h3cVoCallActiveLocalAddressType
                InetAddressType,
            h3cVoCallActiveLocalAddress
                InetAddress,
            h3cVoCallActivePeerAddressType
                InetAddressType,
            h3cVoCallActivePeerAddress
                InetAddress,
            h3cVoCallActiveCallOrigin
                INTEGER,
            h3cVoCallActiveIPSigType
                INTEGER,
            h3cVoCallActivePSTNSigType
                INTEGER,
            h3cVoCallActiveStatus
                INTEGER
         }

    h3cVoCallActiveChannel OBJECT-TYPE
        SYNTAX Integer32
        MAX-ACCESS not-accessible
        STATUS current
        DESCRIPTION
            "This object indicates the logic channel number of a call."
        ::= { h3cVoCallActiveEntry 1 }

    
    h3cVoCallActiveCallerNumber OBJECT-TYPE
        SYNTAX OCTET STRING
        MAX-ACCESS read-only
        STATUS current
        DESCRIPTION
            "This object indicates the caller number of a call."
        ::= { h3cVoCallActiveEntry 2 }

    
    h3cVoCallActiveCalledNumber OBJECT-TYPE
        SYNTAX OCTET STRING
        MAX-ACCESS read-only
        STATUS current
        DESCRIPTION
            "This object indicates the called number of a call."
        ::= { h3cVoCallActiveEntry 3 }

    
    h3cVoCallActiveEncodeType OBJECT-TYPE
        SYNTAX CodecType
        MAX-ACCESS read-only
        STATUS current
        DESCRIPTION
            "This object indicates the encode type of a call."
        ::= { h3cVoCallActiveEntry 4 }


    h3cVoCallActiveLocalAddressType OBJECT-TYPE
        SYNTAX  InetAddressType
        MAX-ACCESS read-only
        STATUS current
        DESCRIPTION
            "This object indicates the local IP address type of a call."
        ::= { h3cVoCallActiveEntry 5 }

    
    h3cVoCallActiveLocalAddress OBJECT-TYPE
        SYNTAX InetAddress
        MAX-ACCESS read-only
        STATUS current
        DESCRIPTION
            "This object indicates the local IP address of a call."
        ::= { h3cVoCallActiveEntry 6 }


    h3cVoCallActivePeerAddressType OBJECT-TYPE
        SYNTAX  InetAddressType
        MAX-ACCESS read-only
        STATUS current
        DESCRIPTION
            "This object indicates the peer IP address type of a call."
        ::= { h3cVoCallActiveEntry 7 }

    
    h3cVoCallActivePeerAddress OBJECT-TYPE
        SYNTAX InetAddress
        MAX-ACCESS read-only
        STATUS current
        DESCRIPTION
            "This object indicates the peer IP address of a call."
        ::= { h3cVoCallActiveEntry 8 }

    
    h3cVoCallActiveCallOrigin OBJECT-TYPE
        SYNTAX INTEGER
            {
            caller(1),
            called(2)
            }
        MAX-ACCESS read-only
        STATUS current
        DESCRIPTION
            "This object indicates the direction of a call."
        ::= { h3cVoCallActiveEntry 9 }

    
    h3cVoCallActiveIPSigType OBJECT-TYPE
        SYNTAX INTEGER 
            { 
            unknown(1),
            h323(2),
            sip(3)
            }
        MAX-ACCESS read-only
        STATUS current
        DESCRIPTION
            "This object indicates the ip signal type."
        ::= { h3cVoCallActiveEntry 10 }

    
    h3cVoCallActivePSTNSigType OBJECT-TYPE
        SYNTAX INTEGER
            {
            unknown(1),
            fxs(2),
            fxo(3),
            em(4),
            r2(5),
            dss1(6),
            dem(7)
            }
        MAX-ACCESS read-only
        STATUS current
        DESCRIPTION
            "This object indicates the PSTN(Public Switched Telephone Network) 
            signal type."
        ::= { h3cVoCallActiveEntry 11 }

    
    h3cVoCallActiveStatus OBJECT-TYPE
        SYNTAX INTEGER
            {
            idle(1),
            calling(2),
            alerting(3),
            talking(4),
            release(5)
            }
        MAX-ACCESS read-only
        STATUS current
        DESCRIPTION
            "This object indicates the current progress status of a call."
        ::= { h3cVoCallActiveEntry 12 }
    
END
