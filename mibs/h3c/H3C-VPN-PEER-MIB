-- ==========================================================================
-- Copyright (c) 2004-2016 Hangzhou H3C Tech. Co., Ltd.  All rights reserved.
--
-- Description: The MIB contains the managed objects definitions for the Virtual
--              Private Network (VPN) peer on devices supporting this feature.
-- Reference:
-- Version: V1.0
-- History:
--   V1.0 2016-03-09 Initial version created by qujin
-- ==========================================================================
H3C-VPN-PEER-MIB DEFINITIONS ::= BEGIN

IMPORTS
    h3cCommon
        FROM HUAWEI-3COM-OID-MIB
    OBJECT-TYPE, MODULE-IDENTITY, Counter64
        FROM SNMPv2-SMI;

h3cVpnPeer MODULE-IDENTITY
    LAST-UPDATED "201603091600Z"        -- 9th March, 2016 at 16:00 GMT
    ORGANIZATION
        "Hangzhou H3C Technologies Co., Ltd."
    CONTACT-INFO
        "Platform Team H3C Technologies Co., Ltd.
         Hai-Dian District Beijing P.R. China
         http://www.h3c.com
         Zip: 100085
         "
    DESCRIPTION
        "This MIB provides information about VPN peers.  This MIB is applicable to PE devices.
        Some objects in this MIB may be used only for some specific products,
        so users should refer to the related documents to acquire more
        detailed information.
        "
    REVISION "201603091600Z"
    DESCRIPTION
        "The initial revision of this MIB module."
    ::= { h3cCommon 165 }


-- =================================================================
-- Note that a scalar group should be defined firstly and all
-- scalar objects are placed under that group.
-- =================================================================
h3cVpnPeerGroup OBJECT IDENTIFIER ::= { h3cVpnPeer 1 }

-- =================================================================
-- The section below describes statistics of VPN peer on a device.
-- =================================================================
h3cVpnPeerStat OBJECT IDENTIFIER ::= { h3cVpnPeerGroup 1 }

-- =============================================================================
-- h3cVpnPeerStatTable Definition
-- =============================================================================
h3cVpnPeerStatTable OBJECT-TYPE
    SYNTAX      SEQUENCE OF H3cVpnPeerStatEntry
    MAX-ACCESS  not-accessible
    STATUS      current
    DESCRIPTION
        "This table contains objects to get statistic information
         of a VPN peer on a device."
    ::= { h3cVpnPeerStat 1 }

h3cVpnPeerStatEntry OBJECT-TYPE
    SYNTAX      H3cVpnPeerStatEntry
    MAX-ACCESS  not-accessible
    STATUS      current
    DESCRIPTION
        "Entry items"
    INDEX
        {
            h3cVpnPeerName
        }
    ::= { h3cVpnPeerStatTable 1 }

H3cVpnPeerStatEntry ::=
    SEQUENCE {
        h3cVpnPeerName
            OCTET STRING,
        h3cVpnPeerOutPassPkts
            Counter64,
        h3cVpnPeerOutPassBytes
            Counter64,
        h3cVpnPeerOutDropPkts
            Counter64,
        h3cVpnPeerOutDropBytes
            Counter64
             }

h3cVpnPeerName OBJECT-TYPE
    SYNTAX      OCTET STRING(SIZE(1..31))
    MAX-ACCESS  not-accessible
    STATUS      current
    DESCRIPTION
        "A unique human-readable value for each VPN peer."
    ::= { h3cVpnPeerStatEntry 1 }

h3cVpnPeerOutPassPkts OBJECT-TYPE
    SYNTAX      Counter64
    MAX-ACCESS  read-only
    STATUS      current
    DESCRIPTION
        "The total number of packets transmitted out of the VPN peer."
    ::= { h3cVpnPeerStatEntry 2 }

h3cVpnPeerOutPassBytes OBJECT-TYPE
    SYNTAX      Counter64
    MAX-ACCESS  read-only
    STATUS      current
    DESCRIPTION
        "The total number of bytes transmitted out of the VPN peer."
    ::= { h3cVpnPeerStatEntry 3 }

h3cVpnPeerOutDropPkts OBJECT-TYPE
    SYNTAX      Counter64
    MAX-ACCESS  read-only
    STATUS      current
    DESCRIPTION
        "The total number of dropped packets transmitted out of the VPN peer."
    ::= { h3cVpnPeerStatEntry 4 }

h3cVpnPeerOutDropBytes OBJECT-TYPE
    SYNTAX      Counter64
    MAX-ACCESS  read-only
    STATUS      current
    DESCRIPTION
        "The total number of dropped bytes transmitted out of the VPN peer."
    ::= { h3cVpnPeerStatEntry 5 }


END
