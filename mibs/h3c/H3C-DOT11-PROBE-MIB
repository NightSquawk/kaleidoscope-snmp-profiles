-- =============================================================================
-- Copyright (c) 2004-2016 Hangzhou H3C Tech. Co., Ltd.  All rights reserved.
--
-- Description:
--   The file defines a MIB to provide the probing feature.
-- Reference:
-- Version: V1.0
-- History:
--   V1.0 created by sunanzhi
--     Initial version 2016-03-28
-- =============================================================================
H3C-DOT11-PROBE-MIB DEFINITIONS ::= BEGIN

IMPORTS
    TimeTicks, Integer32, OBJECT-TYPE, MODULE-IDENTITY
        FROM SNMPv2-SMI
    TruthValue, MacAddress, TEXTUAL-CONVENTION
        FROM SNMPv2-TC
    h3cDot11
        FROM HUAWEI-3COM-OID-MIB;

h3cDot11PROBE MODULE-IDENTITY
    LAST-UPDATED "201603280951Z"        -- March 28, 2016 at 09:51 GMT
    ORGANIZATION
        "Hangzhou H3C Technologies Co., Ltd."
    CONTACT-INFO
        "Platform Team Hangzhou H3C Technologies Co., Ltd.
        Hai-Dian District Beijing P.R. China
        http://www.h3c.com
        Zip:100085
        "
    DESCRIPTION
        "This MIB provides information about the probing feature.
        Probing is designed to detect wireless devices around a sensor.
        "
    REVISION "201603280951Z"        -- March 28, 2016 at 09:51 GMT
    DESCRIPTION
        "The initial revision of this MIB module."
    ::= {  h3cDot11 17 }

--
-- Textual conventions
--
H3cDot11PROBEEnabledStatus ::= TEXTUAL-CONVENTION
    STATUS      current
    DESCRIPTION
        "The enable status values for objects.
        Values include enabled and disabled."
    SYNTAX      INTEGER { enabled(1), disabled(2) }

H3cDot11PROBERadioType ::= TEXTUAL-CONVENTION
    STATUS current
    DESCRIPTION
        "Represents AP's 802.11 radio type of 802.11a/b/g/n as per
        the standard.
        The following values are supported:
        dot11a  - 802.11a
        dot11b  - 802.11b
        dot11g  - 802.11g
        dot11n  - 802.11n
        dot11gn  - 802.11gn
        dot11an  - 802.11an
        dot11ac  - 802.11ac
        dot11gac  - 802.11gac"
    SYNTAX INTEGER
        {
        dot11a(1),
        dot11b(2),
        dot11g(4),
        dot11n(8),
        dot11gn(16),
        dot11an(32),
        dot11ac(64),
        dot11gac(128)
       }

H3cDot11PROBEDevStatus ::= TEXTUAL-CONVENTION
    STATUS current
    DESCRIPTION
        "Represents the status of devices detected by probing."
    SYNTAX INTEGER
        {
        active(1),
        inactive(2)
       }

H3cDot11PROBEChannel ::= TEXTUAL-CONVENTION
    DISPLAY-HINT "d"
    STATUS current
    DESCRIPTION
        "Represents the channel number."
    SYNTAX Integer32 (1..224)

H3cDot11PROBEEncryptMethod ::= TEXTUAL-CONVENTION
    DISPLAY-HINT "d"
    STATUS current
    DESCRIPTION
        "Represents the frame encryption cipher types (bitmap) for
        frames on IEEE 802.11 radio interfaces.
        The MIB defines TC by referring to the 802.11i protocol.
        The following bits are supported:
        first bit:    none,
        second bit:   wep,
        third bit:    wep40,
        fourth bit:   tkip
        fifth bit:    reserve
        sixth bit:    ccmp
        seventh bit:  wep104
        eighth bit:   wep128"
    SYNTAX Integer32 (1..65535)

H3cDot11PROBEAuthMethod ::= TEXTUAL-CONVENTION
    DISPLAY-HINT "d"
    STATUS current
    DESCRIPTION
        "Represents the key management mode (bitmap), compliant with 802.11i.
        The following bits are supported:
        first bit:   none         - No key management mode is specified,
        second bit:  dot1x        - 802.1X authentication.
        third bit:   psk          - Pre-shared key authentication,
        fourth bit:  other        - Other authentication."
    SYNTAX Integer32 (1..65535)

H3cDot11PROBESecurityType ::= TEXTUAL-CONVENTION
    DISPLAY-HINT "d"
    STATUS current
    DESCRIPTION
        "Represents the AP security type (bitmap).
        The following bits are supported:
        first bit:   none,
        second bit:  wpa2,
        third bit:   wpa,
        fourth bit:  wlanex
        fifth bit:   wep"
    SYNTAX Integer32 (1..255)

--
-- Node definitions
--
h3cDot11PROBEConfigGroup OBJECT IDENTIFIER ::= { h3cDot11PROBE 1 }
h3cDot11PROBEDataGroup OBJECT IDENTIFIER ::= { h3cDot11PROBE 2 }

h3cDot11PROBERadioCfgTable OBJECT-TYPE
    SYNTAX SEQUENCE OF H3cDot11PROBERadioCfgEntry
    MAX-ACCESS not-accessible
    STATUS current
    DESCRIPTION
        "The table defines the configuration of probing enable status."
    ::= { h3cDot11PROBEConfigGroup 1 }

h3cDot11PROBERadioCfgEntry OBJECT-TYPE
    SYNTAX H3cDot11PROBERadioCfgEntry
    MAX-ACCESS not-accessible
    STATUS current
    DESCRIPTION
        "Each entry contains the enable status of probing."
    INDEX { h3cDot11PROBERadioCfgApName, h3cDot11PROBERadioCfgRadioId }
    ::= { h3cDot11PROBERadioCfgTable 1 }

H3cDot11PROBERadioCfgEntry ::= SEQUENCE {
        h3cDot11PROBERadioCfgApName            OCTET STRING,
        h3cDot11PROBERadioCfgRadioId           Integer32,
        h3cDot11PROBERadioCfgStatus            H3cDot11PROBEEnabledStatus
    }

h3cDot11PROBERadioCfgApName OBJECT-TYPE
    SYNTAX OCTET STRING (SIZE (1..64))
    MAX-ACCESS not-accessible
    STATUS current
    DESCRIPTION
        "Represents the AP name."
    ::= { h3cDot11PROBERadioCfgEntry 1 }

h3cDot11PROBERadioCfgRadioId OBJECT-TYPE
    SYNTAX Integer32 (1..4)
    MAX-ACCESS not-accessible
    STATUS current
    DESCRIPTION
        "Represents the radio ID of the AP."
    ::= { h3cDot11PROBERadioCfgEntry 2 }

h3cDot11PROBERadioCfgStatus OBJECT-TYPE
    SYNTAX H3cDot11PROBEEnabledStatus
    MAX-ACCESS read-write
    STATUS current
    DESCRIPTION
        "The enable status of probing configuration on the radio."
    ::= { h3cDot11PROBERadioCfgEntry 3 }

h3cDot11PROBEClientTable OBJECT-TYPE
    SYNTAX SEQUENCE OF H3cDot11PROBEClientEntry
    MAX-ACCESS not-accessible
    STATUS current
    DESCRIPTION
        "The table contains information about clients detected by probing."
    ::= { h3cDot11PROBEDataGroup 1 }

h3cDot11PROBEClientEntry OBJECT-TYPE
    SYNTAX H3cDot11PROBEClientEntry
    MAX-ACCESS not-accessible
    STATUS current
    DESCRIPTION
        "Each entry contains information about a client detected by probing."
    INDEX { h3cDot11PROBEClientMac }
    ::= { h3cDot11PROBEClientTable 1 }

H3cDot11PROBEClientEntry ::= SEQUENCE {
        h3cDot11PROBEClientMac                MacAddress,
        h3cDot11PROBEClientBSSID              MacAddress,
        h3cDot11PROBEClientSSID               OCTET STRING,
        h3cDot11PROBEClientIsDiss             TruthValue,
        h3cDot11PROBEClientStatus             H3cDot11PROBEDevStatus,
        h3cDot11PROBEClientDuratTime          TimeTicks,
        h3cDot11PROBEClientVendor             OCTET STRING,
        h3cDot11PROBEClientRptApNum           Integer32,
        h3cDot11PROBEClientWorkChannel        H3cDot11PROBEChannel,
        h3cDot11PROBEClientRSSIMax            Integer32,
        h3cDot11PROBEClientRSSIMin            Integer32,
        h3cDot11PROBEClientRSSI               Integer32,
        h3cDot11PROBEClientFirstTime          OCTET STRING,
        h3cDot11PROBEClientLastTime           OCTET STRING
    }

h3cDot11PROBEClientMac OBJECT-TYPE
    SYNTAX MacAddress
    MAX-ACCESS not-accessible
    STATUS current
    DESCRIPTION
        "Represents the MAC address of the client detected by probing."
    ::= { h3cDot11PROBEClientEntry 1 }

h3cDot11PROBEClientBSSID OBJECT-TYPE
    SYNTAX MacAddress
    MAX-ACCESS read-only
    STATUS current
    DESCRIPTION
        "Represents the BSSID with which the detected client is associated."
    ::= { h3cDot11PROBEClientEntry 2 }

h3cDot11PROBEClientSSID OBJECT-TYPE
    SYNTAX OCTET STRING (SIZE (0..32))
    MAX-ACCESS read-only
    STATUS current
    DESCRIPTION
        "Represents the SSID with which the detected client is associated."
    ::= { h3cDot11PROBEClientEntry 3 }

h3cDot11PROBEClientIsDiss OBJECT-TYPE
    SYNTAX TruthValue
    MAX-ACCESS read-only
    STATUS current
    DESCRIPTION
        "Represents whether the detected client is disassociated."
    ::= { h3cDot11PROBEClientEntry 4 }

h3cDot11PROBEClientStatus OBJECT-TYPE
    SYNTAX H3cDot11PROBEDevStatus
    MAX-ACCESS read-only
    STATUS current
    DESCRIPTION
        "Represents the status of the detected client."
    ::= { h3cDot11PROBEClientEntry 5 }

h3cDot11PROBEClientDuratTime OBJECT-TYPE
    SYNTAX TimeTicks
    MAX-ACCESS read-only
    STATUS current
    DESCRIPTION
        "Represents the duration of the detected client status."
    ::= { h3cDot11PROBEClientEntry 6 }

h3cDot11PROBEClientVendor OBJECT-TYPE
    SYNTAX OCTET STRING (SIZE (0..127))
    MAX-ACCESS read-only
    STATUS current
    DESCRIPTION
        "Represents the vendor of the detected client."
    ::= { h3cDot11PROBEClientEntry 7 }

h3cDot11PROBEClientRptApNum OBJECT-TYPE
    SYNTAX Integer32
    MAX-ACCESS read-only
    STATUS current
    DESCRIPTION
        "Represents the number of sensors that have detected the client."
    ::= { h3cDot11PROBEClientEntry 8 }

h3cDot11PROBEClientWorkChannel OBJECT-TYPE
    SYNTAX H3cDot11PROBEChannel
    MAX-ACCESS read-only
    STATUS current
    DESCRIPTION
        "Represents the channel on which the sensor detected
        the client."
    ::= { h3cDot11PROBEClientEntry 9 }

h3cDot11PROBEClientRSSIMax OBJECT-TYPE
    SYNTAX Integer32
    MAX-ACCESS read-only
    STATUS current
    DESCRIPTION
        "Represents the maximum RSSI of the detected client."
    ::= { h3cDot11PROBEClientEntry 10 }

h3cDot11PROBEClientRSSIMin OBJECT-TYPE
    SYNTAX Integer32
    MAX-ACCESS read-only
    STATUS current
    DESCRIPTION
        "Represents the minimum RSSI of the detected client."
    ::= { h3cDot11PROBEClientEntry 11 }

h3cDot11PROBEClientRSSI OBJECT-TYPE
    SYNTAX Integer32
    MAX-ACCESS read-only
    STATUS current
    DESCRIPTION
        "Represents the RSSI of the detected client."
    ::= { h3cDot11PROBEClientEntry 12 }

h3cDot11PROBEClientFirstTime OBJECT-TYPE
    SYNTAX OCTET STRING (SIZE (1..256))
    MAX-ACCESS read-only
    STATUS current
    DESCRIPTION
        "Represents the First Report Time of the detected client."
    ::= { h3cDot11PROBEClientEntry 13 }

h3cDot11PROBEClientLastTime OBJECT-TYPE
    SYNTAX OCTET STRING (SIZE (1..256))
    MAX-ACCESS read-only
    STATUS current
    DESCRIPTION
        "Represents the Last Report Time of the detected client."
    ::= { h3cDot11PROBEClientEntry 14 }

h3cDot11PROBEStatTable OBJECT-TYPE
    SYNTAX SEQUENCE OF H3cDot11PROBEStatEntry
    MAX-ACCESS not-accessible
    STATUS current
    DESCRIPTION
        "The table contains statistic information about detected clients."
    ::= { h3cDot11PROBEDataGroup 2 }

h3cDot11PROBEStatEntry OBJECT-TYPE
    SYNTAX H3cDot11PROBEStatEntry
    MAX-ACCESS not-accessible
    STATUS current
    DESCRIPTION
        "Each entry contains statistic information about a detected station."
    INDEX { h3cDot11PROBEStatTime }
    ::= { h3cDot11PROBEStatTable 1 }

H3cDot11PROBEStatEntry ::= SEQUENCE {
        h3cDot11PROBEStatTime            OCTET STRING,
        h3cDot11PROBEStatRssiMaxNum      Integer32,
        h3cDot11PROBEStatRssiMiddleNum   Integer32,
        h3cDot11PROBEStatRssiMinNum      Integer32,
        h3cDot11PROBEStatTotalNum        Integer32,
        h3cDot11PROBEStatAssocNum        Integer32,
        h3cDot11PROBEStatDissocNum       Integer32
    }

h3cDot11PROBEStatTime OBJECT-TYPE
    SYNTAX OCTET STRING (SIZE (1..256))
    MAX-ACCESS not-accessible
    STATUS current
    DESCRIPTION
        "Represents the statistics collection time of the detected client."
    ::= { h3cDot11PROBEStatEntry 1 }

h3cDot11PROBEStatRssiMaxNum OBJECT-TYPE
    SYNTAX Integer32
    MAX-ACCESS read-only
    STATUS current
    DESCRIPTION
        "Represents the maximum RSSI of the detected client."
    ::= { h3cDot11PROBEStatEntry 2 }

h3cDot11PROBEStatRssiMiddleNum OBJECT-TYPE
    SYNTAX Integer32
    MAX-ACCESS read-only
    STATUS current
    DESCRIPTION
        "Represents the medium RSSI of the detected client."
    ::= { h3cDot11PROBEStatEntry 3 }

h3cDot11PROBEStatRssiMinNum OBJECT-TYPE
    SYNTAX Integer32
    MAX-ACCESS read-only
    STATUS current
    DESCRIPTION
        "Represents the minimum RSSI of the detected client."
    ::= { h3cDot11PROBEStatEntry 4 }

h3cDot11PROBEStatTotalNum OBJECT-TYPE
    SYNTAX Integer32
    MAX-ACCESS read-only
    STATUS current
    DESCRIPTION
        "Represents the total number of detected clients."
    ::= { h3cDot11PROBEStatEntry 5 }

h3cDot11PROBEStatAssocNum OBJECT-TYPE
    SYNTAX Integer32
    MAX-ACCESS read-only
    STATUS current
    DESCRIPTION
        "Represents the number of detected associated clients."
    ::= { h3cDot11PROBEStatEntry 6 }

h3cDot11PROBEStatDissocNum OBJECT-TYPE
    SYNTAX Integer32
    MAX-ACCESS read-only
    STATUS current
    DESCRIPTION
        "Represents the number of detected disassociated clients."
    ::= { h3cDot11PROBEStatEntry 7 }

h3cDot11PROBEApTable OBJECT-TYPE
    SYNTAX SEQUENCE OF H3cDot11PROBEApEntry
    MAX-ACCESS not-accessible
    STATUS current
    DESCRIPTION
        "The table contains information about AP detected by probing."
    ::= { h3cDot11PROBEDataGroup 3 }

h3cDot11PROBEApEntry OBJECT-TYPE
    SYNTAX H3cDot11PROBEApEntry
    MAX-ACCESS not-accessible
    STATUS current
    DESCRIPTION
        "Each entry contains information about a detected AP."
    INDEX { h3cDot11PROBEApMacAddress }
    ::= { h3cDot11PROBEApTable 1 }

H3cDot11PROBEApEntry ::= SEQUENCE {
        h3cDot11PROBEApMacAddress                MacAddress,
        h3cDot11PROBEApSsid                      OCTET STRING,
        h3cDot11PROBEApStatus                    H3cDot11PROBEDevStatus,
        h3cDot11PROBEApStatusDuTime              TimeTicks,
        h3cDot11PROBEApVendor                    OCTET STRING,
        h3cDot11PROBEApRadioType                 H3cDot11PROBERadioType,
        h3cDot11PROBEApSecurityType              H3cDot11PROBESecurityType,
        h3cDot11PROBEApEncryMethod               H3cDot11PROBEEncryptMethod,
        h3cDot11PROBEApAuthMethod                H3cDot11PROBEAuthMethod,
        h3cDot11PROBEApIsBroadSSID               TruthValue,
        h3cDot11PROBEApQosSupport                TruthValue,
        h3cDot11PROBEApBeaconIntvl               Integer32,
        h3cDot11PROBEApUpDuration                TimeTicks,
        h3cDot11PROBEApSCWS                      TruthValue,
        h3cDot11PROBEApRptSensorNum              Integer32,
        h3cDot11PROBEApChannel                   H3cDot11PROBEChannel,
        h3cDot11PROBEApRSSIMax                   Integer32,
        h3cDot11PROBEApRSSIMin                   Integer32,
        h3cDot11PROBEApRSSI                      Integer32,
        h3cDot11PROBEApFirstRptTime              OCTET STRING,
        h3cDot11PROBEApLastRptTime               OCTET STRING
    }

h3cDot11PROBEApMacAddress OBJECT-TYPE
    SYNTAX MacAddress
    MAX-ACCESS not-accessible
    STATUS current
    DESCRIPTION
        "Represents the MAC address of the detected AP."
    ::= { h3cDot11PROBEApEntry 1 }

h3cDot11PROBEApSsid OBJECT-TYPE
    SYNTAX OCTET STRING  (SIZE (0..32))
    MAX-ACCESS read-only
    STATUS current
    DESCRIPTION
        "Represents the SSID of the detected AP."
    ::= { h3cDot11PROBEApEntry 2 }

h3cDot11PROBEApStatus OBJECT-TYPE
    SYNTAX H3cDot11PROBEDevStatus
    MAX-ACCESS read-only
    STATUS current
    DESCRIPTION
        "Represents the device status of the detected AP."
    ::= { h3cDot11PROBEApEntry 3}

h3cDot11PROBEApStatusDuTime OBJECT-TYPE
    SYNTAX TimeTicks
    MAX-ACCESS read-only
    STATUS current
    DESCRIPTION
        "Represents the last report time of the detected AP."
    ::= { h3cDot11PROBEApEntry 4 }

h3cDot11PROBEApVendor OBJECT-TYPE
    SYNTAX OCTET STRING   (SIZE (0..127))
    MAX-ACCESS read-only
    STATUS current
    DESCRIPTION
        "Represents the vendor of the detected AP."
    ::= { h3cDot11PROBEApEntry 5 }

h3cDot11PROBEApRadioType OBJECT-TYPE
    SYNTAX H3cDot11PROBERadioType
    MAX-ACCESS read-only
    STATUS current
    DESCRIPTION
        "Represents the radio type used by the detected AP."
    ::= { h3cDot11PROBEApEntry 6}

h3cDot11PROBEApSecurityType OBJECT-TYPE
    SYNTAX H3cDot11PROBESecurityType
    MAX-ACCESS read-only
    STATUS current
    DESCRIPTION
        "Represents the security suites of the detected AP."
    ::= { h3cDot11PROBEApEntry 7 }

h3cDot11PROBEApEncryMethod OBJECT-TYPE
    SYNTAX H3cDot11PROBEEncryptMethod
    MAX-ACCESS read-only
    STATUS current
    DESCRIPTION
        "Represents the encryption method used by the detected AP."
    ::= { h3cDot11PROBEApEntry 8 }

h3cDot11PROBEApAuthMethod OBJECT-TYPE
    SYNTAX H3cDot11PROBEAuthMethod
    MAX-ACCESS read-only
    STATUS current
    DESCRIPTION
        "Represents the authentication method used by the detected AP."
    ::= { h3cDot11PROBEApEntry 9 }

h3cDot11PROBEApIsBroadSSID OBJECT-TYPE
    SYNTAX TruthValue
    MAX-ACCESS read-only
    STATUS current
    DESCRIPTION
        "Represents the support of the detected AP for broadcasting the SSID."
    ::= { h3cDot11PROBEApEntry 10 }

h3cDot11PROBEApQosSupport OBJECT-TYPE
    SYNTAX TruthValue
    MAX-ACCESS read-only
    STATUS current
    DESCRIPTION
        "Represents the support of the detected AP for QoS."
    ::= { h3cDot11PROBEApEntry 11 }

h3cDot11PROBEApBeaconIntvl OBJECT-TYPE
    SYNTAX Integer32
    MAX-ACCESS read-only
    STATUS current
    DESCRIPTION
        "Represents the beacon interval of the detected AP."
    ::= { h3cDot11PROBEApEntry 12 }

h3cDot11PROBEApUpDuration OBJECT-TYPE
    SYNTAX TimeTicks
    MAX-ACCESS read-only
    STATUS current
    DESCRIPTION
        "Represents the amount of time that has elapsed since AP
        started to work, which is calculated by using beacon/probe
        response frame."
    ::= { h3cDot11PROBEApEntry 13 }

h3cDot11PROBEApSCWS OBJECT-TYPE
    SYNTAX TruthValue
    MAX-ACCESS read-only
    STATUS current
    DESCRIPTION
        "Represents the support for channel bandwidth of the detected AP."
    ::= { h3cDot11PROBEApEntry 14 }

h3cDot11PROBEApRptSensorNum OBJECT-TYPE
    SYNTAX Integer32
    MAX-ACCESS read-only
    STATUS current
    DESCRIPTION
        "Represents the number of sensors that have detected the AP."
    ::= { h3cDot11PROBEApEntry 15 }

h3cDot11PROBEApChannel OBJECT-TYPE
    SYNTAX H3cDot11PROBEChannel
    MAX-ACCESS read-only
    STATUS current
    DESCRIPTION
        "Represents the radio channel on which the detected AP operates."
    ::= { h3cDot11PROBEApEntry 16 }

h3cDot11PROBEApRSSIMax OBJECT-TYPE
    SYNTAX Integer32
    MAX-ACCESS read-only
    STATUS current
    DESCRIPTION
        "Represents the maximum RSSI of the detected AP."
    ::= { h3cDot11PROBEApEntry 17 }

h3cDot11PROBEApRSSIMin OBJECT-TYPE
    SYNTAX Integer32
    MAX-ACCESS read-only
    STATUS current
    DESCRIPTION
        "Represents the minimum RSSI of the detected AP."
    ::= { h3cDot11PROBEApEntry 18 }

h3cDot11PROBEApRSSI OBJECT-TYPE
    SYNTAX Integer32
    MAX-ACCESS read-only
    STATUS current
    DESCRIPTION
        "Represents the RSSI of the detected AP."
    ::= { h3cDot11PROBEApEntry 19 }

h3cDot11PROBEApFirstRptTime OBJECT-TYPE
    SYNTAX  OCTET STRING (SIZE (1..256))
    MAX-ACCESS read-only
    STATUS current
    DESCRIPTION
        "Represents the first report time of the detected AP."
    ::= { h3cDot11PROBEApEntry 20 }

h3cDot11PROBEApLastRptTime OBJECT-TYPE
    SYNTAX  OCTET STRING (SIZE (1..256))
    MAX-ACCESS read-only
    STATUS current
    DESCRIPTION
        "Represents the last report time of the detected AP."
    ::= { h3cDot11PROBEApEntry 21 }

h3cDot11PROBEApAssoCltTable OBJECT-TYPE
    SYNTAX SEQUENCE OF H3cDot11PROBEApAssoCltEntry
    MAX-ACCESS not-accessible
    STATUS current
    DESCRIPTION
        "The table contains information about associated clients."
    ::= { h3cDot11PROBEDataGroup 4 }

h3cDot11PROBEApAssoCltEntry OBJECT-TYPE
    SYNTAX H3cDot11PROBEApAssoCltEntry
    MAX-ACCESS not-accessible
    STATUS current
    DESCRIPTION
        "Each entry contains information about an associated client."
    INDEX { h3cDot11PROBEApAssoCltApMac, h3cDot11PROBEApAssoCltCltMac }
    ::= { h3cDot11PROBEApAssoCltTable 1 }

H3cDot11PROBEApAssoCltEntry ::= SEQUENCE {
        h3cDot11PROBEApAssoCltApMac               MacAddress,
        h3cDot11PROBEApAssoCltCltMac              MacAddress,
        h3cDot11PROBEApAssoCltIsAsso              TruthValue
    }

h3cDot11PROBEApAssoCltApMac OBJECT-TYPE
    SYNTAX MacAddress
    MAX-ACCESS not-accessible
    STATUS current
    DESCRIPTION
        "Represents the MAC address of the AP."
    ::= { h3cDot11PROBEApAssoCltEntry 1 }

h3cDot11PROBEApAssoCltCltMac OBJECT-TYPE
    SYNTAX MacAddress
    MAX-ACCESS not-accessible
    STATUS current
    DESCRIPTION
        "Represents the MAC address of the client."
    ::= { h3cDot11PROBEApAssoCltEntry 2 }

h3cDot11PROBEApAssoCltIsAsso OBJECT-TYPE
    SYNTAX TruthValue
    MAX-ACCESS read-only
    STATUS current
    DESCRIPTION
        "Represents whether the detected client has been associated with the AP."
    ::= { h3cDot11PROBEApAssoCltEntry 3 }

h3cDot11PROBEApRepSenTable OBJECT-TYPE
    SYNTAX SEQUENCE OF H3cDot11PROBEApRepSenEntry
    MAX-ACCESS not-accessible
    STATUS current
    DESCRIPTION
        "The table contains information about the sensor that detected the AP."
    ::= { h3cDot11PROBEDataGroup 5 }

h3cDot11PROBEApRepSenEntry OBJECT-TYPE
    SYNTAX H3cDot11PROBEApRepSenEntry
    MAX-ACCESS not-accessible
    STATUS current
    DESCRIPTION
        "Each entry contains information about the sensor that detected the AP."
    INDEX { h3cDot11PROBEApRepSenApMac, h3cDot11PROBEApRepSenSenName }
    ::= { h3cDot11PROBEApRepSenTable 1 }

H3cDot11PROBEApRepSenEntry ::= SEQUENCE {
        h3cDot11PROBEApRepSenApMac                MacAddress,
        h3cDot11PROBEApRepSenSenName              OCTET STRING,
        h3cDot11PROBEApRepSenRadioId              Integer32,
        h3cDot11PROBEApRepSenRssi                 Integer32,
        h3cDot11PROBEApRepSenChannel              H3cDot11PROBEChannel,
        h3cDot11PROBEApRepSenFirRepTim            OCTET STRING,
        h3cDot11PROBEApRepSenLasRepTim            OCTET STRING
    }

h3cDot11PROBEApRepSenApMac OBJECT-TYPE
    SYNTAX MacAddress
    MAX-ACCESS not-accessible
    STATUS current
    DESCRIPTION
        "Represents the MAC address of the AP."
    ::= { h3cDot11PROBEApRepSenEntry 1 }

h3cDot11PROBEApRepSenSenName OBJECT-TYPE
    SYNTAX OCTET STRING (SIZE (1..64))
    MAX-ACCESS not-accessible
    STATUS current
    DESCRIPTION
        "Represents the name of the sensor."
    ::= { h3cDot11PROBEApRepSenEntry 2 }

h3cDot11PROBEApRepSenRadioId OBJECT-TYPE
    SYNTAX Integer32 (1..4)
    MAX-ACCESS read-only
    STATUS current
    DESCRIPTION
        "Represents the radio ID of the sensor."
    ::= { h3cDot11PROBEApRepSenEntry 3 }

h3cDot11PROBEApRepSenRssi OBJECT-TYPE
    SYNTAX Integer32
    MAX-ACCESS read-only
    STATUS current
    DESCRIPTION
        "Represents the RSSI of the sensor."
    ::= { h3cDot11PROBEApRepSenEntry 4 }

h3cDot11PROBEApRepSenChannel OBJECT-TYPE
    SYNTAX H3cDot11PROBEChannel
    MAX-ACCESS read-only
    STATUS current
    DESCRIPTION
        "Represents the channel on which the sensor detected
        the AP."
    ::= { h3cDot11PROBEApRepSenEntry 5 }

h3cDot11PROBEApRepSenFirRepTim OBJECT-TYPE
    SYNTAX  OCTET STRING (SIZE (1..256))
    MAX-ACCESS read-only
    STATUS current
    DESCRIPTION
        "Represents the duration of the detected AP."
    ::= { h3cDot11PROBEApRepSenEntry 6 }

h3cDot11PROBEApRepSenLasRepTim OBJECT-TYPE
    SYNTAX  OCTET STRING (SIZE (1..256))
    MAX-ACCESS read-only
    STATUS current
    DESCRIPTION
        "Represents the duration of the detected AP."
    ::= { h3cDot11PROBEApRepSenEntry 7 }

h3cDot11PROBECliRepSenTable OBJECT-TYPE
    SYNTAX SEQUENCE OF H3cDot11PROBECliRepSenEntry
    MAX-ACCESS not-accessible
    STATUS current
    DESCRIPTION
        "The table contains information about the sensor that detected the client."
    ::= { h3cDot11PROBEDataGroup 6 }

h3cDot11PROBECliRepSenEntry OBJECT-TYPE
    SYNTAX H3cDot11PROBECliRepSenEntry
    MAX-ACCESS not-accessible
    STATUS current
    DESCRIPTION
        "Each entry contains information about the sensor that detected the client."
    INDEX { h3cDot11PROBECliRepSenCliMac, h3cDot11PROBECliRepSenSenName }
    ::= { h3cDot11PROBECliRepSenTable 1 }

H3cDot11PROBECliRepSenEntry ::= SEQUENCE {
        h3cDot11PROBECliRepSenCliMac               MacAddress,
        h3cDot11PROBECliRepSenSenName              OCTET STRING,
        h3cDot11PROBECliRepSenRadioId              Integer32,
        h3cDot11PROBECliRepSenRssi                 Integer32,
        h3cDot11PROBECliRepSenChannel              H3cDot11PROBEChannel,
        h3cDot11PROBECliRepSenFRepTime             OCTET STRING,
        h3cDot11PROBECliRepSenLRepTime             OCTET STRING,
        h3cDot11PROBECliRepSenAssAPMac             MacAddress
    }

h3cDot11PROBECliRepSenCliMac OBJECT-TYPE
    SYNTAX MacAddress
    MAX-ACCESS not-accessible
    STATUS current
    DESCRIPTION
        "Represents the MAC address of the client."
    ::= { h3cDot11PROBECliRepSenEntry 1 }

h3cDot11PROBECliRepSenSenName OBJECT-TYPE
    SYNTAX OCTET STRING (SIZE (1..64))
    MAX-ACCESS not-accessible
    STATUS current
    DESCRIPTION
        "Represents the name of the sensor."
    ::= { h3cDot11PROBECliRepSenEntry 2 }

h3cDot11PROBECliRepSenRadioId OBJECT-TYPE
    SYNTAX Integer32 (1..4)
    MAX-ACCESS read-only
    STATUS current
    DESCRIPTION
        "Represents the radio ID of the sensor."
    ::= { h3cDot11PROBECliRepSenEntry 3 }

h3cDot11PROBECliRepSenRssi OBJECT-TYPE
    SYNTAX Integer32
    MAX-ACCESS read-only
    STATUS current
    DESCRIPTION
        "Represents the RSSI of the sensor."
    ::= { h3cDot11PROBECliRepSenEntry 4 }

h3cDot11PROBECliRepSenChannel OBJECT-TYPE
    SYNTAX H3cDot11PROBEChannel
    MAX-ACCESS read-only
    STATUS current
    DESCRIPTION
        "Represents the channel on which the sensor detected
        the client."
    ::= { h3cDot11PROBECliRepSenEntry 5 }

h3cDot11PROBECliRepSenFRepTime OBJECT-TYPE
    SYNTAX OCTET STRING (SIZE (1..256))
    MAX-ACCESS read-only
    STATUS current
    DESCRIPTION
        "Represents the duration of the detected client."
    ::= { h3cDot11PROBECliRepSenEntry 6 }

h3cDot11PROBECliRepSenLRepTime OBJECT-TYPE
    SYNTAX  OCTET STRING (SIZE (1..256))
    MAX-ACCESS read-only
    STATUS current
    DESCRIPTION
        "Represents the duration of the detected client."
    ::= { h3cDot11PROBECliRepSenEntry 7 }

h3cDot11PROBECliRepSenAssAPMac OBJECT-TYPE
    SYNTAX MacAddress
    MAX-ACCESS read-only
    STATUS current
    DESCRIPTION
        "Represents the MAC address of the associated AP."
    ::= { h3cDot11PROBECliRepSenEntry 8 }

END
