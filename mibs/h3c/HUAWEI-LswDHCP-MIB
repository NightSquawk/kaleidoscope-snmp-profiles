-- ==================================================================
-- Copyright (C) 2002 by  H3C TECHNOLOGIES. All rights reserved.
--
-- Description: DHCP MIB
-- Reference:
-- Version: V1.0
-- History:
--(1) Created by Zhang Shilin, 2001.6.29
--(2) Revised by Qi Zhenglin, 2002.01.08
-- ==================================================================

-- ==================================================================
--
-- Varibles and types be imported
--
-- ==================================================================

HUAWEI-LswDHCP-MIB DEFINITIONS ::= BEGIN

IMPORTS

    RowStatus, MacAddress
        FROM SNMPv2-TC

    MODULE-IDENTITY,OBJECT-TYPE, IpAddress
        FROM SNMPv2-SMI

    lswCommon
        FROM HUAWEI-3COM-OID-MIB;

-- ==================================================================
--
-- ======================= definition begin =========================
--
-- ==================================================================
hwLswDhcpMib MODULE-IDENTITY
            LAST-UPDATED "200106290000Z"
            ORGANIZATION
                "Hangzhou H3C Tech. Co., Ltd."
            CONTACT-INFO
                "Platform Team Hangzhou H3C Tech. Co., Ltd.
                Hai-Dian District Beijing P.R. China
                http://www.h3c.com
                Zip:100085
                "
            DESCRIPTION
            ""
            REVISION "200106290000Z"
            DESCRIPTION
            ""
            ::= { lswCommon  8 }

    hwLswDhcpMibObject OBJECT IDENTIFIER ::= {  hwLswDhcpMib 1  }

    hwDhcpGroupTable OBJECT-TYPE
        SYNTAX  SEQUENCE OF HwDhcpGroupEntry
        MAX-ACCESS not-accessible
        STATUS   current
        DESCRIPTION "A table containing the information of dhcp group "
        ::= { hwLswDhcpMibObject 1 }


     hwDhcpGroupEntry OBJECT-TYPE
        SYNTAX  HwDhcpGroupEntry
        MAX-ACCESS not-accessible
        STATUS current
        DESCRIPTION "A table entry containing the information of dhcp group "
        INDEX   { hwDhcpGroupID }
        ::= { hwDhcpGroupTable 1 }

    HwDhcpGroupEntry    ::=
    SEQUENCE {
        hwDhcpGroupID           INTEGER ,
        hwIpDhcpServerAddress1  IpAddress ,
        hwIpDhcpServerAddress2  IpAddress ,
        hwDhcpRowStatus         RowStatus
        }

    hwDhcpGroupID OBJECT-TYPE
        SYNTAX  INTEGER  (0..19)
        MAX-ACCESS read-create
        STATUS current
        DESCRIPTION " DHCP group identifier "
        ::= { hwDhcpGroupEntry 1 }

    hwIpDhcpServerAddress1 OBJECT-TYPE
        SYNTAX  IpAddress
        MAX-ACCESS read-write
        STATUS current
        DESCRIPTION " The first IP address of DHCP server group "
        ::= { hwDhcpGroupEntry 2 }

    hwIpDhcpServerAddress2 OBJECT-TYPE
        SYNTAX  IpAddress
        MAX-ACCESS read-write
        STATUS current
        DESCRIPTION " The second IP address of DHCP server group "
        ::= { hwDhcpGroupEntry 3 }

    hwDhcpRowStatus OBJECT-TYPE
        SYNTAX  RowStatus
        MAX-ACCESS read-create
        STATUS current
        DESCRIPTION " Operation status of this table entry     "
        ::= { hwDhcpGroupEntry 4 }

    hwDhcpSecurityTable OBJECT-TYPE
        SYNTAX  SEQUENCE OF HwDhcpSecurityEntry
        MAX-ACCESS not-accessible
        STATUS   current
        DESCRIPTION "A table containing the information of dhcp security "
        ::= { hwLswDhcpMibObject 2 }


     hwDhcpSecurityEntry OBJECT-TYPE
        SYNTAX  HwDhcpSecurityEntry
        MAX-ACCESS not-accessible
        STATUS current
        DESCRIPTION "A table containing the information of dhcp security "
        INDEX   { hwDhcpClientIpAddress }
        ::= { hwDhcpSecurityTable 1 }

    HwDhcpSecurityEntry    ::=
    SEQUENCE {
        hwDhcpClientIpAddress   IpAddress ,
        hwDhcpClientMacAddress  MacAddress,
        hwDhcpClientProperty    INTEGER ,
        hwDhcpClientRowStatus   RowStatus
        }

    hwDhcpClientIpAddress OBJECT-TYPE
        SYNTAX  IpAddress
        MAX-ACCESS read-only
        STATUS current
        DESCRIPTION " DHCP client's net ip address "
        ::= { hwDhcpSecurityEntry 1 }

    hwDhcpClientMacAddress OBJECT-TYPE
        SYNTAX  MacAddress
        MAX-ACCESS read-write
        STATUS current
        DESCRIPTION " DHCP client's mac address     "
        ::= { hwDhcpSecurityEntry 2 }

    hwDhcpClientProperty OBJECT-TYPE
        SYNTAX  INTEGER
        {
            static(1),
            dynamic(2)
        }
        MAX-ACCESS read-write
        STATUS current
        DESCRIPTION " Property of client address     "
        ::= { hwDhcpSecurityEntry 3 }

    hwDhcpClientRowStatus OBJECT-TYPE
        SYNTAX  RowStatus
        MAX-ACCESS read-create
        STATUS current
        DESCRIPTION " status of this table's entry.     "
        ::= { hwDhcpSecurityEntry 4 }


    hwDhcpToL3IfTable OBJECT-TYPE
        SYNTAX  SEQUENCE OF HwDhcpToL3IfEntry
        MAX-ACCESS not-accessible
        STATUS   current
        DESCRIPTION "A table configuring dhcp for layer 3 interface"
        ::= { hwLswDhcpMibObject 3 }


    hwDhcpToL3IfEntry OBJECT-TYPE
        SYNTAX  HwDhcpToL3IfEntry
        MAX-ACCESS not-accessible
        STATUS current
        DESCRIPTION "A table configuring dhcp for layer 3 interface "
        INDEX   { hwDhcpToL3VlanIfIndex }
        ::= { hwDhcpToL3IfTable 1 }

    HwDhcpToL3IfEntry    ::=
    SEQUENCE {
        hwDhcpToL3VlanIfIndex  INTEGER ,
        hwDhcpToL3GroupId      INTEGER,
        hwDhcpToL3AddressCheck INTEGER ,
        hwDhcpToL3RowStatus    RowStatus
        }

    hwDhcpToL3VlanIfIndex OBJECT-TYPE
        SYNTAX  INTEGER
        MAX-ACCESS read-only
        STATUS current
        DESCRIPTION " vlan virtual interface index "
        ::= { hwDhcpToL3IfEntry 1 }

    hwDhcpToL3GroupId OBJECT-TYPE
        SYNTAX  INTEGER  (0..19)
        MAX-ACCESS read-write
        STATUS current
        DESCRIPTION " DHCP group id for this vlan virtual interface"
        ::= { hwDhcpToL3IfEntry 2 }

    hwDhcpToL3AddressCheck OBJECT-TYPE
        SYNTAX  INTEGER
        {
            enabled(1),
            disabled(2)
        }
        MAX-ACCESS read-write
        STATUS current
        DESCRIPTION " If dhcp security check enabled for this vlan virtual interface "
        ::= { hwDhcpToL3IfEntry 3 }

    hwDhcpToL3RowStatus OBJECT-TYPE
        SYNTAX  RowStatus
        MAX-ACCESS read-create
        STATUS current
        DESCRIPTION " status of this table's entry.     "
        ::= { hwDhcpToL3IfEntry 4 }
END
