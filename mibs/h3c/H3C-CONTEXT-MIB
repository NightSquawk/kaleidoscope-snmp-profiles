-- ===========================================================================================================
-- Copyright (c) 2004-2014 Hangzhou H3C Technologies. Co., Ltd. All rights reserved.
--
-- Description: context MIB
-- Reference:
-- Version: V1.0
-- History:
-- revision 1.0 2014-3-18 created by c08124
--
-- ============================================================================================================
H3C-CONTEXT-MIB DEFINITIONS ::= BEGIN

IMPORTS
    h3cCommon
        FROM HUAWEI-3COM-OID-MIB
    Integer32, OBJECT-TYPE, MODULE-IDENTITY, NOTIFICATION-TYPE
        FROM SNMPv2-SMI
    DisplayString
        FROM SNMPv2-TC;

h3cContext MODULE-IDENTITY
    LAST-UPDATED "201403180000Z"
    ORGANIZATION
        "Hangzhou H3C Technologies. Co., Ltd."
    CONTACT-INFO
        "Platform Team Hangzhou H3C Technologies. Co., Ltd.
        Haidian District Beijing P.R. China
        http://www.h3c.com
        Zip:100085"
    DESCRIPTION
        "This MIB contains objects for managing context operations."

    REVISION "201403180000Z"
    DESCRIPTION
        "Initial revision of this MIB module."
    ::= { h3cCommon 154 }

h3cContextTables OBJECT IDENTIFIER ::= { h3cContext 1 }

h3cContextControl OBJECT IDENTIFIER ::= { h3cContextTables 1 }


h3cContextControlTable OBJECT-TYPE
    SYNTAX SEQUENCE OF H3cContextControlEntry
    MAX-ACCESS not-accessible
    STATUS current
    DESCRIPTION
        "This table is used to configure contexts for a device and
         show context status info."
    ::= { h3cContextControl 1 }


h3cContextControlEntry OBJECT-TYPE
    SYNTAX H3cContextControlEntry
    MAX-ACCESS not-accessible
    STATUS current
    DESCRIPTION
        "An entry of the h3cContextControlTable.
         Each entry corresponds to one context."
    INDEX { h3cContextIndex }
    ::= { h3cContextControlTable 1 }

H3cContextControlEntry ::=
    SEQUENCE
        {
            h3cContextIndex
                Integer32,
            h3cContextName
                DisplayString
        }

h3cContextIndex OBJECT-TYPE
    SYNTAX Integer32 (1..2147483647)
    MAX-ACCESS accessible-for-notify
    STATUS current
    DESCRIPTION
        "The value range of Context ID depends on the device model."
    ::= { h3cContextControlEntry 1 }


h3cContextName OBJECT-TYPE
    SYNTAX DisplayString (SIZE (1..15))
    MAX-ACCESS read-only
    STATUS current
    DESCRIPTION
        "Specifies the context name,
         a case-sensitive string of 1 to 15 characters.
         The context name cannot be modified once created."
    ::= { h3cContextControlEntry 2 }


h3cContextNotification OBJECT IDENTIFIER ::= { h3cContext 8 }

h3cContextNotificationObjects OBJECT IDENTIFIER ::= { h3cContextNotification 0 }

h3cContextStateChangeToActive NOTIFICATION-TYPE
    OBJECTS {h3cContextIndex, h3cContextName}
    STATUS current
    DESCRIPTION
        "The h3cContextStateChangeToActive trap indicates
         that the context status has changed to active."
    ::= { h3cContextNotificationObjects 1 }

h3cContextStateChangeToInactive NOTIFICATION-TYPE
    OBJECTS {h3cContextIndex, h3cContextName}
    STATUS current
    DESCRIPTION
        "The h3cContextStateChangeToInactive trap indicates
         that the context status has changed to inactive."
    ::= { h3cContextNotificationObjects 2 }

END
