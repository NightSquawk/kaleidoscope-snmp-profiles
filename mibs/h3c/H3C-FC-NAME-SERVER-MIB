-- =====================================================================
-- Copyright (c) 2004-2014 Hangzhou H3C Tech. Co., Ltd. All rights reserved.
--
-- Description:
--      This MIB module is intended for the management of Fibre Channel (FC)
--      Name Server.
-- Reference:
-- Version: V1.0
-- History:
--   V1.0 Initial version
--        created by qiaoxinghua 2014-03-03
-- =====================================================================
H3C-FC-NAME-SERVER-MIB DEFINITIONS ::= BEGIN

IMPORTS
    h3cSan, h3cVsanIndex
        FROM H3C-VSAN-MIB
    H3cFcNameId
        FROM H3C-FC-TC-MIB
    OBJECT-TYPE, MODULE-IDENTITY, NOTIFICATION-TYPE
        FROM SNMPv2-SMI
    TruthValue
        FROM SNMPv2-TC;

h3cFcNameServer MODULE-IDENTITY
    LAST-UPDATED "201403031018Z"    -- March 03, 2014 at 10:18 GMT
    ORGANIZATION
        "Hangzhou H3C Tech. Co., Ltd."
    CONTACT-INFO
        "Platform Team Hangzhou H3C Tech. Co., Ltd.
         Hai-Dian District Beijing P.R. China
         http://www.h3c.com
         Zip:100085"
    DESCRIPTION
        "This MIB module is intended for the management of Fibre Channel (FC)
         Name Server."
    REVISION "201403031018Z"
    DESCRIPTION
        "Initial version of this MIB module."
    ::= { h3cSan 10 }

-- Node definitions
h3cFcNameServerMibObjects OBJECT IDENTIFIER ::= { h3cFcNameServer 1 }

-- FC Name Server Notifications
h3cFcNsNotification OBJECT IDENTIFIER ::= { h3cFcNameServerMibObjects 1 }

h3cFcNsNotificationPrefix   OBJECT IDENTIFIER ::= { h3cFcNsNotification 0 }
h3cFcNsNotificationSwitch   OBJECT IDENTIFIER ::= { h3cFcNsNotification 1 }
h3cFcNsObjsForNotification  OBJECT IDENTIFIER ::= { h3cFcNsNotification 2 }

h3cFcNsPortLoginNotify NOTIFICATION-TYPE
    OBJECTS    { h3cVsanIndex,
                 h3cFcNsLocalSwitchWWN,
                 h3cFcNsFloginPortWWN }
    STATUS     current
    DESCRIPTION
    "This notification will be generated when an entry is added to the
     Name Server database by Nx_Port locally logging in."
    ::= { h3cFcNsNotificationPrefix 1 }

h3cFcNsPortLogoutNotify NOTIFICATION-TYPE
    OBJECTS    { h3cVsanIndex,
                 h3cFcNsLocalSwitchWWN,
                 h3cFcNsFloginPortWWN }
    STATUS     current
    DESCRIPTION
    "This notification will be generated when an entry is deleted from
     the Name Server database by Nx_Port locally logging out."
    ::= { h3cFcNsNotificationPrefix 2 }

h3cFcNsPortLoginNotifyEnable OBJECT-TYPE
    SYNTAX     TruthValue
    MAX-ACCESS read-write
    STATUS     current
    DESCRIPTION
    "This object is used to determine whether h3cFcNsPortLoginNotify
     will be generated for Nx_Port locally logging in."
    ::= { h3cFcNsNotificationSwitch 1 }

h3cFcNsPortLogoutNotifyEnable OBJECT-TYPE
    SYNTAX     TruthValue
    MAX-ACCESS read-write
    STATUS     current
    DESCRIPTION
    "This object is used to determine whether h3cFcNsPortLogoutNotify
     will be generated for Nx_Port locally logging out."
    ::= { h3cFcNsNotificationSwitch 2 }

h3cFcNsLocalSwitchWWN OBJECT-TYPE
    SYNTAX     H3cFcNameId
    MAX-ACCESS accessible-for-notify
    STATUS     current
    DESCRIPTION
        "The world wide name of the local switch."
    ::= { h3cFcNsObjsForNotification 1 }

h3cFcNsFloginPortWWN OBJECT-TYPE
    SYNTAX     H3cFcNameId
    MAX-ACCESS accessible-for-notify
    STATUS     current
    DESCRIPTION
        "The world wide name of the local logged-in Nx_Port."
    ::= { h3cFcNsObjsForNotification 2 }

END
