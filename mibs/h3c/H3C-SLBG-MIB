-- =====================================================================
-- Copyright (c) 2004-2013 Hangzhou H3C Tech. Co., Ltd.  All rights reserved.
-- Description: Service loopback group MIB.
-- Reference:
-- Version: V1.0
-- History:
-- V1.0 Initial version
-- =====================================================================
H3C-SLBG-MIB DEFINITIONS ::= BEGIN

IMPORTS
    Unsigned32, OBJECT-TYPE, MODULE-IDENTITY
        FROM SNMPv2-SMI
    RowStatus
        FROM SNMPv2-TC
    InterfaceIndex
        FROM IF-MIB
    h3cCommon
        FROM HUAWEI-3COM-OID-MIB;

h3cSlbg MODULE-IDENTITY
    LAST-UPDATED "201210160000Z"
    ORGANIZATION
        "Hangzhou H3C Tech. Co., Ltd."
    CONTACT-INFO
        "Platform Team Hangzhou H3C Tech. Co., Ltd.
        Hai-Dian District Beijing P.R. China
        http://www.h3c.com
        Zip: 100085"
    DESCRIPTION
        "Service loopback group MIB."
    REVISION "201210160000Z"
    DESCRIPTION
        "The initial revision of this MIB module."
    ::= { h3cCommon 130 }

---------------------------------------------------------------
-- Node definitions
---------------------------------------------------------------

h3cSlbgMibTable OBJECT IDENTIFIER ::= { h3cSlbg 1 }

h3cSlbgGroupTable OBJECT-TYPE
    SYNTAX SEQUENCE OF H3cSlbgGroupEntry
    MAX-ACCESS not-accessible
    STATUS current
    DESCRIPTION
        "A table of service loopback group objects."
    ::= { h3cSlbgMibTable 1 }

h3cSlbgGroupEntry OBJECT-TYPE
    SYNTAX H3cSlbgGroupEntry
    MAX-ACCESS not-accessible
    STATUS current
    DESCRIPTION
        "The service loopback group entry."
    INDEX { h3cSlbgGroupNumber }
    ::= { h3cSlbgGroupTable 1 }

H3cSlbgGroupEntry ::=
    SEQUENCE {
        h3cSlbgGroupNumber
            Unsigned32,
        h3cSlbgGroupSrvType
            BITS,
        h3cSlbgGroupRowStatus
            RowStatus
     }

h3cSlbgGroupNumber OBJECT-TYPE
    SYNTAX Unsigned32
    MAX-ACCESS not-accessible
    STATUS current
    DESCRIPTION
        "Serial number of the service loopback group."
    ::= { h3cSlbgGroupEntry 1 }

h3cSlbgGroupSrvType OBJECT-TYPE
    SYNTAX BITS
        {
            ipv6(0),
            ipv6mc(1),
            tunnel(2),
            multicastTunnel(3),
            mpls(4)
        }
    MAX-ACCESS read-create
    STATUS current
    DESCRIPTION
        "Service type of the service loopback group.
         ipv6: IPv6 unicast service type.
         ipv6mc: IPv6 multicast service type.
         tunnel: Unicast tunnel service type.
         multicastTunnel: Multicast tunnel service type.
         mpls: MPLS service type."
    ::= { h3cSlbgGroupEntry 2 }

h3cSlbgGroupRowStatus OBJECT-TYPE
    SYNTAX      RowStatus
    MAX-ACCESS  read-create
    STATUS      current
    DESCRIPTION
        "This object is used to create, modify, or delete rows.
         h3cSlbgGroupNumber and h3cSlbgGroupSrvType must have a valid value before a row can be activated."
    ::= { h3cSlbgGroupEntry 3 }

h3cSlbgPortTable OBJECT-TYPE
    SYNTAX SEQUENCE OF H3cSlbgPortEntry
    MAX-ACCESS not-accessible
    STATUS current
    DESCRIPTION
        "A table of port objects."
    ::= { h3cSlbgMibTable 2 }

h3cSlbgPortEntry OBJECT-TYPE
    SYNTAX H3cSlbgPortEntry
    MAX-ACCESS not-accessible
    STATUS current
    DESCRIPTION
        "The service loopback group port entry."
    INDEX { h3cSlbgPortIndex }
    ::= { h3cSlbgPortTable 1 }

H3cSlbgPortEntry ::=
    SEQUENCE {
        h3cSlbgPortIndex
            InterfaceIndex,
        h3cSlbgPortAttachedGroupNumber
            Unsigned32,
        h3cSlbgPortSelectedGroupNumber
            Unsigned32
    }

h3cSlbgPortIndex OBJECT-TYPE
    SYNTAX InterfaceIndex
    MAX-ACCESS not-accessible
    STATUS current
    DESCRIPTION
        "Interface index of the port, which is defined in RFC1213 (MIB-II)."
    ::= { h3cSlbgPortEntry 1 }

h3cSlbgPortAttachedGroupNumber OBJECT-TYPE
    SYNTAX Unsigned32
    MAX-ACCESS read-write
    STATUS current
    DESCRIPTION
        "The value of the service group number to which this port is assigned.
         The value is zero if the port is not assigned to any service loopback group."
    ::= { h3cSlbgPortEntry 2 }

h3cSlbgPortSelectedGroupNumber OBJECT-TYPE
    SYNTAX Unsigned32
    MAX-ACCESS read-only
    STATUS current
    DESCRIPTION
        "The value of the service group number to which this selected port is assigned.
         The value is zero if the port is not selected or not assigned to any service loopback group."
    ::= { h3cSlbgPortEntry 3 }

END
