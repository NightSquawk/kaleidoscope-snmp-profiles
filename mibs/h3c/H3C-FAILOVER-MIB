-- ============================================================================
-- Copyright (c) 2004-2015 Hangzhou H3C Tech. Co., Ltd. All rights reserved.
--
-- Description: FAILOVER GROUP MIB
-- Reference:
-- Version: V1.0
-- History:
-- revision 1.0 2015-10-27 created by j03525
--
-- ============================================================================
H3C-FAILOVER-MIB DEFINITIONS ::= BEGIN

IMPORTS
    h3cCommon
        FROM HUAWEI-3COM-OID-MIB
    Integer32, Unsigned32, OBJECT-TYPE, MODULE-IDENTITY, NOTIFICATION-TYPE
        FROM SNMPv2-SMI
    DisplayString, RowStatus
        FROM SNMPv2-TC;

h3cFailover MODULE-IDENTITY
    LAST-UPDATED "201510271040Z"
    ORGANIZATION
        "Hangzhou H3C Tech. Co., Ltd."
    CONTACT-INFO
        "Platform Team Hangzhou H3C Tech. Co., Ltd.
        Hai-Dian District Beijing P.R. China
        http://www.h3c.com
        Zip:100085"
    DESCRIPTION
        "This MIB file is to provide the definition of failover group.

        Such as:
        1. Configure Failover Groups for a device and display Failover Groups
           and their status.
        2. Assign CPU to the Failover Group, and display their status.

        Failover Group: A failover group contains a primary node and a secondary node.
        When a failover group is referenced by a service module, the primary node
        processes services and backs up service data to the secondary node.
        The secondary node does not process services, but it takes over the services
        when the primary node fails.
        When the primary node is recovered, traffic is switched to the primary node again."
    REVISION "201510271040Z"
    DESCRIPTION
        "The initial revision of this MIB module."
    ::= { h3cCommon 164 }


-- Node definitions

h3cFailoverScalarObjects OBJECT IDENTIFIER ::= { h3cFailover 1 }

h3cFailoverMaxNum OBJECT-TYPE
    SYNTAX Unsigned32
    MAX-ACCESS read-only
    STATUS current
    DESCRIPTION
        "The maximum number of Failover groups which the system supported to create, does not include the AutoBackup."
    ::= { h3cFailoverScalarObjects 1 }


h3cFailoverCurrentNum OBJECT-TYPE
    SYNTAX Unsigned32
    MAX-ACCESS read-only
    STATUS current
    DESCRIPTION
        "The current number of Failover groups which the system has created, does not include the AutoBackup."
    ::= { h3cFailoverScalarObjects 2 }


h3cFailoverTables OBJECT IDENTIFIER ::= { h3cFailover 2 }

h3cFailoverCfgTable OBJECT-TYPE
    SYNTAX SEQUENCE OF H3cFailoverCfgEntry
    MAX-ACCESS not-accessible
    STATUS current
    DESCRIPTION
        "This table is for configuration of backup group."
    ::= { h3cFailoverTables 1 }


h3cFailoverCfgEntry OBJECT-TYPE
    SYNTAX H3cFailoverCfgEntry
    MAX-ACCESS not-accessible
    STATUS current
    DESCRIPTION
        "An entry of the h3cFailoverGroupCfgTable."
    INDEX { h3cFailoverIndex }
    ::= { h3cFailoverCfgTable 1 }


H3cFailoverCfgEntry ::=
    SEQUENCE
    {
        h3cFailoverIndex
            Unsigned32,
        h3cFailoverName
            DisplayString,
        h3cFailoverPrimaryChassisID
            Integer32,
        h3cFailoverPrimarySlotID
            Integer32,
        h3cFailoverPrimaryCpuID
            Integer32,
        h3cFailoverSecondaryChassisID
            Integer32,
        h3cFailoverSecondarySlotID
            Integer32,
        h3cFailoverSecondaryCpuID
            Integer32,
        h3cFailoverState
            INTEGER,
        h3cFailoverRowStatus
            RowStatus
    }

h3cFailoverIndex OBJECT-TYPE
    SYNTAX Unsigned32 (0..4294967295)
    MAX-ACCESS accessible-for-notify
    STATUS current
    DESCRIPTION
        "Failover group ID is used as group index, the value range of failover group ID
        depends on the device model.
        The failover GroupIndex cannot be modified after creation."
    ::= { h3cFailoverCfgEntry 1 }


h3cFailoverName OBJECT-TYPE
    SYNTAX DisplayString (SIZE (1..63))
    MAX-ACCESS read-create
    STATUS current
    DESCRIPTION
        "Specifies the backup group name, a case-sensitive string of 1 to 63 characters.
        The failover group name cannot be modified after creation.
        The name can not include '?', and can not begin or end with ' '."
    ::= { h3cFailoverCfgEntry 2 }


h3cFailoverPrimaryChassisID OBJECT-TYPE
    SYNTAX Integer32 (-1..255)
    MAX-ACCESS read-create
    STATUS current
    DESCRIPTION
        "Specifies a card on an IRF member device.  The chassis-number argument represents
        the member ID of the IRF member device.  (Distributed devices In IRF mode.)
        On a centralized or distributed device, the value for this node is always zero.
        Note:The -1 for delete the node."
    ::= { h3cFailoverCfgEntry 3 }


h3cFailoverPrimarySlotID OBJECT-TYPE
    SYNTAX Integer32 (-1..255)
    MAX-ACCESS read-create
    STATUS current
    DESCRIPTION
        "Specifies a card by its slot number.  (Distributed devices In standalone mode.)
        Note:The -1 for delete the node."
    ::= { h3cFailoverCfgEntry 4 }


h3cFailoverPrimaryCpuID OBJECT-TYPE
    SYNTAX Integer32 (-1..7)
    MAX-ACCESS read-create
    STATUS current
    DESCRIPTION
        "Specifies a CPU by its number.  This option is available only if multiple CPUs
        are available on the specified slot.
        Note:The -1 for delete the node."
    ::= { h3cFailoverCfgEntry 5 }


h3cFailoverSecondaryChassisID OBJECT-TYPE
    SYNTAX Integer32 (-1..255)
    MAX-ACCESS read-create
    STATUS current
    DESCRIPTION
        "Specifies a card on an IRF member device.  The chassis-number argument represents
        the member ID of the IRF member device.  (Distributed devices In IRF mode.)
        On a centralized or distributed device, the value for this node is always zero.
        Note:The -1 for delete the node."
    ::= { h3cFailoverCfgEntry 6 }


h3cFailoverSecondarySlotID OBJECT-TYPE
    SYNTAX Integer32 (-1..255)
    MAX-ACCESS read-create
    STATUS current
    DESCRIPTION
        "Specifies a card by its slot number.  (Distributed devices In standalone mode.)
        Note:The -1 for delete the node."
    ::= { h3cFailoverCfgEntry 7 }


h3cFailoverSecondaryCpuID OBJECT-TYPE
    SYNTAX Integer32 (-1..7)
    MAX-ACCESS read-create
    STATUS current
    DESCRIPTION
        "Specifies a CPU by its number.  This option is available only if multiple CPUs
        are available on the specified slot.
        Note:The -1 for delete the node."
    ::= { h3cFailoverCfgEntry 8 }


h3cFailoverState OBJECT-TYPE
    SYNTAX INTEGER
        {
            initial(1),
            normal(2),
            fault(3)
        }
    MAX-ACCESS read-only
    STATUS current
    DESCRIPTION
        "Backup group state:
        Initial: No node in the failover group is processing services.
        Normal: The primary node is processing services.
        Fault: The secondary node is processing services."
    ::= { h3cFailoverCfgEntry 9 }


h3cFailoverRowStatus OBJECT-TYPE
    SYNTAX RowStatus
    MAX-ACCESS read-create
    STATUS current
    DESCRIPTION
        "The status of this table entry.
        Only support active(1), createAndGo(4) and destroy(6)."
    ::= { h3cFailoverCfgEntry 10 }

--
-- Notification definitions
--
-- =================================================================
-- Traps are defined below.
h3cFailoverNotification OBJECT IDENTIFIER ::= { h3cFailover 3 }

-- All objects used for TRAP only are defined here.
h3cFailoverTrap OBJECT IDENTIFIER ::= { h3cFailoverNotification 0 }

h3cFailoverCreate  NOTIFICATION-TYPE
    OBJECTS
        {
            h3cFailoverIndex,
            h3cFailoverName
        }

    STATUS current
    DESCRIPTION
        "The h3cFailoverCreate trap indicates that the failover group has created."
    ::= { h3cFailoverTrap 1 }

h3cFailoverDelete  NOTIFICATION-TYPE
    OBJECTS
        {
            h3cFailoverIndex,
            h3cFailoverName
        }
    STATUS current
    DESCRIPTION
        "The h3cFailoverDelete trap indicates that the failover group has deleted."
    ::= { h3cFailoverTrap 2 }

h3cFailoverPrimaryNodeAdd  NOTIFICATION-TYPE
    OBJECTS
        {
            h3cFailoverIndex,
            h3cFailoverName,
            h3cFailoverPrimaryChassisID,
            h3cFailoverPrimarySlotID,
            h3cFailoverPrimaryCpuID
        }
    STATUS current
    DESCRIPTION
        "The h3cFailoverPrimaryNodeAdd trap indicates that the failover group has
        added the primary node."
    ::= { h3cFailoverTrap 3 }

h3cFailoverPrimaryNodeRemove  NOTIFICATION-TYPE
    OBJECTS
        {
            h3cFailoverIndex,
            h3cFailoverName,
            h3cFailoverPrimaryChassisID,
            h3cFailoverPrimarySlotID,
            h3cFailoverPrimaryCpuID
        }
    STATUS current
    DESCRIPTION
        "The h3cFailoverPrimaryNodeRemove trap indicates that the failover group has
        removed the primary node."
    ::= { h3cFailoverTrap 4 }

h3cFailoverSecondaryNodeAdd  NOTIFICATION-TYPE
    OBJECTS
        {
            h3cFailoverIndex,
            h3cFailoverName,
            h3cFailoverSecondaryChassisID,
            h3cFailoverSecondarySlotID,
            h3cFailoverSecondaryCpuID
        }
    STATUS current
    DESCRIPTION
        "The h3cFailoverSecondaryNodeAdd trap indicates that the failover group has
        added the secondary node."
    ::= { h3cFailoverTrap 5 }

h3cFailoverSecondaryNodeRemove  NOTIFICATION-TYPE
    OBJECTS
        {
            h3cFailoverIndex,
            h3cFailoverName,
            h3cFailoverSecondaryChassisID,
            h3cFailoverSecondarySlotID,
            h3cFailoverSecondaryCpuID
        }
    STATUS current
    DESCRIPTION
        "The h3cFailoverSecondaryNodeRemove trap indicates that the failover group has
        removed the secondary node."
    ::= { h3cFailoverTrap 6 }

END
