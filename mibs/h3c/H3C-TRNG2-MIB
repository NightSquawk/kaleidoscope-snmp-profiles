-- =====================================================================
-- Copyright (c) 2004-2013 Hangzhou H3C Tech. Co., Ltd.  All rights reserved.
--
-- Description: Timerange MIB Definition
-- Reference:
-- Version: V1.1
-- History:
-- V1.0 xujunjie,2012-05-14,Initial Version.
-- V1.1 modified by MouXuanli
--     Change name "trng" to "trange".
-- =====================================================================
H3C-TRNG2-MIB DEFINITIONS ::= BEGIN
IMPORTS
    h3cCommon
        FROM HUAWEI-3COM-OID-MIB
    Integer32, OBJECT-TYPE, MODULE-IDENTITY
        FROM SNMPv2-SMI
    TruthValue, DateAndTime, RowStatus
        FROM SNMPv2-TC;

h3cTRNG2 MODULE-IDENTITY
    LAST-UPDATED "201303080000Z"        -- Mar 8, 2013 at 00:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "The H3C-TRNG2-MIB contains objects to
        Configure the system absolute and periodic time-range."
    REVISION "201303080000Z"        -- Mar 8, 2013 at 00:00 GMT
    DESCRIPTION
        "Modified to change node name from 'trng' to 'trange'."
    REVISION "201205140000Z"        -- May 14, 2012 at 00:00 GMT
    DESCRIPTION
        "201205140000Z, --The initial revision of this MIB module."
    ::= { h3cCommon 121 }

--
-- Node definitions
--

h3cTRNG2MibObjects OBJECT IDENTIFIER ::= { h3cTRNG2 1 }

-- h3cTrangeCreateTimerangeTable

h3cTrangeCreateTimerangeTable OBJECT-TYPE
    SYNTAX SEQUENCE OF H3cTrangeCreateTimerangeEntry
    MAX-ACCESS not-accessible
    STATUS current
    DESCRIPTION
        "Creat TimeRange."
    ::= { h3cTRNG2MibObjects 1 }

h3cTrangeCreateTimerangeEntry OBJECT-TYPE
    SYNTAX H3cTrangeCreateTimerangeEntry
    MAX-ACCESS not-accessible
    STATUS current
    DESCRIPTION
        "Define the entry of h3cTrangeCreateTimerangeTable"
    INDEX { h3cTrangeIndex }
    ::= { h3cTrangeCreateTimerangeTable 1 }

H3cTrangeCreateTimerangeEntry ::=
    SEQUENCE {
        h3cTrangeIndex
            Integer32,
        h3cTrangeName
            OCTET STRING,
        h3cTrangeValidFlag
            TruthValue,
        h3cTrangeCreateRowStatus
            RowStatus
     }

h3cTrangeIndex OBJECT-TYPE
    SYNTAX Integer32 (0..2147483647)
    MAX-ACCESS not-accessible
    STATUS current
    DESCRIPTION
        "TimeRange's index"
    ::= { h3cTrangeCreateTimerangeEntry 1 }

h3cTrangeName OBJECT-TYPE
    SYNTAX OCTET STRING (SIZE (1..32))
    MAX-ACCESS read-create
    STATUS current
    DESCRIPTION
        "TimeRange's name"
    ::= { h3cTrangeCreateTimerangeEntry 2 }

h3cTrangeValidFlag OBJECT-TYPE
    SYNTAX TruthValue
    MAX-ACCESS read-only
    STATUS current
    DESCRIPTION
        "Valid or Invalid flag"
    ::= { h3cTrangeCreateTimerangeEntry 3 }

h3cTrangeCreateRowStatus OBJECT-TYPE
    SYNTAX RowStatus
    MAX-ACCESS read-create
    STATUS current
    DESCRIPTION
        "The status of this conceptual row.Now only realize CreateAndGo and Destroy and Active."
    ::= { h3cTrangeCreateTimerangeEntry 4 }

-- h3cTrangeAbsoluteTable

h3cTrangeAbsoluteTable OBJECT-TYPE
    SYNTAX SEQUENCE OF H3cTrangeAbsoluteEntry
    MAX-ACCESS not-accessible
    STATUS current
    DESCRIPTION
        "Creat absoluteness time item of the TimeRange"
    ::= { h3cTRNG2MibObjects 2 }

h3cTrangeAbsoluteEntry OBJECT-TYPE
    SYNTAX H3cTrangeAbsoluteEntry
    MAX-ACCESS not-accessible
    STATUS current
    DESCRIPTION
        "Define the entry of h3cTrangeAbsoluteTable"
    INDEX { h3cTrangeAbsoluteNameIndex, h3cTrangeAbsoluteSubIndex }
    ::= { h3cTrangeAbsoluteTable 1 }

H3cTrangeAbsoluteEntry ::=
    SEQUENCE {
        h3cTrangeAbsoluteNameIndex
            Integer32,
        h3cTrangeAbsoluteSubIndex
            Integer32,
        h3cTrangeAbsoluteStartTime
            DateAndTime,
        h3cTrangeAbsoluteEndTime
            DateAndTime,
        h3cTrangeAbsolueRowStatus
            RowStatus
     }

h3cTrangeAbsoluteNameIndex OBJECT-TYPE
    SYNTAX Integer32 (0..2147483647)
    MAX-ACCESS not-accessible
    STATUS current
    DESCRIPTION
        "TimeRange's index"
    ::= { h3cTrangeAbsoluteEntry 1 }

h3cTrangeAbsoluteSubIndex OBJECT-TYPE
    SYNTAX Integer32 (1..12)
    MAX-ACCESS not-accessible
    STATUS current
    DESCRIPTION
        "SubItem's index"
    ::= { h3cTrangeAbsoluteEntry 2 }

h3cTrangeAbsoluteStartTime OBJECT-TYPE
    SYNTAX DateAndTime
    MAX-ACCESS read-create
    STATUS current
    DESCRIPTION
        "Start point of the timerange.The format defined like 'YYYY-MM-DD,hh:mm:0.0'."
    ::= { h3cTrangeAbsoluteEntry 3 }

h3cTrangeAbsoluteEndTime OBJECT-TYPE
    SYNTAX DateAndTime
    MAX-ACCESS read-create
    STATUS current
    DESCRIPTION
        "End point of the timerange.The format defined like 'YYYY-MM-DD,hh:mm:0.0'."
    ::= { h3cTrangeAbsoluteEntry 4 }

h3cTrangeAbsolueRowStatus OBJECT-TYPE
    SYNTAX RowStatus
    MAX-ACCESS read-create
    STATUS current
    DESCRIPTION
        "The status of this conceptual row. Now only realize CreateAndGo and Destroy and Active."
    ::= { h3cTrangeAbsoluteEntry 5 }

-- h3cTrangePeriodicTable

h3cTrangePeriodicTable OBJECT-TYPE
    SYNTAX SEQUENCE OF H3cTrangePeriodicEntry
    MAX-ACCESS not-accessible
    STATUS current
    DESCRIPTION
        "Creat periodic time item of the TimeRange"
    ::= { h3cTRNG2MibObjects 3 }

h3cTrangePeriodicEntry OBJECT-TYPE
    SYNTAX H3cTrangePeriodicEntry
    MAX-ACCESS not-accessible
    STATUS current
    DESCRIPTION
        "Define the index of h3cTrangePeriodicTable"
    INDEX { h3cTrangePeriodicNameIndex, h3cTrangePeriodicSubIndex }
    ::= { h3cTrangePeriodicTable 1 }

H3cTrangePeriodicEntry ::=
    SEQUENCE {
        h3cTrangePeriodicNameIndex
            Integer32,
        h3cTrangePeriodicSubIndex
            Integer32,
        h3cTrangePeriodicDayOfWeek
            BITS,
        h3cTrangePeriodicStartTime
            DateAndTime,
        h3cTrangePeriodicEndTime
            DateAndTime,
        h3cTrangePeriodicRowStatus
            RowStatus
     }

h3cTrangePeriodicNameIndex OBJECT-TYPE
    SYNTAX Integer32 (0..2147483647)
    MAX-ACCESS not-accessible
    STATUS current
    DESCRIPTION
        "TimeRange's index"
    ::= { h3cTrangePeriodicEntry 1 }

h3cTrangePeriodicSubIndex OBJECT-TYPE
    SYNTAX Integer32 (1..32)
    MAX-ACCESS not-accessible
    STATUS current
    DESCRIPTION
        "SubItem's index"
    ::= { h3cTrangePeriodicEntry 2 }

h3cTrangePeriodicDayOfWeek OBJECT-TYPE
    SYNTAX BITS {
                    sunday(0),
                    monday(1),
                    tuesday(2),
                    wednesday(3),
                    thursday(4),
                    friday(5),
                    saturday(6)
                }
    MAX-ACCESS read-create
    STATUS current
    DESCRIPTION
        "The day of week. This is a bit-map of possible conditions.
        The various bit positions are:
        |0        |sunday                 |
        |1        |monday                 |
        |2        |tuesday                |
        |3        |wednesday              |
        |4        |thursday               |
        |5        |friday                 |
        |6        |saturday               |
        "
    ::= { h3cTrangePeriodicEntry 3 }

h3cTrangePeriodicStartTime OBJECT-TYPE
    SYNTAX DateAndTime
    MAX-ACCESS read-create
    STATUS current
    DESCRIPTION
        "Start point of this timerange,The format defined like 'hh:mm:0,0'."
    ::= { h3cTrangePeriodicEntry 4 }

h3cTrangePeriodicEndTime OBJECT-TYPE
    SYNTAX DateAndTime
    MAX-ACCESS read-create
    STATUS current
    DESCRIPTION
        "End point of this timerange. The format definedlike 'hh:mm:0,0'."
    ::= { h3cTrangePeriodicEntry 5 }

h3cTrangePeriodicRowStatus OBJECT-TYPE
    SYNTAX RowStatus
    MAX-ACCESS read-create
    STATUS current
    DESCRIPTION
        "The status of this conceptual row, Now only realize CreateAndGo and Destroy and Active."
    ::= { h3cTrangePeriodicEntry 6 }

END
