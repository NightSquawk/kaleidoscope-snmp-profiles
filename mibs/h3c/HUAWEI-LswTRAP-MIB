-- ==================================================================
-- Copyright (c) 2004-2017 Hangzhou H3C Tech. Co., Ltd. All rights reserved.
--
-- Description: Lan Switch trap MIB
-- Reference:
-- Version: V1.5
-- History:
-- V1.0 Created by Zhangshilin, 2001.06.29
-- V1.1 Modified by lifengguang 2008.11.10, add trap node hwBootImageUpdated
-- V1.2 2011-11-26 updated by duyanbing
--      Add hwDevMFirstTrapTime to powerfailure and hwPowerNormal.
-- V1.3 2012-04-26 updated by wangcong
--      Added hwNetworkHealthMonitorFailure, hwNetworkHealthMonitorNormal for reserving.
-- V1.4 2013-03-08 updated by fangliwen
--      Added hwCpuRemoved, hwCpuFailure, hwCpuNormal.
--      2014-08-02 updated by fangliwen
--      Added hwPowerIncompatible.
-- V1.5 2016-12-21 updated by yanfang
--      Add hwCpuUsageSevereNotification
--          hwCpuUsageSevereRecoverNotification
--          hwCpuUsageMinorNotification
--          hwCpuUsageMinorRecoverNotification.
--          hwMemoryUsageEarlyWarningNotification
--          hwMemoryUsageEarlyWarningRecoverNotification
--          hwMemoryUsageMinorNotification
--          hwMemoryUsageMinorRecoverNotification
--          hwMemoryUsageSevereNotification
--          hwMemoryUsageSevereRecoverNotification
--          hwMemoryUsageCriticalNotification
--          hwMemoryUsageCriticalRecoverNotification.
--      2017-06-23 updated by wangweihui
--      Add hwCoreUsageNotification
--      2017-07-17 updated by fangliwen
--      Add hwBoardPowerNotEnough, hwAvailablePower and hwRequiredPower.
--      2017-12-5 updated by yuhaiyan
--      Add hwAlarmInPortIn
--          hwAlarmInPortRecover
-- ==================================================================

-- ==================================================================
--
-- Variables and types be imported
--
-- ==================================================================
HUAWEI-LswTRAP-MIB DEFINITIONS ::= BEGIN
IMPORTS
    MODULE-IDENTITY, NOTIFICATION-TYPE, OBJECT-TYPE, Unsigned32
        FROM SNMPv2-SMI
    lswCommon
        FROM HUAWEI-3COM-OID-MIB
    SnmpAdminString
        FROM SNMP-FRAMEWORK-MIB
    hwDevMPowerNum, hwDevMFanNum, hwDevMFirstTrapTime
        FROM HUAWEI-LswDEVM-MIB
    hwLswFrameIndex, hwLswSlotIndex, hwLswSubslotIndex, hwLswCpuIndex, hwLswCoreIndex, hwLswCoreThreshold
        FROM HUAWEI-LSW-DEV-ADM-MIB;

-- ==================================================================
--
-- ======================= definition begin =========================
--
-- ==================================================================

    hwsLswTrapMib MODULE-IDENTITY
            LAST-UPDATED "201712050000Z"
            ORGANIZATION
                "Hangzhou H3C Tech. Co., Ltd."
            CONTACT-INFO
                "Platform Team Hangzhou H3C Tech. Co., Ltd.
                Hai-Dian District Beijing P.R. China
                http://www.h3c.com
                Zip:100085
                "
            DESCRIPTION
            ""
            REVISION "201712050000Z"
            DESCRIPTION
            "Added hwAlarmInPortIn,  hwAlarmInPortRecover."
            REVISION "201707170000Z"
            DESCRIPTION
            "Added hwBoardPowerNotEnough, hwAvailablePower and hwRequiredPower."
            REVISION "201706240000Z"
            DESCRIPTION
            "hwCoreUsageNotification.
             Add hwsLswTRAPMibObjectV2Prefix for bindings of notification."
            REVISION "201701120000Z"
            DESCRIPTION
            "Add hwCpuUsageSevereNotification
             hwCpuUsageSevereRecoverNotification
             hwCpuUsageMinorNotification
             hwCpuUsageMinorRecoverNotification.
             hwMemoryUsageEarlyWarningNotification
             hwMemoryUsageEarlyWarningRecoverNotification
             hwMemoryUsageMinorNotification
             hwMemoryUsageMinorRecoverNotification
             hwMemoryUsageSevereNotification
             hwMemoryUsageSevereRecoverNotification
             hwMemoryUsageCriticalNotification
             hwMemoryUsageCriticalRecoverNotification.
             Add hwsLswTRAPMibInfor for bindings of notification."
            REVISION "201111260000Z"
            DESCRIPTION
            ""
            ::= { lswCommon 12 }

-- ==================================================================
--
-- lsw trap object
--
-- ==================================================================
    hwsLswTRAPMibObject OBJECT IDENTIFIER ::= { hwsLswTrapMib 1 }

    powerfailure NOTIFICATION-TYPE
      OBJECTS { hwDevMPowerNum, hwDevMFirstTrapTime }
      STATUS  current
      DESCRIPTION
              "Power supply failure"
      ::= { hwsLswTRAPMibObject 1 }

    hwPowerNormal NOTIFICATION-TYPE
      OBJECTS { hwDevMPowerNum, hwDevMFirstTrapTime }
      STATUS  current
      DESCRIPTION
              "Power supply normal"
      ::= { hwsLswTRAPMibObject 2 }

    hwMasterPowerNormal NOTIFICATION-TYPE
      OBJECTS { hwDevMPowerNum }
      STATUS  current
      DESCRIPTION
              "Master power supply normal"
      ::= { hwsLswTRAPMibObject 3 }

    hwSlavePowerNormal NOTIFICATION-TYPE
      OBJECTS { hwDevMPowerNum }
      STATUS  current
      DESCRIPTION
              "Slave power supply normal"
      ::= { hwsLswTRAPMibObject 4 }

    hwPowerRemoved NOTIFICATION-TYPE
      OBJECTS { hwDevMPowerNum }
      STATUS  current
      DESCRIPTION
              "Power removed"
      ::= { hwsLswTRAPMibObject 5 }

    fanfailure NOTIFICATION-TYPE
      OBJECTS { hwDevMFanNum }
      STATUS  current
      DESCRIPTION
              "Fan failure"
      ::= { hwsLswTRAPMibObject 6 }

    hwFanNormal NOTIFICATION-TYPE
      OBJECTS { hwDevMFanNum }
      STATUS  current
      DESCRIPTION
              "Fan normal"
      ::= { hwsLswTRAPMibObject 7 }

    hwBoardRemoved NOTIFICATION-TYPE
      OBJECTS { hwLswFrameIndex, hwLswSlotIndex }
      STATUS  current
      DESCRIPTION
              "Board removed"
      ::= { hwsLswTRAPMibObject 8 }

    hwBoardInserted NOTIFICATION-TYPE
      OBJECTS { hwLswFrameIndex,hwLswSlotIndex }
      STATUS  current
      DESCRIPTION
              "Board inserted"
      ::= { hwsLswTRAPMibObject 9 }

    hwBoardFailure NOTIFICATION-TYPE
      OBJECTS { hwLswFrameIndex, hwLswSlotIndex }
      STATUS  current
      DESCRIPTION
              "Board failed"
      ::= { hwsLswTRAPMibObject 10 }

    hwBoardNormal NOTIFICATION-TYPE
      OBJECTS { hwLswFrameIndex, hwLswSlotIndex }
      STATUS  current
      DESCRIPTION
              "Board normal"
      ::= { hwsLswTRAPMibObject 11 }

    hwSubcardRemove NOTIFICATION-TYPE
      OBJECTS { hwLswFrameIndex, hwLswSlotIndex, hwLswSubslotIndex }
      STATUS  current
      DESCRIPTION
              "Sub card removed"
      ::= { hwsLswTRAPMibObject 12 }

    hwSubcardInsert NOTIFICATION-TYPE
      OBJECTS { hwLswFrameIndex, hwLswSlotIndex, hwLswSubslotIndex }
      STATUS  current
      DESCRIPTION
              "Sub card inserted"
      ::= { hwsLswTRAPMibObject 13 }

    hwBoaardTemperatureLower NOTIFICATION-TYPE
      OBJECTS { hwLswFrameIndex, hwLswSlotIndex }
      STATUS  current
      DESCRIPTION
              "Board temperature low"
      ::= { hwsLswTRAPMibObject 14 }

    hwBoaardTemperatureFromLowerToNormal NOTIFICATION-TYPE
      OBJECTS { hwLswFrameIndex, hwLswSlotIndex }
      STATUS  current
      DESCRIPTION
              "Board temperature form lower to normal"
      ::= { hwsLswTRAPMibObject 15 }

    hwBoaardTemperatureHigher NOTIFICATION-TYPE
      OBJECTS { hwLswFrameIndex, hwLswSlotIndex }
      STATUS  current
      DESCRIPTION
              "Board temperature high"
      ::= { hwsLswTRAPMibObject 16 }

    hwBoaardTemperatureFormHigherToNormal NOTIFICATION-TYPE
      OBJECTS { hwLswFrameIndex, hwLswSlotIndex }
      STATUS  current
      DESCRIPTION
              "Board temperature from higher to normal"
      ::= { hwsLswTRAPMibObject 17 }

    hwRequestLoading NOTIFICATION-TYPE
      OBJECTS { hwLswFrameIndex, hwLswSlotIndex }
      STATUS  current
      DESCRIPTION
              "Board request load"
      ::= { hwsLswTRAPMibObject 18 }

    hwLoadFailure NOTIFICATION-TYPE
      OBJECTS { hwLswFrameIndex, hwLswSlotIndex }
      STATUS  current
      DESCRIPTION
              "Board load failure"
      ::= { hwsLswTRAPMibObject 19 }

    hwLoadFinished NOTIFICATION-TYPE
      OBJECTS { hwLswFrameIndex, hwLswSlotIndex }
      STATUS  current
      DESCRIPTION
              "Board load finished"
      ::= { hwsLswTRAPMibObject 20 }

    hwBackBoardModeSetFuilure NOTIFICATION-TYPE
      OBJECTS { hwLswFrameIndex }
      STATUS  current
      DESCRIPTION
              "Back board mode set failure"
      ::= { hwsLswTRAPMibObject 21 }

    hwBackBoardModeSetOK NOTIFICATION-TYPE
      OBJECTS { hwLswFrameIndex }
      STATUS  current
      DESCRIPTION
              "Back board mode set OK"
      ::= { hwsLswTRAPMibObject 22 }

    hwPowerInserted NOTIFICATION-TYPE
      OBJECTS { hwDevMPowerNum }
      STATUS  current
      DESCRIPTION
              "Power inserted"
      ::= { hwsLswTRAPMibObject 23 }

    hwBootImageUpdated NOTIFICATION-TYPE
      OBJECTS { hwLswFrameIndex, hwLswSlotIndex }
      STATUS  current
      DESCRIPTION
              "This trap node indicates that the boot image of specified board
              is updated."
      ::= { hwsLswTRAPMibObject 24 }

    hwCpuRemoved NOTIFICATION-TYPE
      OBJECTS { hwLswFrameIndex, hwLswSlotIndex, hwLswCpuIndex }
      STATUS  current
      DESCRIPTION
              "Node removed"
      ::= { hwsLswTRAPMibObject 25 }

    hwCpuFailure NOTIFICATION-TYPE
      OBJECTS { hwLswFrameIndex, hwLswSlotIndex, hwLswCpuIndex }
      STATUS  current
      DESCRIPTION
              "Node failed"
      ::= { hwsLswTRAPMibObject 26 }

    hwCpuNormal NOTIFICATION-TYPE
      OBJECTS { hwLswFrameIndex, hwLswSlotIndex, hwLswCpuIndex }
      STATUS  current
      DESCRIPTION
              "Node normal"
      ::= { hwsLswTRAPMibObject 27 }

      hwPowerIncompatible NOTIFICATION-TYPE
      OBJECTS { hwDevMPowerNum}
      STATUS  current
      DESCRIPTION
              "Power module is incompatible with the device"
      ::= { hwsLswTRAPMibObject 28 }

      hwCpuUsageSevereNotification NOTIFICATION-TYPE
      OBJECTS {
            hwLswFrameIndex,
            hwLswSlotIndex,
            hwLswCpuIndex,
            hwLswCpuRatio,
            hwLswCpuUsageMinorThreshold,
            hwLswCpuUsageSevereThreshold,
            hwLswCpuUsageRecoverThreshold,
            hwsLswTrapCpuCoreInfo,
            hwsLswTrapProcessCpuInfo
            }
      STATUS current
      DESCRIPTION
            "The trap indicates that the CPU usage increased to or above
             the hwLswCpuUsageSevereThreshold."
      ::= { hwsLswTRAPMibObject 29 }

      hwCpuUsageSevereRecoverNotification NOTIFICATION-TYPE
      OBJECTS {
            hwLswFrameIndex,
            hwLswSlotIndex,
            hwLswCpuIndex,
            hwLswCpuRatio,
            hwLswCpuUsageMinorThreshold,
            hwLswCpuUsageSevereThreshold,
            hwLswCpuUsageRecoverThreshold,
            hwsLswTrapCpuCoreInfo,
            hwsLswTrapProcessCpuInfo
            }
      STATUS current
      DESCRIPTION
            "
            When the product not supports hwLswCpuUsageRecoverThreshold,
            the trap indicates that the CPU usage decreased to or below
            the hwLswCpuUsageSevereThreshold.
            When the product supports hwLswCpuUsageRecoverThreshold,
            the trap indicates that the CPU usage decreased to or below
            the hwLswCpuUsageMinorThreshold.
            "
      ::= { hwsLswTRAPMibObject 30 }

      hwCpuUsageMinorNotification NOTIFICATION-TYPE
      OBJECTS {
            hwLswFrameIndex,
            hwLswSlotIndex,
            hwLswCpuIndex,
            hwLswCpuRatio,
            hwLswCpuUsageMinorThreshold,
            hwLswCpuUsageSevereThreshold,
            hwLswCpuUsageRecoverThreshold,
            hwsLswTrapCpuCoreInfo,
            hwsLswTrapProcessCpuInfo
            }
      STATUS current
      DESCRIPTION
            "The trap indicates that the CPU usage increased to or above
             the hwLswCpuUsageMinorThreshold."
      ::= { hwsLswTRAPMibObject 31 }

      hwCpuUsageMinorRecoverNotification NOTIFICATION-TYPE
      OBJECTS {
            hwLswFrameIndex,
            hwLswSlotIndex,
            hwLswCpuIndex,
            hwLswCpuRatio,
            hwLswCpuUsageMinorThreshold,
            hwLswCpuUsageSevereThreshold,
            hwLswCpuUsageRecoverThreshold,
            hwsLswTrapCpuCoreInfo,
            hwsLswTrapProcessCpuInfo
            }
      STATUS current
      DESCRIPTION
            "
            When the product not supports hwLswCpuUsageRecoverThreshold,
            the trap indicates that the CPU usage decreased to or below
            the hwLswCpuUsageMinorThreshold.
            When the product supports hwLswCpuUsageRecoverThreshold,
            the trap indicates that the CPU usage decreased to or below
            the hwLswCpuUsageRecoverThreshold.
            "
      ::= { hwsLswTRAPMibObject 32 }

      hwMemoryUsageEarlyWarningNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory decreased to or below
            the hwMemoryUsageEarlyWarningThreshold."
      ::= { hwsLswTRAPMibObject 33 }

      hwMemoryUsageEarlyWarningRecoverNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory usage increased to or above
             the hwMemoryUsageSecureThreshold."
      ::= { hwsLswTRAPMibObject 34 }

      hwMemoryUsageMinorNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory decreased to or below
            the hwLswCpuMemoryMinorThreshold."
      ::= { hwsLswTRAPMibObject 35 }

      hwMemoryUsageMinorRecoverNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory usage increased to or above
             the hwLswCpuMemoryNormalThreshold."
      ::= { hwsLswTRAPMibObject 36 }

      hwMemoryUsageSevereNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory decreased to or below
             the hwMemoryUsageSevereThreshold."
      ::= { hwsLswTRAPMibObject 37 }

      hwMemoryUsageSevereRecoverNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory usage increased to or above
            the hwMemoryUsageMinorThreshold."
      ::= { hwsLswTRAPMibObject 38 }

      hwMemoryUsageCriticalNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory decreased to or below
             the hwMemoryUsageCriticalThreshold."
      ::= { hwsLswTRAPMibObject 39 }

      hwMemoryUsageCriticalRecoverNotification NOTIFICATION-TYPE
      OBJECTS {
            hwLswFrameIndex,
            hwLswSlotIndex,
            hwLswCpuIndex,
            hwLswCpuMemory,
            hwLswCpuMemoryFree,
            hwLswCpuMemoryFreeRatio,
            hwLswCpuMemoryHighTotal,
            hwLswCpuMemoryHighFree,
            hwLswCpuMemoryLowTotal,
            hwLswCpuMemoryLowFree,
            hwLswCpuMemorySecureThreshold,
            hwLswCpuMemoryEarlyWarningThreshold,
            hwLswCpuMemoryNormalThreshold,
            hwLswCpuMemoryMinorThreshold,
            hwLswCpuMemorySevereThreshold,
            hwLswCpuMemoryCriticalThreshold,
            hwLswCpuMemoryCurrentState,
            hwsLswTrapProcessMemoryInfo,
            hwsLswTrapSlubInfo
            }
      STATUS current
      DESCRIPTION
            "The trap indicates that the amount of free memory usage increased to or above
             the hwMemoryUsageSevereThreshold."
      ::= { hwsLswTRAPMibObject 40 }

    hwNetworkHealthMonitorFailure OBJECT IDENTIFIER ::= { hwsLswTRAPMibObject 98 }
    hwNetworkHealthMonitorNormal OBJECT IDENTIFIER ::= { hwsLswTRAPMibObject 99 }

-- ==================================================================
--
-- lsw trap info
--
-- ==================================================================
   hwsLswTRAPMibInfor OBJECT IDENTIFIER ::= { hwsLswTrapMib 2 }

   hwsLswTrapCpuCoreInfo OBJECT-TYPE
        SYNTAX      SnmpAdminString (SIZE (0..255))
        MAX-ACCESS  accessible-for-notify
        STATUS      current
        DESCRIPTION
            "hwLswCpuCoreIndex,hwLswCpuCoreUsage,hwLswCpuCoreUsr,
             hwLswCpuCoreSys,hwLswCpuCoreIrq,hwLswCpuCoreIdle.

            Each line contains the following comma-separated values:

            hwLswCpuCoreIndex(Integer32):CPU core index.
            hwLswCpuCoreUsage(Unsigned32): Percentage of CPU core usage ,0~100
            hwLswCpuCoreUsr(Unsigned32): Percentage of CPU core user usage ,0~100
            hwLswCpuCoreSys(Unsigned32): Percentage of CPU core system usage ,0~100
            hwLswCpuCoreIrq(Unsigned32): Percentage of CPU core interrupt usage ,0~100
            hwLswCpuCoreIdle(Unsigned32): Percentage of CPU core idle usage ,0~100
            "
        ::= { hwsLswTRAPMibInfor 1}

   hwsLswTrapProcessCpuInfo OBJECT-TYPE
        SYNTAX      SnmpAdminString (SIZE (0..255))
        MAX-ACCESS  accessible-for-notify
        STATUS      current
        DESCRIPTION
            "hwLswProcessJobId,hwLswProcessPid,hwLswProcessName,
            hwLswProcessState,hwLswProcessPriority,hwLswProcessFDs,
            hwLswProcessRunTime,hwLswProcessCpuRatio5Secs,hwLswProcessCpuRatio1Min,
            hwLswProcessCpuRatio5Mins.

            Each line contains the following comma-separated values:

            hwLswProcessName: Process name
            hwLswProcessJobId:Job ID
            hwLswProcessPid: Process ID
            hwLswProcessPriority: Process priority
            hwLswProcessState: Process state
                {
                R(1):running,
                S(2):sleeping,
                T(3):tracedorStopped,
                D(4):uninterruptibleSleep,
                Z(5):zombie
                }
            hwLswProcessFDs: Process FDs
            hwLswProcessRunTime: Process run time
            hwLswProcessCpuRatio: CPU ratio for the process.
            "
        ::= { hwsLswTRAPMibInfor 2 }

   hwsLswTrapProcessMemoryInfo OBJECT-TYPE
        SYNTAX      SnmpAdminString (SIZE (0..255))
        MAX-ACCESS  accessible-for-notify
        STATUS      current
        DESCRIPTION
            "hwLswProcessJobId,hwLswProcessName,hwLswProcessMemoryUsed.

            Each line contains the following comma-separated values:

            hwLswProcessJobId: Job ID
            hwLswProcessName: Process name
            hwLswProcessMemoryUsed:
            Memory be used by the process(text + data + stack + dynamic)in KB.
            "
        ::= { hwsLswTRAPMibInfor 3 }

   hwsLswTrapSlubInfo OBJECT-TYPE
        SYNTAX      SnmpAdminString (SIZE (0..255))
        MAX-ACCESS  accessible-for-notify
        STATUS      current
        DESCRIPTION
            "hwLswSlubInfoUsed + hwLswSlubInfoName.

            Each line contains the following comma-separated values:

            hwLswSlubInfoName: Name of slubinfo
            hwLswSlubInfoUsed: Memory be used by the slub(num*size)
            "
        ::= { hwsLswTRAPMibInfor 4 }

    hwLswTrapCpuUsage OBJECT-TYPE
        SYNTAX      SnmpAdminString (SIZE (0..255))
        MAX-ACCESS  accessible-for-notify
        STATUS      current
        DESCRIPTION
            "Cpu usage in 5sec 1min 5min."
        ::= { hwsLswTRAPMibInfor 5 }

    hwLswTrapCoreProcessInfo OBJECT-TYPE
        SYNTAX      SnmpAdminString (SIZE (0..255))
        MAX-ACCESS  accessible-for-notify
        STATUS      current
        DESCRIPTION
            "
            Each line contains the following values:
            JID PID PPID CPU State Memory 5Sec 1Min 5Min Name.
            "
        ::= { hwsLswTRAPMibInfor 6 }

    hwLswCoreTrapUsage   OBJECT-TYPE
        SYNTAX     Unsigned32
        MAX-ACCESS     accessible-for-notify
        STATUS     current
        DESCRIPTION
            "Core usage in last 30 minutes."
        ::= {hwsLswTRAPMibInfor 7}

    hwBoardAvailablePower OBJECT-TYPE
        SYNTAX      Integer32
        MAX-ACCESS  accessible-for-notify
        STATUS      current
        DESCRIPTION
            "Available power of power supply."
        ::= { hwsLswTRAPMibInfor 8 }

    hwBoardRequiredPower OBJECT-TYPE
        SYNTAX      Integer32
        MAX-ACCESS  accessible-for-notify
        STATUS      current
        DESCRIPTION
            "Power required for a single board."
        ::= { hwsLswTRAPMibInfor 9 }

    hwsLswTRAPMibObjectV2 OBJECT IDENTIFIER ::= { hwsLswTrapMib 3 }
    hwsLswTRAPMibObjectV2Prefix OBJECT IDENTIFIER ::= { hwsLswTRAPMibObjectV2 0 }

    hwCoreUsageNotification NOTIFICATION-TYPE
      OBJECTS {
            hwLswFrameIndex,
            hwLswSlotIndex,
            hwLswCpuIndex,
            hwLswCoreIndex,
            hwLswCoreTrapUsage,
            hwLswCoreThreshold,
            hwLswTrapCpuUsage,
            hwLswTrapCoreProcessInfo
            }
      STATUS current
      DESCRIPTION
            "The trap indicates that the amount of core usage increased to or above
             the hwLswCoreThreshold."
      ::= { hwsLswTRAPMibObjectV2Prefix 1 }

    hwBoardPowerNotEnough NOTIFICATION-TYPE
      OBJECTS { hwLswFrameIndex, hwLswSlotIndex, hwBoardAvailablePower, hwBoardRequiredPower}
      STATUS  current
      DESCRIPTION
              "Not enough power for the board."
      ::= { hwsLswTRAPMibObjectV2Prefix 2 }

    hwAlarmInPortIn NOTIFICATION-TYPE
        OBJECTS { hwLswFrameIndex, hwLswSlotIndex }
        STATUS current
        DESCRIPTION
            "Alarm reported on the alarm-in port."
        ::= { hwsLswTRAPMibObjectV2Prefix 3 }

    hwAlarmInPortRecover NOTIFICATION-TYPE
        OBJECTS { hwLswFrameIndex, hwLswSlotIndex }
        STATUS current
        DESCRIPTION
            "Alarm removed on the alarm-in port."
        ::= { hwsLswTRAPMibObjectV2Prefix 4 }

END
