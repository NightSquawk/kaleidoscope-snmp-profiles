-- ============================================================================
-- Copyright (c) 2004-2014 Hangzhou H3C Tech. Co., Ltd. All rights reserved.
--
-- Description: This MIB is used for configuration of OBJP(object policy).
-- Reference:
-- Version: V1.0
-- History:
-- V1.0 created by gaoyu.
-- ============================================================================
H3C-OBJP-MIB DEFINITIONS ::= BEGIN

IMPORTS
    h3cCommon
        FROM  HUAWEI-3COM-OID-MIB
    OBJECT-TYPE, MODULE-IDENTITY,
    Unsigned32, Counter64
        FROM SNMPv2-SMI;

--
-- Node definitions
--

h3cObjp MODULE-IDENTITY
    LAST-UPDATED "201403101536Z"        -- Mar 10, 2014 at 15:36 GMT
    ORGANIZATION
        "Hangzhou H3C Technologies Co., Ltd."
    CONTACT-INFO
        "Platform Team Hangzhou H3C Technologies Co., Ltd.
        Hai-Dian District Beijing P.R. China
        http://www.h3c.com
        Zip:100085
        "
    DESCRIPTION
        "Object-policy management information base for managing devices
        that support object policy.
        "
    REVISION "201403101536Z"            -- Mar 10, 2014 at 15:36 GMT
    DESCRIPTION
        "The initial revision of this MIB module."
    ::= { h3cCommon 155 }

--
-- Nodes of h3cObjpZonePairObjects
--
h3cObjpZonePairObjects OBJECT IDENTIFIER ::= { h3cObjp 1 }

--
-- Nodes of h3cObjpZonePairRunningInfoTable
--
h3cObjpZonePairRunningInfoTable OBJECT-TYPE
    SYNTAX SEQUENCE OF H3cObjpZonePairRunningInfoEntry
    MAX-ACCESS not-accessible
    STATUS current
    DESCRIPTION
        "Object policy of zone pair running information base."
    ::= { h3cObjpZonePairObjects 1 }

h3cObjpZonePairRunningInfoEntry OBJECT-TYPE
    SYNTAX H3cObjpZonePairRunningInfoEntry
    MAX-ACCESS not-accessible
    STATUS current
    DESCRIPTION
        "Object policy of zone pair running information entry."
    INDEX
    {
        h3cObjpZonePairSrcZone,
        h3cObjpZonePairDstZone,
        h3cObjpZonePairIPVersion,
        h3cObjpZonePairRuleID
    }
    ::= { h3cObjpZonePairRunningInfoTable 1 }

H3cObjpZonePairRunningInfoEntry ::=
    SEQUENCE
    {
        h3cObjpZonePairSrcZone
            OCTET STRING,
        h3cObjpZonePairDstZone
            OCTET STRING,
        h3cObjpZonePairIPVersion
            INTEGER,
        h3cObjpZonePairRuleID
            Unsigned32,
        h3cObjpZonePairMatchPacketCount
            Counter64,
        h3cObjpZonePairLastMatchTime
            Unsigned32
    }

h3cObjpZonePairSrcZone OBJECT-TYPE
    SYNTAX OCTET STRING (SIZE(1..31))
    MAX-ACCESS not-accessible
    STATUS current
    DESCRIPTION
        "Name of the source security zone."
    ::= { h3cObjpZonePairRunningInfoEntry 1 }

h3cObjpZonePairDstZone OBJECT-TYPE
    SYNTAX OCTET STRING (SIZE(1..31))
    MAX-ACCESS not-accessible
    STATUS current
    DESCRIPTION
        "Name of the destination security zone."
    ::= { h3cObjpZonePairRunningInfoEntry 2 }

h3cObjpZonePairIPVersion OBJECT-TYPE
    SYNTAX INTEGER
    {
        ipv4(1),
        ipv6(2)
    }
    MAX-ACCESS not-accessible
    STATUS current
    DESCRIPTION
        "IP protocol version."
    ::= { h3cObjpZonePairRunningInfoEntry 3 }

h3cObjpZonePairRuleID OBJECT-TYPE
    SYNTAX Unsigned32 (0..65534)
    MAX-ACCESS not-accessible
    STATUS current
    DESCRIPTION
        "Rule ID of object policy."
    ::= { h3cObjpZonePairRunningInfoEntry 4 }

h3cObjpZonePairMatchPacketCount OBJECT-TYPE
    SYNTAX Counter64
    MAX-ACCESS read-only
    STATUS current
    DESCRIPTION
        "Number of packets matching the rule."
    ::= { h3cObjpZonePairRunningInfoEntry 5 }

h3cObjpZonePairLastMatchTime OBJECT-TYPE
    SYNTAX Unsigned32
    MAX-ACCESS read-only
    STATUS current
    DESCRIPTION
        "Interval in seconds between the last match and 1970/1/1 00:00:00."
    ::= { h3cObjpZonePairRunningInfoEntry 6 }

END
