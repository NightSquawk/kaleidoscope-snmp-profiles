-- ==================================================================
-- Copyright (C) 2002 by  H3C TECHNOLOGIES. All rights reserved.
-- 
-- Description: Rmon alarm Information MIB
-- Reference:
-- Version: V1.1
-- History:
--(1) Created by Qizhenglin, 2002.8.15
-- V1.1 2004-10-12 updated by gaolong
--      Change MAX-ACCESS to ACCESS.
--      Change current to mandatory.
-- ==================================================================

-- ==================================================================
-- 
-- Varibles and types be imported
--
-- ==================================================================

HUAWEI-LswSMON-MIB DEFINITIONS ::= BEGIN

              IMPORTS
                  OBJECT-TYPE
                      FROM RFC-1212
                  huaweiMgmt,huaweiDatacomm
                      FROM HUAWEI-3COM-OID-MIB;

-- ==================================================================
--
-- ======================= definition begin =========================
--
-- ==================================================================

hwSmonExtend         OBJECT IDENTIFIER ::= { huaweiDatacomm 26 }

smonExtendObject        OBJECT IDENTIFIER ::= { hwSmonExtend 1 }

 
hwdot1qVlanStatNumber OBJECT-TYPE
     SYNTAX  INTEGER
     ACCESS  read-only
     STATUS  mandatory
     DESCRIPTION
         "The number of vlans that can collect statistics of packets."
     ::= { smonExtendObject 1 }
     
-- ==================================================================
--
-- VLAN statistics status table (for SMON)
--
-- ==================================================================
 hwdot1qVlanStatStatusTable OBJECT-TYPE
     SYNTAX     SEQUENCE OF Hwdot1qVlanStatStatusEntry
     ACCESS     not-accessible
     STATUS     mandatory
     DESCRIPTION
         "VLAN statistics status table."
     ::= { smonExtendObject 2 }

 hwdot1qVlanStatStatusEntry OBJECT-TYPE
     SYNTAX     Hwdot1qVlanStatStatusEntry
     ACCESS	not-accessible
     STATUS     mandatory
     DESCRIPTION
         " VLAN statistics status table entry."
     INDEX { hwdot1qVlanStatEnableIndex }
     ::= { hwdot1qVlanStatStatusTable 1 }

      
    Hwdot1qVlanStatStatusEntry ::= SEQUENCE {
        hwdot1qVlanStatEnableIndex                INTEGER,
        hwdot1qVlanStatEnableStatus               INTEGER
    }
        
        
    hwdot1qVlanStatEnableIndex  OBJECT-TYPE
        SYNTAX     INTEGER
        ACCESS 	    read-only
        STATUS      mandatory
        DESCRIPTION
        "Vlan index ."
        ::= { hwdot1qVlanStatStatusEntry 1 }  
        
    hwdot1qVlanStatEnableStatus  OBJECT-TYPE
        SYNTAX     INTEGER
        {
            enabled(1),
            disabled(2)
        }
        ACCESS read-write
        STATUS      mandatory
        DESCRIPTION
        "VLAN Statistics Status.It represent the current VLAN supports statistic or not."
        ::= { hwdot1qVlanStatStatusEntry 2 } 

   END
