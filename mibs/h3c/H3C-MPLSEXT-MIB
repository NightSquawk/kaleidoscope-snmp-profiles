-- =============================================================================
-- Copyright (c) 2004-2017 Hangzhou H3C Tech. Co., Ltd. All rights reserved.
--
-- Description: Multiprotocol Label Switching MIB
-- Reference:
-- Version: V1.3
-- History:
--   V1.0 2013-06-13 Initial version Created by Neng Yan
--   V1.1 2014-12-17 Modified by Neng Yan, Added h3cMplsExtBfdTable
--   V1.2 2015-06-16 Modified by Li Yun, Added h3cMplsExtVpnStatsTable
--   V1.3 2017-02-17 Modified by Liu Qingye, Added h3cMplsExtVpnTable
-- =============================================================================
H3C-MPLSEXT-MIB DEFINITIONS ::= BEGIN
IMPORTS
    MODULE-IDENTITY, OBJECT-TYPE, Unsigned32
        FROM SNMPv2-SMI
    RowStatus, TruthValue, DisplayString
        FROM SNMPv2-TC
    InetAddressType,InetAddress
        FROM INET-ADDRESS-MIB
    InterfaceIndexOrZero
        FROM IF-MIB
    h3cCommon
        FROM HUAWEI-3COM-OID-MIB
    Counter64
        FROM SNMPv2-SMI
    ;

-- =============================================================================
-- module identity part
-- =============================================================================
h3cMplsExt MODULE-IDENTITY
    LAST-UPDATED
        "201702171800Z"   -- Feb 17, 2017 at 18:00 GMT
    ORGANIZATION
        "Hangzhou H3C Technologies Co., Ltd."
    CONTACT-INFO
        "Platform Team Hangzhou H3C Technologies Co., Ltd.
         Hai-Dian District Beijing P.R. China
         http://www.h3c.com
         Zip:100085"
    DESCRIPTION
        "Multiprotocol Label Switching MIB"
    REVISION
        "201702171800Z"   -- Feb 17, 2017 at 18:00 GMT
    DESCRIPTION
        "Added h3cMplsExtVpnTable."
    REVISION
        "201506161800Z"   -- Jun 16, 2015 at 18:00 GMT
    DESCRIPTION
        "Added h3cMplsExtVpnStatsTable."
    REVISION
        "201412171200Z"   -- Dec 17, 2014 at 18:00 GMT
    DESCRIPTION
        "Added h3cMplsExtBfdTable."
    REVISION
        "201306131800Z"   -- Jan 13, 2013 at 18:00 GMT
    DESCRIPTION
        "Initial version of this MIB."
    ::= { h3cCommon 142 }

-- =============================================================================
-- object definition begin
-- =============================================================================
h3cMplsExtObjects      OBJECT IDENTIFIER ::= { h3cMplsExt 1 }

h3cMplsExtScalarGroup  OBJECT IDENTIFIER ::= { h3cMplsExtObjects 1 }

h3cMplsExtLsrID    OBJECT-TYPE
    SYNTAX      OCTET STRING (SIZE (0..32))
    MAX-ACCESS  read-write
    STATUS      current
    DESCRIPTION
        "The Label Switching Router's Identifier."
    ::= { h3cMplsExtScalarGroup 1 }

h3cMplsExtLdpStatus    OBJECT-TYPE
    SYNTAX      TruthValue
    MAX-ACCESS  read-write
    STATUS      current
    DESCRIPTION
        "The global configuration of Label Distribution Protocol(LDP)."
    ::= { h3cMplsExtScalarGroup 2 }

-- =============================================================================
-- h3cMplsExtTable Definition
-- =============================================================================
h3cMplsExtTable  OBJECT-TYPE
    SYNTAX      SEQUENCE OF H3cMplsExtEntry
    MAX-ACCESS  not-accessible
    STATUS      current
    DESCRIPTION
        "A table for configuring
        Multiprotocol Label Switching(MPLS) parameters."
    ::= { h3cMplsExtObjects 2 }

h3cMplsExtEntry   OBJECT-TYPE
    SYNTAX      H3cMplsExtEntry
    MAX-ACCESS  not-accessible
    STATUS      current
    DESCRIPTION
        "An entry for configuring MPLS parameters."
    INDEX
    {
        h3cMplsExtIndex
    }
    ::= { h3cMplsExtTable 1 }

H3cMplsExtEntry ::=
    SEQUENCE
    {
        h3cMplsExtIndex               Unsigned32,
        h3cMplsExtCapability          TruthValue,
        h3cMplsExtMtu                 Unsigned32,
        h3cMplsExtRowStatus           RowStatus
    }

h3cMplsExtIndex   OBJECT-TYPE
    SYNTAX      Unsigned32(1..4294967295)
    MAX-ACCESS  not-accessible
    STATUS      current
    DESCRIPTION
        "Index of MPLS interface."
    ::= { h3cMplsExtEntry 1 }

h3cMplsExtCapability    OBJECT-TYPE
    SYNTAX      TruthValue
    MAX-ACCESS  read-create
    STATUS      current
    DESCRIPTION
        "The MPLS capability of an interface."
    DEFVAL { false }
    ::= { h3cMplsExtEntry 2 }

h3cMplsExtMtu     OBJECT-TYPE
    SYNTAX      Unsigned32(46..65535)
    MAX-ACCESS  read-create
    STATUS      current
    DESCRIPTION
        "The MPLS Maximum Transmission Unit(MTU) of an interface."
    ::= { h3cMplsExtEntry 3 }

h3cMplsExtRowStatus     OBJECT-TYPE
    SYNTAX      RowStatus
    MAX-ACCESS  read-create
    STATUS      current
    DESCRIPTION
        "Operation status of this table entry."
    ::= { h3cMplsExtEntry 4 }
-- =============================================================================
-- End of h3cMplsExtTable Definition
-- =============================================================================

-- =============================================================================
-- h3cMplsExtLdpTable Definition
-- =============================================================================
h3cMplsExtLdpTable     OBJECT-TYPE
    SYNTAX      SEQUENCE OF H3cMplsExtLdpEntry
    MAX-ACCESS  not-accessible
    STATUS      current
    DESCRIPTION
        "A table for configuring LDP parameters."
    ::= { h3cMplsExtObjects 3 }

h3cMplsExtLdpEntry     OBJECT-TYPE
    SYNTAX      H3cMplsExtLdpEntry
    MAX-ACCESS  not-accessible
    STATUS      current
    DESCRIPTION
        "An entry for configuring LDP parameters."
    INDEX
    {
        h3cMplsExtLdpIndex
    }
    ::= { h3cMplsExtLdpTable 1 }

H3cMplsExtLdpEntry ::=
    SEQUENCE
    {
        h3cMplsExtLdpIndex                 Unsigned32,
        h3cMplsExtLdpCapability            TruthValue,
        h3cMplsExtLdpRowStatus             RowStatus
    }

h3cMplsExtLdpIndex     OBJECT-TYPE
    SYNTAX      Unsigned32(1..4294967295)
    MAX-ACCESS  not-accessible
    STATUS      current
    DESCRIPTION
        "Index of LDP interface."
    ::= { h3cMplsExtLdpEntry 1 }

h3cMplsExtLdpCapability    OBJECT-TYPE
    SYNTAX      TruthValue
    MAX-ACCESS  read-create
    STATUS      current
    DESCRIPTION
        "The LDP capability of an interface."
    DEFVAL { false }
    ::= { h3cMplsExtLdpEntry 2 }

h3cMplsExtLdpRowStatus     OBJECT-TYPE
    SYNTAX      RowStatus
    MAX-ACCESS  read-create
    STATUS      current
    DESCRIPTION
        "Operation status of this table entry.  A row entry cannot
        be modified when the value of this object is 'active'."
    ::= { h3cMplsExtLdpEntry 3 }
-- =============================================================================
-- End of h3cMplsExtLdpTable Definition
-- =============================================================================

-- =============================================================================
-- h3cMplsExtBfdTable Definition
-- =============================================================================
h3cMplsExtBfdTable  OBJECT-TYPE
    SYNTAX      SEQUENCE OF H3cMplsExtBfdEntry
    MAX-ACCESS  not-accessible
    STATUS      current
    DESCRIPTION
        "A table of MPLS Bidirectional Forwarding Detection(BFD) sessions."
    ::= { h3cMplsExtObjects 4 }

h3cMplsExtBfdEntry   OBJECT-TYPE
    SYNTAX      H3cMplsExtBfdEntry
    MAX-ACCESS  not-accessible
    STATUS      current
    DESCRIPTION
        "An entry in this table represents information on a single session."
    INDEX
    {
        h3cMplsExtBfdLocalDiscr
    }
    ::= { h3cMplsExtBfdTable 1 }

H3cMplsExtBfdEntry ::=
    SEQUENCE
    {
        h3cMplsExtBfdLocalDiscr            Unsigned32,
        h3cMplsExtBfdType                  INTEGER,
        h3cMplsExtBfdBindIfIndex           InterfaceIndexOrZero,
        h3cMplsExtBfdBindIfName            DisplayString,
        h3cMplsExtBfdXcIndex               OCTET STRING,
        h3cMplsExtBfdPwBackupFlag          INTEGER,
        h3cMplsExtBfdPwId                  Unsigned32,
        h3cMplsExtBfdVsiIndex              Unsigned32,
        h3cMplsExtBfdPwPeerIpType          InetAddressType,
        h3cMplsExtBfdPwPeerIp              InetAddress,
        h3cMplsExtBfdPwSPE                 INTEGER,
        h3cMplsExtBfdPwEncapType           INTEGER
    }

h3cMplsExtBfdLocalDiscr   OBJECT-TYPE
    SYNTAX      Unsigned32(1..4294967295)
    MAX-ACCESS  not-accessible
    STATUS      current
    DESCRIPTION
        "The local discriminator of the BFD session."
    ::= { h3cMplsExtBfdEntry 1 }

h3cMplsExtBfdType    OBJECT-TYPE
    SYNTAX      INTEGER {
                        unknown(1),
                        lsp(2),
                        vpwsPw(3),
                        vplsPw(4),
                        te(5)
                     }
    MAX-ACCESS  read-only
    STATUS      current
    DESCRIPTION
        "The type of the BFD session."
    ::= { h3cMplsExtBfdEntry 2 }

h3cMplsExtBfdBindIfIndex   OBJECT-TYPE
    SYNTAX      InterfaceIndexOrZero
    MAX-ACCESS  read-only
    STATUS      current
    DESCRIPTION
        "This object displays tunnel interface index when the value of
         h3cMplsExtBfdType is te(5), and displays interface index of
         an Attachment Circuit(AC) which is bound to a Pseudowire(PW) when
         the value of h3cMplsExtBfdType is vpwsPw(3).  This object is
         invalid when the value of h3cMplsExtBfdType is not te(5) or
         vpwsPw(3), then this object contains a zero value."
    ::= { h3cMplsExtBfdEntry 3 }

h3cMplsExtBfdBindIfName   OBJECT-TYPE
    SYNTAX      DisplayString (SIZE (0..255))
    MAX-ACCESS  read-only
    STATUS      current
    DESCRIPTION
        "This object displays tunnel interface name when the value of
         h3cMplsExtBfdType is te(5), and displays interface name of
         an AC which is bound to a PW when the value of h3cMplsExtBfdType
         is vpwsPw(3).  This object is invalid when the value of
         h3cMplsExtBfdType is not te(5) or vpwsPw(3), then this object
         contains a zero-length string."
    ::= { h3cMplsExtBfdEntry 4 }

h3cMplsExtBfdXcIndex   OBJECT-TYPE
    SYNTAX      OCTET STRING (SIZE (0..24))
    MAX-ACCESS  read-only
    STATUS      current
    DESCRIPTION
        "Primary index for MplsOutSegmentEntry.  This object is invalid when
        the value of h3cMplsExtBfdType is not lsp(2), then this object
        contains a zero-length string."
    ::= { h3cMplsExtBfdEntry 5 }

h3cMplsExtBfdPwBackupFlag     OBJECT-TYPE
    SYNTAX      INTEGER {
                        none(1),
                        primary(2),
                        backup(3)
                     }
    MAX-ACCESS  read-only
    STATUS      current
    DESCRIPTION
        "PW flag."
    ::= { h3cMplsExtBfdEntry 6 }

h3cMplsExtBfdPwId     OBJECT-TYPE
    SYNTAX      Unsigned32(0..4294967295)
    MAX-ACCESS  read-only
    STATUS      current
    DESCRIPTION
        "PW Identifier."
    DEFVAL { 0 }
    ::= { h3cMplsExtBfdEntry 7 }

h3cMplsExtBfdVsiIndex     OBJECT-TYPE
    SYNTAX      Unsigned32(1..4294967295)
    MAX-ACCESS  read-only
    STATUS      current
    DESCRIPTION
        "Virtual Switch Instance(VSI) index."
    DEFVAL { 4294967295 }
    ::= { h3cMplsExtBfdEntry 8 }

h3cMplsExtBfdPwPeerIpType     OBJECT-TYPE
    SYNTAX      InetAddressType
    MAX-ACCESS  read-only
    STATUS      current
    DESCRIPTION
        "The type of peer address.  Typically, this
        address type is IPv4 or IPv6, with a prefix length
        of 32 or 128, respectively."
    ::= { h3cMplsExtBfdEntry 9 }

h3cMplsExtBfdPwPeerIp     OBJECT-TYPE
    SYNTAX      InetAddress
    MAX-ACCESS  read-only
    STATUS      current
    DESCRIPTION
        "Peer address of the PW."
    ::= { h3cMplsExtBfdEntry 10 }

h3cMplsExtBfdPwSPE     OBJECT-TYPE
    SYNTAX      INTEGER {
                        none(1),
                        upe(2),
                        spe(3)
                     }
    MAX-ACCESS  read-only
    STATUS      current
    DESCRIPTION
        "Node information of the Virtual Private Wire Service(VPWS) PW,
        User facing-Provider Edge(UPE) or Switching Provider Edge(SPE)."
    ::= { h3cMplsExtBfdEntry 11 }

h3cMplsExtBfdPwEncapType     OBJECT-TYPE
    SYNTAX      INTEGER {
                        unknown(1),
                        frDlciMartini(2),
                        atmAal5Sdu(3),
                        atmTransCell(4),
                        vlan(5),
                        ethernet(6),
                        hdlc(7),
                        ppp(8),
                        cesom(9),
                        atmNto1Vcc(10),
                        atmNto1Vpc(11),
                        ipInterworking(12),
                        atm1to1Vcc(13),
                        atm1to1Vpc(14),
                        atmAal5Pdu(15),
                        frPort(16),
                        cep(17),
                        satopE1(18),
                        satopT1(19),
                        satopE3(20),
                        satopT3(21),
                        esopsnBasic(22),
                        tdmoipAal1Mode(23),
                        tdmCesopsnWithCas(24),
                        tdmoipAal2Mode(25),
                        frDlci(26)
                     }
    MAX-ACCESS  read-only
    STATUS      current
    DESCRIPTION
        "Encapsulation type of the PW."
    ::= { h3cMplsExtBfdEntry 12 }
-- =============================================================================
-- End of h3cMplsExtBfdTable Definition
-- =============================================================================

-- =============================================================================
-- h3cMplsExtVpnStatsTable Definition
-- =============================================================================
h3cMplsExtVpnStatsTable  OBJECT-TYPE
    SYNTAX      SEQUENCE OF H3cMplsExtVpnStatsEntry
    MAX-ACCESS  not-accessible
    STATUS      current
    DESCRIPTION
        "A table contains statistical information about packets
         received from and sent by each VPN."
    ::= { h3cMplsExtObjects 5 }

h3cMplsExtVpnStatsEntry   OBJECT-TYPE
    SYNTAX      H3cMplsExtVpnStatsEntry
    MAX-ACCESS  not-accessible
    STATUS      current
    DESCRIPTION
        "An entry in this table contains statistical
        information about packets received from and sent by a VPN."
    INDEX
    {
        h3cMplsExtVpnStatsVrfIndex
    }
    ::= { h3cMplsExtVpnStatsTable 1 }

H3cMplsExtVpnStatsEntry ::=
    SEQUENCE
    {
        h3cMplsExtVpnStatsVrfIndex            Unsigned32,
        h3cMplsExtVpnStatsVpnName             OCTET STRING,
        h3cMplsExtVpnStatsInOctets            Counter64,
        h3cMplsExtVpnStatsInPackets           Counter64,
        h3cMplsExtVpnStatsInErrors            Counter64,
        h3cMplsExtVpnStatsInDiscards          Counter64,
        h3cMplsExtVpnStatsOutOctets           Counter64,
        h3cMplsExtVpnStatsOutPackets          Counter64,
        h3cMplsExtVpnStatsOutErrors           Counter64,
        h3cMplsExtVpnStatsOutDiscards         Counter64
    }

h3cMplsExtVpnStatsVrfIndex   OBJECT-TYPE
    SYNTAX      Unsigned32(1..4294967295)
    MAX-ACCESS  not-accessible
    STATUS      current
    DESCRIPTION
        "The index of a VPN."
    ::= { h3cMplsExtVpnStatsEntry 1 }

h3cMplsExtVpnStatsVpnName   OBJECT-TYPE
    SYNTAX      OCTET STRING (SIZE (1..31))
    MAX-ACCESS  read-only
    STATUS      current
    DESCRIPTION
        "The name of a VPN."
    ::= { h3cMplsExtVpnStatsEntry 2 }

h3cMplsExtVpnStatsInOctets     OBJECT-TYPE
    SYNTAX      Counter64
    MAX-ACCESS  read-only
    STATUS      current
    DESCRIPTION
        "Number of octets received from a VPN."
    ::= { h3cMplsExtVpnStatsEntry 3 }

h3cMplsExtVpnStatsInPackets   OBJECT-TYPE
    SYNTAX      Counter64
    MAX-ACCESS  read-only
    STATUS      current
    DESCRIPTION
        "Number of packets received from a VPN."
    ::= { h3cMplsExtVpnStatsEntry 4 }

h3cMplsExtVpnStatsInErrors     OBJECT-TYPE
    SYNTAX      Counter64
    MAX-ACCESS  read-only
    STATUS      current
    DESCRIPTION
        "Number of error packets received from a VPN."
    ::= { h3cMplsExtVpnStatsEntry 5 }

h3cMplsExtVpnStatsInDiscards   OBJECT-TYPE
    SYNTAX      Counter64
    MAX-ACCESS  read-only
    STATUS      current
    DESCRIPTION
        "Number of incoming packets,
        which were chosen to be discarded by a VPN even
        though no errors had been detected to prevent their
        being transmitted."
    ::= { h3cMplsExtVpnStatsEntry 6 }

h3cMplsExtVpnStatsOutOctets     OBJECT-TYPE
    SYNTAX      Counter64
    MAX-ACCESS  read-only
    STATUS      current
    DESCRIPTION
        "Number of octets sent by a VPN."
    ::= { h3cMplsExtVpnStatsEntry 7 }

h3cMplsExtVpnStatsOutPackets     OBJECT-TYPE
    SYNTAX      Counter64
    MAX-ACCESS  read-only
    STATUS      current
    DESCRIPTION
        "Number of packets sent by a VPN."
    ::= { h3cMplsExtVpnStatsEntry 8 }

h3cMplsExtVpnStatsOutErrors     OBJECT-TYPE
    SYNTAX      Counter64
    MAX-ACCESS  read-only
    STATUS      current
    DESCRIPTION
        "Number of packets that could not be sent by a VPN
        due to errors."
    ::= { h3cMplsExtVpnStatsEntry 9 }

h3cMplsExtVpnStatsOutDiscards     OBJECT-TYPE
    SYNTAX      Counter64
    MAX-ACCESS  read-only
    STATUS      current
    DESCRIPTION
        "Number of outgoing packets which were chosen to be discarded
        by a VPN even though no errors had been detected to prevent
        their being transmitted.  One possible reason for
        discarding such a packet could be to free up
        buffer space."
    ::= { h3cMplsExtVpnStatsEntry 10 }

-- =============================================================================
-- End of h3cMplsExtVpnStatsTable Definition
-- =============================================================================

-- =============================================================================
-- h3cMplsExtVpnTable Definition
-- =============================================================================
h3cMplsExtVpnTable  OBJECT-TYPE
    SYNTAX      SEQUENCE OF H3cMplsExtVpnEntry
    MAX-ACCESS  not-accessible
    STATUS      current
    DESCRIPTION
        "This table contains MPLS VPN information."
    ::= { h3cMplsExtObjects 6 }

h3cMplsExtVpnEntry   OBJECT-TYPE
    SYNTAX      H3cMplsExtVpnEntry
    MAX-ACCESS  not-accessible
    STATUS      current
    DESCRIPTION
        "An entry in this table represents information on a single VPN instance."
    INDEX
    {
        h3cMplsExtVpnName
    }
    ::= { h3cMplsExtVpnTable 1 }

H3cMplsExtVpnEntry ::=
    SEQUENCE
    {
        h3cMplsExtVpnName                  OCTET STRING,
        h3cMplsExtVrfIndex                 Unsigned32
    }

h3cMplsExtVpnName   OBJECT-TYPE
    SYNTAX      OCTET STRING (SIZE (1..31))
    MAX-ACCESS  not-accessible
    STATUS      current
    DESCRIPTION
        "The name of a VPN instance."
    ::= { h3cMplsExtVpnEntry 1 }

h3cMplsExtVrfIndex   OBJECT-TYPE
    SYNTAX      Unsigned32(0..4294967295)
    MAX-ACCESS  read-only
    STATUS      current
    DESCRIPTION
        "The index of a VPN instance."
    ::= { h3cMplsExtVpnEntry 2 }

-- =============================================================================
-- End of h3cMplsExtVpnTable Definition
-- =============================================================================

END
