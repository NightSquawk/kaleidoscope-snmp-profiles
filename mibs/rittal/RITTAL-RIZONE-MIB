--*********************************************************************
-- RITTAL GmbH & Co. KG, Herborn
-- RiZone-MIB Version 1.3
-- RiZone - DK 7990.10x
--
-- Management Information Base for SNMP Network Management
--
-- Copyright 2002 - 2014 Rittal Herborn.
-- All Rights Reserved.
--
-- The information in this document is subject to change without notice.
-- Refer to document "AGB_Software_Rittal.pdf"
--
--*********************************************************************

          RITTAL-RIZONE-MIB DEFINITIONS ::= BEGIN

          IMPORTS
           enterprises FROM RFC1155-SMI
           DisplayString FROM RFC1213-MIB
           sysName FROM RFC1213-MIB
           sysContact FROM RFC1213-MIB  
           sysLocation FROM RFC1213-MIB  

           OBJECT-TYPE FROM RFC-1212
           TRAP-TYPE FROM RFC-1215;

    rittal                         	OBJECT IDENTIFIER ::= { enterprises 2606 }
     riZone                         OBJECT IDENTIFIER ::= { rittal 6 }
       riZoneMibRev                 OBJECT IDENTIFIER ::= { riZone 1 }
       riZoneModules    			OBJECT IDENTIFIER ::= { riZone 2 }
       riZoneProject				OBJECT IDENTIFIER ::= { riZone 3 }
       riZoneStatus 				OBJECT IDENTIFIER ::= { riZone 4 }
        riZoneComponents         	OBJECT IDENTIFIER ::= { riZoneStatus 1 }
        riZoneVariables				OBJECT IDENTIFIER ::= { riZoneStatus 2 }
       riZoneCustomDefines          OBJECT IDENTIFIER ::= { riZone 5 }
        riZoneCustomDefinedTraps    OBJECT IDENTIFIER ::= { riZoneCustomDefines 1 }
                

--*****************************************************************************
--RiZone DK7990.0xx
--*****************************************************************************
--riZoneMibRev-group
          
        riZoneMibMajRev          OBJECT-TYPE
              SYNTAX  INTEGER
              ACCESS  read-only
              STATUS  mandatory
              DESCRIPTION
              "The Major Revision level.
               A change in the major revision level represents a major change
               in the architecture of the MIB. A change in the major revision 
               level may indicate a significant change in the information,
               correct interpretation of data may require a MIB document
               with the same major revision level."
              ::= { riZoneMibRev 1 }

        riZoneMibMinRev          OBJECT-TYPE
              SYNTAX  INTEGER
              ACCESS  read-only
              STATUS  mandatory
              DESCRIPTION
              "The Minor Revision level.
               A change in the minor revision level may represent some minor
               additional support, no changes to any pre-existing information
               has occurred."
              ::= { riZoneMibRev 2 }

        riZoneMibCondition        OBJECT-TYPE
              SYNTAX  INTEGER {
                other (1),
                ok (2),
                degraded (3),
                failed (4),
                configChanged (5),
                timeout (6)
                }
              ACCESS  read-only
              STATUS  mandatory
              DESCRIPTION
              "The overall condition (status) of the system represented by
               this MIB. 
               (1) other or unknown condition
               (2) OK
               (3) a minor problem, warning condition (RiZone warning)
               (4) a major problem (RiZone alarm)
               (5) configuration of project changed
               (6) connection timeout of at least one of the project's devices"
              ::= { riZoneMibRev 3 }


          
--riZoneModules-group
        riZoneCoreState OBJECT-TYPE
              SYNTAX INTEGER {
                failed(1),
                ok(2)
                }
              ACCESS  read-only
              STATUS  mandatory
              DESCRIPTION
              "General status of core process
              (1) failed
              (2) OK"
              ::= { riZoneModules  1 }

        riZoneCoreVersion OBJECT-TYPE
              SYNTAX DisplayString (SIZE (0..10))
              ACCESS read-only
              STATUS mandatory
              DESCRIPTION
              "Core version"
              ::= { riZoneModules  2 }


--riZoneProject-group

        riZoneProjectName OBJECT-TYPE
              SYNTAX DisplayString (SIZE (0..50))
              ACCESS read-only
              STATUS mandatory
              DESCRIPTION
              "Name of published project"
              ::= { riZoneProject  1 }
        riZoneProjectChangeTime OBJECT-TYPE
             SYNTAX DisplayString (SIZE (0..24))
              ACCESS read-only
              STATUS mandatory
              DESCRIPTION
              "Date of last project upload
              Dateformate 'MM/dd/yyyy HH:mm:ss fff'
              MM = The month (01-12).
              dd = The day of the month (01-31).
              yyyy = The year as a four-digit number.
              HH = The hour, using a 24-hour clock (00-24).
              mm = The minute (00-59).
              ss = The seconds (00-59).
              fff = milliseconds"
              ::= { riZoneProject  2 }

--riZoneStatus-group	  
              
        riZoneStatusAvailability OBJECT-TYPE
              SYNTAX INTEGER {
                notAvail(1),
                ok(2),
                warning(3),
                alarm(4),
                timeout(5)
                }
              ACCESS  read-only
              STATUS  mandatory
              DESCRIPTION
              "Summary of all availability states
              (1) Is not available or published in project.
              (2) Ok
              (3) Warning
              (4) Alarm
              (5) Timeout"
              ::= { riZoneStatus  3 }
        riZoneStatusCooling OBJECT-TYPE
              SYNTAX INTEGER {
                notAvail(1),
                ok(2),
                warning(3),
                alarm(4)
                }
              ACCESS  read-only
              STATUS  mandatory
              DESCRIPTION
              "Summary of all cooling states
              (1) Is not available or published in project.
              (2) Ok
              (3) Warning
              (4) Alarm"
              ::= { riZoneStatus  4 }
        riZoneStatusPower OBJECT-TYPE
              SYNTAX INTEGER {
                notAvail(1),
                ok(2),
                warning(3),
                alarm(4)
                }
              ACCESS  read-only
              STATUS  mandatory
              DESCRIPTION
              "Summary of all power states
              (1) Is not available or published in project.
              (2) Ok
              (3) Warning
              (4) Alarm"
              ::= { riZoneStatus  5 }
        riZoneStatusMonitoring OBJECT-TYPE
              SYNTAX INTEGER {
                notAvail(1),
                ok(2),
                warning(3),
                alarm(4)
                }
              ACCESS  read-only
              STATUS  mandatory
              DESCRIPTION
              "Summary of all monitoring states
              (1) Is not available or published in project.
              (2) Ok
              (3) Warning
              (4) Alarm"
              ::= { riZoneStatus  6 }
        riZoneStatusSecurity OBJECT-TYPE
              SYNTAX INTEGER {
                notAvail(1),
                ok(2),
                warning(3),
                alarm(4)
                }
              ACCESS  read-only
              STATUS  mandatory
              DESCRIPTION
              "Summary of all security states
              (1) Is not available or published in project.
              (2) Ok
              (3) Warning
              (4) Alarm"
              ::= { riZoneStatus  7 }
        riZoneStatusCapacity OBJECT-TYPE
              SYNTAX INTEGER {
                notAvail(1),
                ok(2),
                warning(3),
                alarm(4)
                }
              ACCESS  read-only
              STATUS  mandatory
              DESCRIPTION
              "Summary of all capacity states
              (1) Is not available or published in project.
              (2) Ok
              (3) Warning
              (4) Alarm"
              ::= { riZoneStatus  8 }
        riZoneStatusRack OBJECT-TYPE
              SYNTAX INTEGER {
                notAvail(1),
                ok(2),
                warning(3),
                alarm(4)
                }
              ACCESS  read-only
              STATUS  mandatory
              DESCRIPTION
              "Summary of all Rack element states
              (1) Is not available or published in project.
              (2) Ok
              (3) Warning
              (4) Alarm"
              ::= { riZoneStatus  9 }
              
--riZoneComponents-group
              
        riZoneNumberOfComponents OBJECT-TYPE
              SYNTAX INTEGER 
              ACCESS  read-only
              STATUS  mandatory
              DESCRIPTION
              "Number of sensors connected to sensor unit 1"
              ::= { riZoneComponents  1 }

-- table with entry for each sensor available on this unit              
        
        riZoneComponentTable     OBJECT-TYPE
              SYNTAX  SEQUENCE OF RiZoneComponentEntry
              ACCESS  not-accessible
              STATUS  mandatory
              DESCRIPTION
              "Headline of component table"
              ::= { riZoneComponents 2 }

        riZoneComponentEntry     OBJECT-TYPE
              SYNTAX  RiZoneComponentEntry
              ACCESS  not-accessible
              STATUS  mandatory
              DESCRIPTION
              "Entries of sensor table"
              INDEX   { componentIndex }
              ::= { riZoneComponentTable 1 }

              RiZoneComponentEntry ::=
              SEQUENCE {
              componentIndex
                INTEGER,
              componentId
                INTEGER,
              componentName
                DisplayString,                
              componentType
                INTEGER,
              componentParent
                INTEGER,
              componentStatusTotal
                INTEGER,
              componentStatusAvailability
                INTEGER,
              componentStatusCooling
                INTEGER,                
              componentStatusPower
                INTEGER,                
              componentStatusMonitoring
                INTEGER,                
              componentStatusSecurity
                INTEGER,                
              componentStatusCapacity
                INTEGER,                
              componentStatusRack
                INTEGER
              }

        componentIndex OBJECT-TYPE
             SYNTAX INTEGER (1..2147483647)
             ACCESS read-only
             STATUS mandatory
             DESCRIPTION
             "Index for the list of value entries. Its value ranges
              between 1 and the value of riZoneNumberOfComponents." 
             ::= { riZoneComponentEntry 1 }
        
        componentId OBJECT-TYPE
             SYNTAX INTEGER
             ACCESS read-only
             STATUS mandatory
             DESCRIPTION
             "Component ID in RiZone project." 
             ::= { riZoneComponentEntry 2 }
        
        componentName OBJECT-TYPE
              SYNTAX DisplayString (SIZE (0..30))
              ACCESS read-only
              STATUS mandatory
              DESCRIPTION
              "Name of component"
              ::= { riZoneComponentEntry  3 }
        
        componentType OBJECT-TYPE
             SYNTAX INTEGER {
                removed (1),
                domain (2),
                location (3),
                building (4),
                room (5),
                rackrow (6),
                rack (7),
                device (8),
                rackitem (9)
                }
        
        
             ACCESS read-only
             STATUS mandatory
             DESCRIPTION
             "Type of component
              (1) Component removed
              (2) Project domain
              (3) Location
              (4) Building
              (5) Room
              (6) Rackrow
              (7) Rack
              (8) Device represent by driver
              (9) Rackitem"
             ::= { riZoneComponentEntry 4 }
        
        componentParent OBJECT-TYPE
             SYNTAX INTEGER
             ACCESS read-only
             STATUS mandatory
             DESCRIPTION
             "Parent component ID of location tree." 
             ::= { riZoneComponentEntry 5 }

        componentStatusTotal OBJECT-TYPE
              SYNTAX INTEGER {
                notAvail(1),
                ok(2),
                warning(3),
                alarm(4),
                timeout(5)
                }
              ACCESS  read-only
              STATUS  mandatory
              DESCRIPTION
              "Summary of all availability states of this component
              (1) Is not available or published in project.
              (2) Ok
              (3) Warning
              (4) Alarm
              (5) Timeout"
              ::= { riZoneComponentEntry  6 }
        
        componentStatusAvailability OBJECT-TYPE
              SYNTAX INTEGER {
                notAvail(1),
                ok(2),
                warning(3),
                alarm(4),
                timeout(5)
                }
              ACCESS  read-only
              STATUS  mandatory
              DESCRIPTION
              "Summary of all availability states of this component
              (1) Is not available or published in project.
              (2) Ok
              (3) Warning
              (4) Alarm
              (5) Timeout"
              ::= { riZoneComponentEntry  7 }
              
        componentStatusCooling OBJECT-TYPE
              SYNTAX INTEGER {
                notAvail(1),
                ok(2),
                warning(3),
                alarm(4)
                }
              ACCESS  read-only
              STATUS  mandatory
              DESCRIPTION
              "Summary of all cooling states of this component
              (1) Is not available or published in project.
              (2) Ok
              (3) Warning
              (4) Alarm"
              ::= { riZoneComponentEntry  8 }
              
        componentStatusPower OBJECT-TYPE
              SYNTAX INTEGER {
                notAvail(1),
                ok(2),
                warning(3),
                alarm(4)
                }
              ACCESS  read-only
              STATUS  mandatory
              DESCRIPTION
              "Summary of all power states of this component
              (1) Is not available or published in project.
              (2) Ok
              (3) Warning
              (4) Alarm"
              ::= { riZoneComponentEntry  9 }
              
        componentStatusMonitoring OBJECT-TYPE
              SYNTAX INTEGER {
                notAvail(1),
                ok(2),
                warning(3),
                alarm(4)
                }
              ACCESS  read-only
              STATUS  mandatory
              DESCRIPTION
              "Summary of all monitoring states of this component
              (1) Is not available or published in project.
              (2) Ok
              (3) Warning
              (4) Alarm"
              ::= { riZoneComponentEntry  10 }
              
        componentStatusSecurity OBJECT-TYPE
              SYNTAX INTEGER {
                notAvail(1),
                ok(2),
                warning(3),
                alarm(4)
                }
              ACCESS  read-only
              STATUS  mandatory
              DESCRIPTION
              "Summary of all security states of this component
              (1) Is not available or published in project.
              (2) Ok
              (3) Warning
              (4) Alarm"
              ::= { riZoneComponentEntry  11 }

        componentStatusCapacity OBJECT-TYPE
              SYNTAX INTEGER {
                notAvail(1),
                ok(2),
                warning(3),
                alarm(4)
                }
              ACCESS  read-only
              STATUS  mandatory
              DESCRIPTION
              "Summary of all capacity states of this component
              (1) Is not available or published in project.
              (2) Ok
              (3) Warning
              (4) Alarm"
              ::= { riZoneComponentEntry  12 }

        componentStatusRack OBJECT-TYPE
              SYNTAX INTEGER {
                notAvail(1),
                ok(2),
                warning(3),
                alarm(4)
                }
              ACCESS  read-only
              STATUS  mandatory
              DESCRIPTION
              "Summary of all Rack element states of this component
              (1) Is not available or published in project.
              (2) Ok
              (3) Warning
              (4) Alarm"
              ::= { riZoneComponentEntry  13 }

-- table END            
              
--riZoneVariables-group
              
        riZoneNumberOfVariables OBJECT-TYPE
              SYNTAX INTEGER 
              ACCESS  read-only
              STATUS  mandatory
              DESCRIPTION
              "Number of sensors connected to sensor unit 1"
              ::= { riZoneVariables  1 }

-- table with entry for each sensor available on this unit              
        
        riZoneVariableTable     OBJECT-TYPE
              SYNTAX  SEQUENCE OF RiZoneVariableEntry
              ACCESS  not-accessible
              STATUS  mandatory
              DESCRIPTION
              "Headline of component table"
              ::= { riZoneVariables 2 }

        riZoneVariableEntry     OBJECT-TYPE
              SYNTAX  RiZoneVariableEntry
              ACCESS  not-accessible
              STATUS  mandatory
              DESCRIPTION
              "Entries of sensor table"
              INDEX   { variableIndex }
              ::= { riZoneVariableTable 1 }

              RiZoneVariableEntry ::=
              SEQUENCE {
              variableIndex
                INTEGER,
              variableId
                INTEGER,
              variableName
                DisplayString,                
              variableMaintenanceGroup
                INTEGER,
              variableMeasurand
                INTEGER,
              variableParentId
                INTEGER,
              variableType
                INTEGER,
              variableQuality
                INTEGER,
              variableValueInt
                INTEGER,
              variableValueString
                DisplayString,
              variableValueUnit
                DisplayString,                
              variableDivisor
                INTEGER,                
              variableMultiplicator 
                INTEGER              
              }

        variableIndex OBJECT-TYPE
             SYNTAX INTEGER (1..2147483647)
             ACCESS read-only
             STATUS mandatory
             DESCRIPTION
             "Index for the list of value entries. Its value ranges
              between 1 and the value of riZoneNumberOfVariables." 
             ::= { riZoneVariableEntry 1 }
        
        variableId OBJECT-TYPE
             SYNTAX INTEGER
             ACCESS read-only
             STATUS mandatory
             DESCRIPTION
             "Variable ID in RiZone project." 
             ::= { riZoneVariableEntry 2 }
        
        variableName OBJECT-TYPE
              SYNTAX DisplayString (SIZE (0..30))
              ACCESS read-only
              STATUS mandatory
              DESCRIPTION
              "Name of Variable"
              ::= { riZoneVariableEntry  3 }
        
        variableMaintenanceGroup OBJECT-TYPE
             SYNTAX INTEGER {
                undefined(1),
                cooling(2),
                power(4),
                rack(8),
                monitoring(16),
                remoting(32),
                availability(64),
                security(128),
                capacity(256)
                }
                
             ACCESS read-only
             STATUS mandatory
             DESCRIPTION
             "Maintenance Group of Variable (Bit encoded value)
              (1) 	 Undefined
              (2)    Cooling
              (4)    Power
              (8)    Rack
              (16)   Monitoring
              (32)   Remoting
              (64)   Availability
              (128)  Security
              (256)  Capacity"
             ::= { riZoneVariableEntry 4 }
        
        variableMeasurand OBJECT-TYPE
             SYNTAX INTEGER {
                undefined(1),
                temperature(2),
                current(3),
                power(4),
                effectivePower(5),
                humidity(6),
                voltage(7),
                energy(8),
                frequency(9),
                access(10),
                leakage(11),
                percent(12),
                rpm(13),
                co2(14),
                pue(15),
                flow(16),
                time(17),
                costs(18),
                imp(19),
                heatCapacity(20),
                constant(21),
                temperatureDiff(22),
                timespan(23),
                cycles(24),
                pulseRate(34),
                pressure(35),
                acceleration(36),
                timeSpanTicks(37)
                }
             ACCESS read-only
             STATUS mandatory
             DESCRIPTION
             "Measurand of Variable
                undefined(1),
                Temperature(2),
                Current(3),
                Power(4),
                EffectivePower(5),
                Humidity(6),
                Voltage(7),
                Energy(8),
                Frequency(9),
                Access(10),
                Leakage(11),
                Percent(12),
                RPM(13),
                CO2(14),
                PUE(15),
                Flow(16),
                Time(17),
                Costs(18),
                Imp(19),
                HeatCapacity(20),
                Constant(21),
                TemperatureDiff(22),
                Timespan(23),
                Cycles(24),
                PulseRate(34),
                Pressure(35),
                Acceleration(36),
                TimeSpanTicks(37)"
             ::= { riZoneVariableEntry 5 }
        
        variableParentId OBJECT-TYPE
             SYNTAX INTEGER
             ACCESS read-only
             STATUS mandatory
             DESCRIPTION
             "Component ID in RiZone project." 
             ::= { riZoneVariableEntry 6 }
             
            
        variableType OBJECT-TYPE
              SYNTAX INTEGER {
                number(1),
                string(2),
                enum(3)
                }
              ACCESS  read-only
              STATUS  mandatory
              DESCRIPTION
              "Summary of all availability states of this component
              (1) Number
              (2) String
              (3) Enum"
              ::= { riZoneVariableEntry  7 }
              
        variableQuality OBJECT-TYPE
              SYNTAX INTEGER {
                undefined(1),
                good(2),
                bad(3)
                }
              ACCESS  read-only
              STATUS  mandatory
              DESCRIPTION
              "Quality of value. Bad values have old timestamps. The actual and state value is unknown. 
              (1) undefined
              (2) good
              (3) bad"
              ::= { riZoneVariableEntry  8 }
              
        variableValueInt OBJECT-TYPE
             SYNTAX INTEGER
             ACCESS read-only
             STATUS mandatory
             DESCRIPTION
             "Value of variables without decimal separator." 
             ::= { riZoneVariableEntry  9 }
              
        variableValueString OBJECT-TYPE
              SYNTAX DisplayString (SIZE (0..30))
              ACCESS read-write
              STATUS mandatory
              DESCRIPTION
              "Value of variables as string. For numbers, a point is used as decimal separator."
              ::= { riZoneVariableEntry  10 }
              
        variableValueUnit OBJECT-TYPE
              SYNTAX DisplayString (SIZE (0..10))
              ACCESS read-only
              STATUS mandatory
              DESCRIPTION
              "The unit of value"
              ::= { riZoneVariableEntry  11 }
              
        variableDivisor OBJECT-TYPE
             SYNTAX INTEGER
             ACCESS read-only
             STATUS mandatory
             DESCRIPTION
             "Divisor of variables. If the value is not equal to 1, then variableValueInt must be divided by this value to get the result." 
             ::= { riZoneVariableEntry 12 }
             
        variableMultiplicator OBJECT-TYPE
             SYNTAX INTEGER
             ACCESS read-only
             STATUS mandatory
             DESCRIPTION
             "Multiplicator of variables. If the value is not equal to 1, then variableValueInt must be multiplied with this value to get the result."  
             ::= { riZoneVariableEntry 13 }

-- table END 

--riZoneCustomDefinedTraps-group
              
        riZoneNumberOfTraps OBJECT-TYPE
              SYNTAX INTEGER 
              ACCESS  read-only
              STATUS  mandatory
              DESCRIPTION
              "Number of custom defined traps"
              ::= { riZoneCustomDefinedTraps  1 }

-- table with entry for customDefinedTraps            
        
        riZoneCustomDefinedTrapsTable     OBJECT-TYPE
              SYNTAX  SEQUENCE OF RiZoneCustomDefinedTrapsEntry
              ACCESS  not-accessible
              STATUS  mandatory
              DESCRIPTION
              "Headline of Custom Defined Trap table"
              ::= { riZoneCustomDefinedTraps 2 }

        riZoneCustomDefinedTrapsEntry     OBJECT-TYPE
              SYNTAX  RiZoneCustomDefinedTrapsEntry
              ACCESS  not-accessible
              STATUS  mandatory
              DESCRIPTION
              "Entries of sensor table"
              INDEX   { customDefinedTrapIndex }
              ::= { riZoneCustomDefinedTrapsTable 1 }

              RiZoneCustomDefinedTrapsEntry ::=
              SEQUENCE {
              customDefinedTrapIndex 
				INTEGER,
              cdtMessageCategory
                INTEGER,
              cdtWorkflowId
                INTEGER, 
			  cdtWorkflowName
				DisplayString,
			  cdtFlowElementId
				DisplayString,
			  cdtMessageText
			    DisplayString,
			  cdtVariableId
			    INTEGER,
			  cdtVariableName
			    DisplayString,
			  cdtVariableValue
				INTEGER,
			  cdtVariableTranslation
				DisplayString,
			  cdtVariableOwnerId
				INTEGER,
			  cdtVariableOwnerName
				DisplayString
               }

        customDefinedTrapIndex OBJECT-TYPE
             SYNTAX INTEGER (1..2147483647)
             ACCESS read-only
             STATUS mandatory
             DESCRIPTION
             "Index for the list of value entries. Its value ranges
              between 1 and the value of riZoneNumberOfTraps." 
             ::= { riZoneCustomDefinedTrapsEntry 1 }
        
		
        cdtMessageCategory OBJECT-TYPE
             SYNTAX INTEGER {
                na (1),
                info (2),
                warning (3),
                error (4),
                ok (5)
                }
                
             ACCESS read-only
             STATUS mandatory
             DESCRIPTION
             "Trap category
              (1) Not Available  
              (2) Info
              (3) Warning
              (4) Error
              (5) Ok"
             ::= { riZoneCustomDefinedTrapsEntry  2 }

        cdtWorkflowId OBJECT-TYPE
             SYNTAX INTEGER (0..2147483647)
             ACCESS read-only
             STATUS mandatory
             DESCRIPTION
             "Workflow ID in RiZone project." 
             ::= { riZoneCustomDefinedTrapsEntry 3 }

        cdtWorkflowName OBJECT-TYPE
             SYNTAX DisplayString (SIZE(0..255))
             ACCESS read-only
             STATUS mandatory
             DESCRIPTION
             "Workflow Name in RiZone project." 
             ::= { riZoneCustomDefinedTrapsEntry 4 }
			 
        cdtFlowElementId OBJECT-TYPE
             SYNTAX DisplayString (SIZE (0..10))
             ACCESS read-only
             STATUS mandatory
             DESCRIPTION
             "Workflow ID in RiZone project." 
             ::= { riZoneCustomDefinedTrapsEntry 5 }
        
		cdtMessageText OBJECT-TYPE
             SYNTAX DisplayString (SIZE (0..255))
             ACCESS read-only
             STATUS mandatory
             DESCRIPTION
             "Message Text of the trap." 
             ::= { riZoneCustomDefinedTrapsEntry 6 } 
			 
		cdtVariableId OBJECT-TYPE
             SYNTAX INTEGER (1..2147483647)
             ACCESS read-only
             STATUS mandatory
             DESCRIPTION
             "Variable ID in RiZone project." 
             ::= { riZoneCustomDefinedTrapsEntry 7 }    
			 
		cdtVariableName OBJECT-TYPE
             SYNTAX DisplayString (SIZE (0..255))
             ACCESS read-only
             STATUS mandatory
             DESCRIPTION
             "Name of the variable." 
             ::= { riZoneCustomDefinedTrapsEntry 8 }
		
		cdtVariableValue OBJECT-TYPE
             SYNTAX INTEGER (1..2147483647)
             ACCESS read-only
             STATUS mandatory
             DESCRIPTION
             "Current value of the Variable." 
             ::= { riZoneCustomDefinedTrapsEntry 9 }
		
		cdtVariableTranslation OBJECT-TYPE
             SYNTAX DisplayString (SIZE (0..255))
             ACCESS read-only
             STATUS mandatory
             DESCRIPTION
             "Tranlsation of the current value of the Variable (if available)." 
             ::= { riZoneCustomDefinedTrapsEntry 10 }
			 		
		cdtVariableOwnerId OBJECT-TYPE
             SYNTAX INTEGER (1..2147483647)
             ACCESS read-only
             STATUS mandatory
             DESCRIPTION
             "Id of the owner of the variable in RiZone." 
             ::= { riZoneCustomDefinedTrapsEntry 11 }  	
			 
		cdtVariableOwnerName OBJECT-TYPE
             SYNTAX DisplayString (SIZE (0..255))
             ACCESS read-only
             STATUS mandatory
             DESCRIPTION
             "Name of the owner of the variable." 
             ::= { riZoneCustomDefinedTrapsEntry 12 }		  
-- table END            

--Traps
        projectUpload TRAP-TYPE
            ENTERPRISE riZone
            VARIABLES {sysName, sysLocation, sysContact, riZoneProjectName, riZoneProjectChangeTime }
            DESCRIPTION
            "New project is uploaded"
--
--#TYPE         "Project uploaded"
--#SUMMARY      "New project %s is uploaded at %s  Name: %s, Location: %s, Contact %s"
--#ARGUMENTS    {4,5,1,2,3}
--#SEVERITY     MAJOR
--#TIMEINDEX    4
--#STATE        OPERATIONAL
--                      
              ::= 1
              
              
        customDefinedTrap TRAP-TYPE
            ENTERPRISE riZone
            VARIABLES {cdtMessageCategory, cdtWorkflowId, cdtWorkflowName, cdtMessageText, cdtVariableId, cdtVariableName, cdtVariableValue, cdtVariableTranslation, cdtVariableOwnerId, cdtVariableOwnerName  }
            DESCRIPTION
            "Custom defined trap"
--
--#TYPE         "Custom defined trap"
--#SUMMARY      "Custom defined trap from workflow with Id %s and catergory %s"
--#ARGUMENTS    {2, 1}
--#SEVERITY     MAJOR
--#TIMEINDEX    4
--#STATE        OPERATIONAL
--                      
              ::= 2      
          

            END
