-----------------------------------------------------------------------
-- MIB table for T5545
--
-- v3.0 for firmware 1-5-7-2, 2016-04-11
-----------------------------------------------------------------------
T5545-MIB DEFINITIONS ::= BEGIN


IMPORTS
	enterprises
		FROM RFC1155-SMI
	OBJECT-TYPE
		FROM RFC-1212
	TRAP-TYPE
		FROM RFC-1215;

  DisplayString ::= OCTET STRING


comet      OBJECT IDENTIFIER ::= { enterprises 22626 }
products   OBJECT IDENTIFIER ::= { comet 1 }
t5545      OBJECT IDENTIFIER ::= { products 2 }
values     OBJECT IDENTIFIER ::= { t5545 1 }
global     OBJECT IDENTIFIER ::= { t5545 2 }
valuesInt  OBJECT IDENTIFIER ::= { t5545 3 }
settings   OBJECT IDENTIFIER ::= { t5545 4 }
traps      OBJECT IDENTIFIER ::= { t5545 5 }
tables	   OBJECT IDENTIFIER ::= { t5545 6 }


-----------------------------------------------------------------------
-- Measured values - String
-----------------------------------------------------------------------
co2 OBJECT-TYPE
	SYNTAX		DisplayString (SIZE (0..8))
	ACCESS		read-only
	STATUS		mandatory
	DESCRIPTION	"CO2 level"
::= { values 4 }

co2Alarm OBJECT-TYPE
	SYNTAX		DisplayString (SIZE (0..8))
	ACCESS		read-only
	STATUS		mandatory
	DESCRIPTION	"Alarm on CO2; none, high, low"
::= { values 8 }

co2Unit OBJECT-TYPE
	SYNTAX  	DisplayString (SIZE (0..8))
	ACCESS		read-only
	STATUS		mandatory
	DESCRIPTION	"CO2 Unit"
::= { values 12 }

co2Min OBJECT-TYPE
	SYNTAX  	DisplayString (SIZE (0..8))
	ACCESS		read-only
	STATUS		mandatory
	DESCRIPTION	"Minimal CO2 level"
::= { values 16 }

co2Max OBJECT-TYPE
	SYNTAX  	DisplayString (SIZE (0..8))
	ACCESS		read-only
	STATUS		mandatory
	DESCRIPTION	"Maximal CO2 level"
::= { values 20 }


-----------------------------------------------------------------------
-- Device informations
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- Measured values - Integer
-----------------------------------------------------------------------
co2Int OBJECT-TYPE
	SYNTAX		INTEGER (-5000..20000)
	ACCESS		read-only
	STATUS		mandatory
	DESCRIPTION	"CO2 level"
::= { valuesInt 4 }

co2AlarmInt OBJECT-TYPE
	SYNTAX		INTEGER (0..2)
	ACCESS		read-only
	STATUS		mandatory
	DESCRIPTION	"Alarm on CO2; 0 - No, 1 - High, 2 - Low"
::= { valuesInt 8 }


-----------------------------------------------------------------------
-- Alarm settings
-----------------------------------------------------------------------
co2LowInt OBJECT-TYPE
	SYNTAX		INTEGER (-5000..20000)
	ACCESS		read-only
	STATUS		mandatory
	DESCRIPTION	"CO2 Limit Low"
::= { settings 13 }

co2HighInt OBJECT-TYPE
	SYNTAX		INTEGER (-5000..20000)
	ACCESS		read-only
	STATUS		mandatory
	DESCRIPTION	"CO2 Limit High"
::= { settings 14 }

co2DelayInt OBJECT-TYPE
	SYNTAX		INTEGER (0..4500)
	ACCESS		read-only
	STATUS		mandatory
	DESCRIPTION	"CO2 alaram delay [sec]"
::= { settings 15 }

co2HystInt OBJECT-TYPE
	SYNTAX		INTEGER (0..10000)
	ACCESS		read-only
	STATUS		mandatory
	DESCRIPTION	"CO2 hysteresis"
::= { settings 16 }


-----------------------------------------------------------------------
-- Trap message
-----------------------------------------------------------------------
messageString OBJECT-TYPE
	SYNTAX		DisplayString (SIZE (0..32))
	ACCESS		read-only
	STATUS		mandatory
	DESCRIPTION	"Message giving more detailed information on alarms"
::= { traps 1 }


-----------------------------------------------------------------------
-- Tables
-----------------------------------------------------------------------
historyTable OBJECT-TYPE
	SYNTAX		SEQUENCE OF HistoryEntry
	ACCESS		not-accessible
	STATUS		mandatory
	DESCRIPTION	"Table of the history values"
::= { tables 1 }

historyEntry OBJECT-TYPE
	SYNTAX		HistoryEntry
	ACCESS		not-accessible
	STATUS		optional
	DESCRIPTION	"History values entries"
	INDEX		{ histCO2 }
::= { historyTable 1 }

HistoryEntry ::=
	SEQUENCE {
		histCO2
			INTEGER
		}

histCO2 OBJECT-TYPE
	SYNTAX		INTEGER(-5000..20000)
	ACCESS		read-only
	STATUS		mandatory
	DESCRIPTION	"CO2 level reading"
::= { historyEntry 4 }


-----------------------------------------------------------------------
-- Traps definition
-----------------------------------------------------------------------

trapTest TRAP-TYPE
	ENTERPRISE	comet
	VARIABLES	{ sensorName, messageString }
	DESCRIPTION
		"Testing trap, testing trap by TSensor software"
	::= 0

trapNTPError TRAP-TYPE
	ENTERPRISE	comet
	VARIABLES	{ sensorName, messageString }
	DESCRIPTION
		"Error on time synchronisation via NTP"
	::= 1

trapEmailErrLogin TRAP-TYPE
	ENTERPRISE	comet
	VARIABLES	{ sensorName, messageString }
	DESCRIPTION
		"SMTP error - unknown server"
	::= 2

trapEmailErrAuth TRAP-TYPE
	ENTERPRISE	comet
	VARIABLES	{ sensorName, messageString }
	DESCRIPTION
		"SMTP error - authentication error"
	::= 3

trapEmailErrSome TRAP-TYPE
	ENTERPRISE	comet
	VARIABLES	{ sensorName, messageString }
	DESCRIPTION
		"SMTP error - error during communication with server, unexpected return code"
	::= 4

trapEmailErrSocket TRAP-TYPE
	ENTERPRISE	comet
	VARIABLES	{ sensorName, messageString }
	DESCRIPTION
		"SMTP error - socket error, server is not available"
	::= 5

trapEmailErrDNS TRAP-TYPE
	ENTERPRISE	comet
	VARIABLES	{ sensorName, messageString }
	DESCRIPTION
		"SMTP error - DNS error"
	::= 6

trapSOAPErrFile TRAP-TYPE
	ENTERPRISE	comet
	VARIABLES	{ sensorName, messageString }
	DESCRIPTION
		"SOAP error - file SOAP not found"
	::= 7

trapSOAPErrDNS TRAP-TYPE
	ENTERPRISE	comet
	VARIABLES	{ sensorName, messageString }
	DESCRIPTION
		"SOAP error - DNS error"
	::= 8

trapSOAPErrSocket TRAP-TYPE
	ENTERPRISE	comet
	VARIABLES	{ sensorName, messageString }
	DESCRIPTION
		"SOAP error - socket error, server is not available"
	::= 9

trapSOAPErrDelivery TRAP-TYPE
	ENTERPRISE	comet
	VARIABLES	{ sensorName, messageString }
	DESCRIPTION
		"SOAP error - delivery error, wrong return code from server"
	::= 10

trapCo2HighAlarm TRAP-TYPE
	ENTERPRISE	comet
	VARIABLES	{ sensorName, messageString, co2, co2AlarmInt }
	DESCRIPTION
		"Trap for high alarm on CO2 level"
	::= 14

trapCo2LowAlarm TRAP-TYPE
	ENTERPRISE	comet
	VARIABLES	{ sensorName, messageString, co2, co2AlarmInt }
	DESCRIPTION
		"Trap for low alarm on CO2 level"
	::= 24

trapCo2ClrAlarm TRAP-TYPE
	ENTERPRISE	comet
	VARIABLES	{ sensorName, messageString, co2, co2AlarmInt }
	DESCRIPTION
		"Trap for clearing alarm on CO2 level"
	::= 34

trapCo2Error TRAP-TYPE
	ENTERPRISE	comet
	VARIABLES	{ sensorName, messageString, co2, co2AlarmInt }
	DESCRIPTION
		"Trap for error on CO2 level"
	::= 44


END
