-----------------------------------------------------------------------
-- MIB table for P2520
--
-- v2.0 for firmware 7-5-0.x, 2016-04-22
-----------------------------------------------------------------------
P2520-MIB DEFINITIONS ::= BEGIN


IMPORTS
	enterprises
		FROM RFC1155-SMI
	OBJECT-TYPE
		FROM RFC-1212;

  DisplayString ::= OCTET STRING


comet         OBJECT IDENTIFIER ::= { enterprises 22626 }
products      OBJECT IDENTIFIER ::= { comet 1 }
p2520         OBJECT IDENTIFIER ::= { products 6 }
global        OBJECT IDENTIFIER ::= { p2520 1 }
channels      OBJECT IDENTIFIER ::= { p2520 2 }
channel1      OBJECT IDENTIFIER ::= { channels 1 }
channel2      OBJECT IDENTIFIER ::= { channels 2 }
traps         OBJECT IDENTIFIER ::= { p2520 3 }


-----------------------------------------------------------------------
-- global
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- channels
-----------------------------------------------------------------------

-----------------------------------------------------------------------
-- channel1
-----------------------------------------------------------------------
ch1Name OBJECT-TYPE
	SYNTAX		DisplayString (SIZE (0..20))
	ACCESS		read-only
	STATUS		mandatory
	DESCRIPTION	"Channel 1 name"
::= { channel1 1 }

ch1Unit OBJECT-TYPE
	SYNTAX		DisplayString (SIZE (0..8))
	ACCESS		read-only
	STATUS		mandatory
	DESCRIPTION	"Channel 1 unit"
::= { channel1 2 }

ch1StrVal OBJECT-TYPE
	SYNTAX		DisplayString (SIZE (0..18))
	ACCESS		read-only
	STATUS		mandatory
	DESCRIPTION	"Channel 1 value - string"
::= { channel1 3 }

ch1IntVal OBJECT-TYPE
	SYNTAX		INTEGER (-32010..32767)
	ACCESS		read-only
	STATUS		mandatory
	DESCRIPTION	"Channel 1 value - integer16bit (12 dgrC = 12, error <= -32000)"
::= { channel1 4 }

ch1Int10Val OBJECT-TYPE
	SYNTAX		INTEGER (-32010..32767)
	ACCESS		read-only
	STATUS		mandatory
	DESCRIPTION	"Channel 1 value - integer16bit*10 (12.5 dgrC = 125, error <= -32000)"
::= { channel1 5 }

ch1Int100Val OBJECT-TYPE
	SYNTAX		INTEGER (-32010..32767)
	ACCESS		read-only
	STATUS		mandatory
	DESCRIPTION	"Channel 1 value - integer16bit*100 (12.53 dgrC = 1253, error <= -32000)"
::= { channel1 6 }

ch1DwVal OBJECT-TYPE
	SYNTAX		INTEGER (-320000010..2147483647)
	ACCESS		read-only
	STATUS		mandatory
	DESCRIPTION	"Channel 1 value - integer32bit (12 dgrC = 12, error <= -320000000)"
::= { channel1 7 }

ch1Dw10Val OBJECT-TYPE
	SYNTAX		INTEGER (-320000010..2147483647)
	ACCESS		read-only
	STATUS		mandatory
	DESCRIPTION	"Channel 1 value - integer32bit*10 (12.5 dgrC = 125, error <= -320000000)"
::= { channel1 8 }

ch1Dw100Val OBJECT-TYPE
	SYNTAX		INTEGER (-320000010..2147483647)
	ACCESS		read-only
	STATUS		mandatory
	DESCRIPTION	"Channel 1 value - integer32bit*100 (12.53 dgrC = 1253, error <= -320000000)"
::= { channel1 9 }

ch1StrCurrent OBJECT-TYPE
	SYNTAX		DisplayString (SIZE (0..18))
	ACCESS		read-only
	STATUS		mandatory
	DESCRIPTION	"Channel 1 current [mA] - string"
::= { channel1 10 }

ch1IntCurrent OBJECT-TYPE
	SYNTAX		INTEGER (-32010..32767)
	ACCESS		read-only
	STATUS		mandatory
	DESCRIPTION	"Channel 1 current [uA] - integer (120uA = 120, error <= -32000)"
::= { channel1 11 }

ch1IntAlarm OBJECT-TYPE
	SYNTAX		INTEGER (0..2)
	ACCESS		read-only
	STATUS		mandatory
	DESCRIPTION	"Alarm on channel 1; 0 - No alarm, 1 - Alarm High, 2 - Alarm Low"
::= { channel1 12 }

ch1StrAlarm OBJECT-TYPE
	SYNTAX		DisplayString (SIZE (0..8))
	ACCESS		read-only
	STATUS		mandatory
	DESCRIPTION	"Alarm on channel 1; none, high, low"
::= { channel1 13 }


-----------------------------------------------------------------------
-- channel2
-----------------------------------------------------------------------
ch2Name OBJECT-TYPE
	SYNTAX		DisplayString (SIZE (0..20))
	ACCESS		read-only
	STATUS		mandatory
	DESCRIPTION	"Channel 2 name"
::= { channel2 1 }

ch2Unit OBJECT-TYPE
	SYNTAX		DisplayString (SIZE (0..8))
	ACCESS		read-only
	STATUS		mandatory
	DESCRIPTION	"Channel 2 unit"
::= { channel2 2 }

ch2StrVal OBJECT-TYPE
	SYNTAX		DisplayString (SIZE (0..18))
	ACCESS		read-only
	STATUS		mandatory
	DESCRIPTION	"Channel 2 value - string"
::= { channel2 3 }

ch2IntVal OBJECT-TYPE
	SYNTAX		INTEGER (-32010..32767)
	ACCESS		read-only
	STATUS		mandatory
	DESCRIPTION	"Channel 2 value - integer16bit (12 dgrC = 12, error <= -32000)"
::= { channel2 4 }

ch2Int10Val OBJECT-TYPE
	SYNTAX		INTEGER (-32010..32767)
	ACCESS		read-only
	STATUS		mandatory
	DESCRIPTION	"Channel 2 value - integer16bit*10 (12.5 dgrC = 125, error <= -32000)"
::= { channel2 5 }

ch2Int100Val OBJECT-TYPE
	SYNTAX		INTEGER (-32010..32767)
	ACCESS		read-only
	STATUS		mandatory
	DESCRIPTION	"Channel 2 value - integer16bit*100 (12.53 dgrC = 1253, error <= -32000)"
::= { channel2 6 }

ch2DwVal OBJECT-TYPE
	SYNTAX		INTEGER (-320000010..2147483647)
	ACCESS		read-only
	STATUS		mandatory
	DESCRIPTION	"Channel 2 value - integer32bit (12 dgrC = 12, error <= -320000000)"
::= { channel2 7 }

ch2Dw10Val OBJECT-TYPE
	SYNTAX		INTEGER (-320000010..2147483647)
	ACCESS		read-only
	STATUS		mandatory
	DESCRIPTION	"Channel 2 value - integer32bit*10 (12.5 dgrC = 125, error <= -320000000)"
::= { channel2 8 }

ch2Dw100Val OBJECT-TYPE
	SYNTAX		INTEGER (-320000010..2147483647)
	ACCESS		read-only
	STATUS		mandatory
	DESCRIPTION	"Channel 2 value - integer32bit*100 (12.53 dgrC = 1253, error <= -320000000)"
::= { channel2 9 }

ch2StrCurrent OBJECT-TYPE
	SYNTAX		DisplayString (SIZE (0..18))
	ACCESS		read-only
	STATUS		mandatory
	DESCRIPTION	"Channel 2 current [mA] - string"
::= { channel2 10 }

ch2IntCurrent OBJECT-TYPE
	SYNTAX		INTEGER (-32010..32767)
	ACCESS		read-only
	STATUS		mandatory
	DESCRIPTION	"Channel 2 current [uA] - integer (120uA = 120, error <= -32000)"
::= { channel2 11 }

ch2IntAlarm OBJECT-TYPE
	SYNTAX		INTEGER (0..2)
	ACCESS		read-only
	STATUS		mandatory
	DESCRIPTION	"Alarm on channel 2; 0 - No alarm, 1 - Alarm High, 2 - Alarm Low"
::= { channel2 12 }

ch2StrAlarm OBJECT-TYPE
	SYNTAX		DisplayString (SIZE (0..8))
	ACCESS		read-only
	STATUS		mandatory
	DESCRIPTION	"Alarm on channel 2; none, high, low"
::= { channel2 13 }


-----------------------------------------------------------------------
-- traps
-----------------------------------------------------------------------
messageString OBJECT-TYPE
	SYNTAX		DisplayString (SIZE (0..32))
	ACCESS		read-only
	STATUS		mandatory
	DESCRIPTION	"Message giving more detailed information on alarms"
::= { traps 1 }


END
