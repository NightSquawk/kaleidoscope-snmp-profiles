-----------------------------------------------------------------------
-- MIB table for Multilogger
-- SNMP version 2.0
--
-- Date: 2016-04-22
-----------------------------------------------------------------------
MULTILOGGER-MIB DEFINITIONS ::= BEGIN


IMPORTS
  enterprises, IpAddress, Counter, TimeTicks
    FROM RFC1155-SMI
  OBJECT-TYPE
    FROM RFC-1212
  DisplayString
    FROM RFC-1213;

comet        OBJECT IDENTIFIER ::= { enterprises 22626 }
products     OBJECT IDENTIFIER ::= { comet 1 }
multilogger  OBJECT IDENTIFIER ::= { products 7 }
device       OBJECT IDENTIFIER ::= { multilogger 1 }
channels     OBJECT IDENTIFIER ::= { multilogger 2 }
global       OBJECT IDENTIFIER ::= { multilogger 3 }


-----------------------------------------------------------------------
-- device
-----------------------------------------------------------------------

deviceName OBJECT-TYPE
	SYNTAX		DisplayString (SIZE (0..32))
	ACCESS		read-only
	STATUS		mandatory
	DESCRIPTION	"Device name"
::= { device 1 }

serialNo OBJECT-TYPE
	SYNTAX		DisplayString (SIZE (0..8))
	ACCESS		read-only
	STATUS		mandatory
	DESCRIPTION	"Device serial number"
::= { device 2 }

deviceType OBJECT-TYPE
	SYNTAX		INTEGER(0..255)
	ACCESS		read-only
	STATUS		mandatory
	DESCRIPTION	"Device model identification"
::= { device 3 }

deviceModel OBJECT-TYPE
	SYNTAX		DisplayString (SIZE (0..8))
	ACCESS		read-only
	STATUS		mandatory
	DESCRIPTION	"Device model name"
::= { device 4 }


-----------------------------------------------------------------------
-- channels
-----------------------------------------------------------------------

chTable OBJECT-TYPE
	SYNTAX  SEQUENCE OF chEntry
	ACCESS  not-accessible
	STATUS  mandatory
	DESCRIPTION	"Channels information table"
::= { channels 1 }

chEntry OBJECT-TYPE
	SYNTAX  chEntry
	ACCESS  not-accessible
	STATUS  optional
  DESCRIPTION	"Channels values entries"
	INDEX   { channelIndex }
::= { chTable 1 }

chEntry ::=
	SEQUENCE {
		channelIndex
			INTEGER,
		inputName
			OCTET STRING,
		channelName
			OCTET STRING,
		channelValue
			OCTET STRING,
		channelValueInt
			INTEGER,
		decPointNr
			INTEGER,
		channelUnit
			OCTET STRING,
		channelAlarm1
			INTEGER,
		channelAlarm2
			INTEGER,
		channelMinValue
			OCTET STRING,
		channelMaxValue
			OCTET STRING
		}

channelIndex OBJECT-TYPE
	SYNTAX		INTEGER(1..16)
	ACCESS		read-only
	STATUS		mandatory
	DESCRIPTION	"Channel index"
::= { chEntry 1 }

inputName OBJECT-TYPE
	SYNTAX		DisplayString (SIZE (0..16))
	ACCESS		read-only
	STATUS		mandatory
	DESCRIPTION	"Input name"
::= { chEntry 2 }

channelName OBJECT-TYPE
	SYNTAX		DisplayString (SIZE (0..4))
	ACCESS		read-only
	STATUS		mandatory
	DESCRIPTION	"Channel name"
::= { chEntry 3 }

channelValue OBJECT-TYPE
	SYNTAX		DisplayString (SIZE (0..18))
	ACCESS		read-only
	STATUS		mandatory
	DESCRIPTION	"Channel value - string"
::= { chEntry 4 }

channelValueInt OBJECT-TYPE
	SYNTAX		INTEGER
	ACCESS		read-only
	STATUS		mandatory
	DESCRIPTION	"Channel value - integer (number of decimal places in next OID, error code set to -320000000 and lower)"
::= { chEntry 5 }

decPointNr OBJECT-TYPE
	SYNTAX		INTEGER
	ACCESS		read-only
	STATUS		mandatory
	DESCRIPTION	"Number of decimal places"
::= { chEntry 6 }

channelUnit OBJECT-TYPE
	SYNTAX		DisplayString (SIZE (0..6))
	ACCESS		read-only
	STATUS		mandatory
	DESCRIPTION	"Channel unit"
::= { chEntry 7 }

channelAlarm1 OBJECT-TYPE
	SYNTAX		INTEGER(0..1)
	ACCESS		read-only
	STATUS		mandatory
	DESCRIPTION	"Alarm 1 state (1=alarm active, 0=none)"
::= { chEntry 8 }

channelAlarm2 OBJECT-TYPE
	SYNTAX		INTEGER(0..1)
	ACCESS		read-only
	STATUS		mandatory
	DESCRIPTION	"Alarm 2 state (1=alarm active, 0=none)"
::= { chEntry 9 }

channelMinValue OBJECT-TYPE
	SYNTAX		DisplayString (SIZE (0..18))
	ACCESS		read-only
	STATUS		mandatory
	DESCRIPTION	"Min value - string"
::= { chEntry 10 }

channelMaxValue OBJECT-TYPE
	SYNTAX		DisplayString (SIZE (0..18))
	ACCESS		read-only
	STATUS		mandatory
	DESCRIPTION	"Max value - string"
::= { chEntry 11 }


-----------------------------------------------------------------------
-- global
-----------------------------------------------------------------------

recordOn OBJECT-TYPE
	SYNTAX		INTEGER(0..1)
	ACCESS		read-only
	STATUS		mandatory
	DESCRIPTION	"Device is recording"
::= { global 1 }

selftestError OBJECT-TYPE
	SYNTAX		INTEGER(0..1)
	ACCESS		read-only
	STATUS		mandatory
	DESCRIPTION	"Selftest error"
::= { global 2 }

alarmOut OBJECT-TYPE
	SYNTAX		INTEGER(0..255)
	ACCESS		read-only
	STATUS		mandatory
	DESCRIPTION	"Alarm OUT state"
::= { global 3 }

accoustic OBJECT-TYPE
	SYNTAX		INTEGER(0..255)
	ACCESS		read-only
	STATUS		mandatory
	DESCRIPTION	"Audio alarm state"
::= { global 4 }

memoryOccupation OBJECT-TYPE
	SYNTAX		INTEGER(0..255)
	ACCESS		read-only
	STATUS		mandatory
	DESCRIPTION	"Percent of memory occupation"
::= { global 5 }

batteryCapacity OBJECT-TYPE
	SYNTAX		INTEGER(0..255)
	ACCESS		read-only
	STATUS		mandatory
	DESCRIPTION	"Battery capacity [%]"
::= { global 6 }


END
