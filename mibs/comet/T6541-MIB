-----------------------------------------------------------------------
-- MIB table for T6541
--
-- v3.0 for firmware 1-5-7-2, 2016-04-11
-----------------------------------------------------------------------
T6541-MIB DEFINITIONS ::= BEGIN


IMPORTS
	enterprises
		FROM RFC1155-SMI
	OBJECT-TYPE
		FROM RFC-1212
	TRAP-TYPE
		FROM RFC-1215;

  DisplayString ::= OCTET STRING


comet      OBJECT IDENTIFIER ::= { enterprises 22626 }
products   OBJECT IDENTIFIER ::= { comet 1 }
t6541      OBJECT IDENTIFIER ::= { products 2 }
values     OBJECT IDENTIFIER ::= { t6541 1 }
global     OBJECT IDENTIFIER ::= { t6541 2 }
valuesInt  OBJECT IDENTIFIER ::= { t6541 3 }
settings   OBJECT IDENTIFIER ::= { t6541 4 }
traps      OBJECT IDENTIFIER ::= { t6541 5 }
tables	   OBJECT IDENTIFIER ::= { t6541 6 }


-----------------------------------------------------------------------
-- Measured values - String
-----------------------------------------------------------------------
temp OBJECT-TYPE
	SYNTAX		DisplayString (SIZE (0..8))
	ACCESS		read-only
	STATUS		mandatory
	DESCRIPTION	"Temperature"
::= { values 1 }

hum OBJECT-TYPE
	SYNTAX		DisplayString (SIZE (0..8))
	ACCESS		read-only
	STATUS		mandatory
	DESCRIPTION	"Relative humidity"
::= { values 2 }

compVal OBJECT-TYPE
	SYNTAX		DisplayString (SIZE (0..8))
	ACCESS		read-only
	STATUS		mandatory
	DESCRIPTION	"Computed value"
::= { values 3 }

co2 OBJECT-TYPE
	SYNTAX		DisplayString (SIZE (0..8))
	ACCESS		read-only
	STATUS		mandatory
	DESCRIPTION	"CO2 level"
::= { values 4 }

tempAlarm OBJECT-TYPE
	SYNTAX		DisplayString (SIZE (0..8))
	ACCESS		read-only
	STATUS		mandatory
	DESCRIPTION	"Alarm on Temperature; none, high, low"
::= { values 5 }

humAlarm OBJECT-TYPE
	SYNTAX		DisplayString (SIZE (0..8))
	ACCESS		read-only
	STATUS		mandatory
	DESCRIPTION	"Alarm on Relative humidity; none, high, low"
::= { values 6 }

compValAlarm OBJECT-TYPE
	SYNTAX		DisplayString (SIZE (0..8))
	ACCESS		read-only
	STATUS		mandatory
	DESCRIPTION	"Alarm on Computed value; none, high, low"
::= { values 7 }

co2Alarm OBJECT-TYPE
	SYNTAX		DisplayString (SIZE (0..8))
	ACCESS		read-only
	STATUS		mandatory
	DESCRIPTION	"Alarm on CO2; none, high, low"
::= { values 8 }

tempUnit OBJECT-TYPE
	SYNTAX  	DisplayString (SIZE (0..8))
	ACCESS		read-only
	STATUS		mandatory
	DESCRIPTION	"Temperature Unit"
::= { values 9 }

humUnit OBJECT-TYPE
	SYNTAX  	DisplayString (SIZE (0..8))
	ACCESS		read-only
	STATUS		mandatory
	DESCRIPTION	"Relative humidity Unit"
::= { values 10 }

compValUnit OBJECT-TYPE
	SYNTAX  	DisplayString (SIZE (0..8))
	ACCESS		read-only
	STATUS		mandatory
	DESCRIPTION	"Computed value Unit"
::= { values 11 }

co2Unit OBJECT-TYPE
	SYNTAX  	DisplayString (SIZE (0..8))
	ACCESS		read-only
	STATUS		mandatory
	DESCRIPTION	"CO2 Unit"
::= { values 12 }

tempMin OBJECT-TYPE
	SYNTAX  	DisplayString (SIZE (0..8))
	ACCESS		read-only
	STATUS		mandatory
	DESCRIPTION	"Minimal temperature"
::= { values 13 }

humMin OBJECT-TYPE
	SYNTAX  	DisplayString (SIZE (0..8))
	ACCESS		read-only
	STATUS		mandatory
	DESCRIPTION	"Minimal relative humidity"
::= { values 14 }

compValMin OBJECT-TYPE
	SYNTAX  	DisplayString (SIZE (0..8))
	ACCESS		read-only
	STATUS		mandatory
	DESCRIPTION	"Minimal computed value"
::= { values 15 }

co2Min OBJECT-TYPE
	SYNTAX  	DisplayString (SIZE (0..8))
	ACCESS		read-only
	STATUS		mandatory
	DESCRIPTION	"Minimal CO2 level"
::= { values 16 }

tempMax OBJECT-TYPE
	SYNTAX  	DisplayString (SIZE (0..8))
	ACCESS		read-only
	STATUS		mandatory
	DESCRIPTION	"Maximal temperature"
::= { values 17 }

humMax OBJECT-TYPE
	SYNTAX  	DisplayString (SIZE (0..8))
	ACCESS		read-only
	STATUS		mandatory
	DESCRIPTION	"Maximal relative humidity"
::= { values 18 }

compValMax OBJECT-TYPE
	SYNTAX  	DisplayString (SIZE (0..8))
	ACCESS		read-only
	STATUS		mandatory
	DESCRIPTION	"Maximal computed value"
::= { values 19 }

co2Max OBJECT-TYPE
	SYNTAX  	DisplayString (SIZE (0..8))
	ACCESS		read-only
	STATUS		mandatory
	DESCRIPTION	"Maximal CO2 level"
::= { values 20 }


-----------------------------------------------------------------------
-- Device informations
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- Measured values - Integer
-----------------------------------------------------------------------
tempInt OBJECT-TYPE
	SYNTAX		INTEGER (-5000..20000)
	ACCESS		read-only
	STATUS		mandatory
	DESCRIPTION	"Temperature (value*10)"
::= { valuesInt 1 }

humInt OBJECT-TYPE
	SYNTAX		INTEGER (-5000..20000)
	ACCESS		read-only
	STATUS		mandatory
	DESCRIPTION	"Relative humidity (value*10)"
::= { valuesInt 2 }

compValInt OBJECT-TYPE
	SYNTAX		INTEGER (-5000..20000)
	ACCESS		read-only
	STATUS		mandatory
	DESCRIPTION	"Computed value (value*10)"
::= { valuesInt 3 }

co2Int OBJECT-TYPE
	SYNTAX		INTEGER (-5000..20000)
	ACCESS		read-only
	STATUS		mandatory
	DESCRIPTION	"CO2 level"
::= { valuesInt 4 }

tempAlarmInt OBJECT-TYPE
	SYNTAX		INTEGER (0..2)
	ACCESS		read-only
	STATUS		mandatory
	DESCRIPTION	"Alarm on Temperature; 0 - No, 1 - High, 2 - Low"
::= { valuesInt 5 }

humAlarmInt OBJECT-TYPE
	SYNTAX		INTEGER (0..2)
	ACCESS		read-only
	STATUS		mandatory
	DESCRIPTION	"Alarm on Relative humidity; 0 - No, 1 - High, 2 - Low"
::= { valuesInt 6 }

compValAlarmInt OBJECT-TYPE
	SYNTAX		INTEGER (0..2)
	ACCESS		read-only
	STATUS		mandatory
	DESCRIPTION	"Alarm on Computed value; 0 - No, 1 - High, 2 - Low"
::= { valuesInt 7 }

co2AlarmInt OBJECT-TYPE
	SYNTAX		INTEGER (0..2)
	ACCESS		read-only
	STATUS		mandatory
	DESCRIPTION	"Alarm on CO2; 0 - No, 1 - High, 2 - Low"
::= { valuesInt 8 }


-----------------------------------------------------------------------
-- Alarm settings
-----------------------------------------------------------------------
tempLowInt OBJECT-TYPE
	SYNTAX		INTEGER (-5000..20000)
	ACCESS		read-only
	STATUS		mandatory
	DESCRIPTION	"Temperature Limit Low (value*10)"
::= { settings 1 }

tempHighInt OBJECT-TYPE
	SYNTAX		INTEGER (-5000..20000)
	ACCESS		read-only
	STATUS		mandatory
	DESCRIPTION	"Temperature Limit High (value*10)"
::= { settings 2 }

humLowInt OBJECT-TYPE
	SYNTAX		INTEGER (-5000..20000)
	ACCESS		read-only
	STATUS		mandatory
	DESCRIPTION	"Humidity Limit Low (value*10)"
::= { settings 3 }

humHighInt OBJECT-TYPE
	SYNTAX		INTEGER (-5000..20000)
	ACCESS		read-only
	STATUS		mandatory
	DESCRIPTION	"Humidity Limit High (value*10)"
::= { settings 4 }

compValLowInt OBJECT-TYPE
	SYNTAX		INTEGER (-5000..20000)
	ACCESS		read-only
	STATUS		mandatory
	DESCRIPTION	"Computed value Limit Low (value*10)"
::= { settings 5 }

compValHighInt OBJECT-TYPE
	SYNTAX		INTEGER (-5000..20000)
	ACCESS		read-only
	STATUS		mandatory
	DESCRIPTION	"Computed value Limit High (value*10)"
::= { settings 6 }

tempDelayInt OBJECT-TYPE
	SYNTAX		INTEGER (0..4500)
	ACCESS		read-only
	STATUS		mandatory
	DESCRIPTION	"Temperature alaram delay [sec]"
::= { settings 7 }

humDelayInt OBJECT-TYPE
	SYNTAX		INTEGER (0..4500)
	ACCESS		read-only
	STATUS		mandatory
	DESCRIPTION	"Humidity alaram delay [sec]"
::= { settings 8 }

compValDelayInt OBJECT-TYPE
	SYNTAX		INTEGER (0..4500)
	ACCESS		read-only
	STATUS		mandatory
	DESCRIPTION	"Computed value alaram delay [sec]"
::= { settings 9 }

tempHystInt OBJECT-TYPE
	SYNTAX		INTEGER (0..10000)
	ACCESS		read-only
	STATUS		mandatory
	DESCRIPTION	"Temperature hysteresis (value*10)"
::= { settings 10 }

humHystInt OBJECT-TYPE
	SYNTAX		INTEGER (0..10000)
	ACCESS		read-only
	STATUS		mandatory
	DESCRIPTION	"Humidity hysteresis (value*10)"
::= { settings 11 }

compValHystInt OBJECT-TYPE
	SYNTAX		INTEGER (0..10000)
	ACCESS		read-only
	STATUS		mandatory
	DESCRIPTION	"Computed value hysteresis (value*10)"
::= { settings 12 }

co2LowInt OBJECT-TYPE
	SYNTAX		INTEGER (-5000..20000)
	ACCESS		read-only
	STATUS		mandatory
	DESCRIPTION	"CO2 Limit Low"
::= { settings 13 }

co2HighInt OBJECT-TYPE
	SYNTAX		INTEGER (-5000..20000)
	ACCESS		read-only
	STATUS		mandatory
	DESCRIPTION	"CO2 Limit High"
::= { settings 14 }

co2DelayInt OBJECT-TYPE
	SYNTAX		INTEGER (0..4500)
	ACCESS		read-only
	STATUS		mandatory
	DESCRIPTION	"CO2 alaram delay [sec]"
::= { settings 15 }

co2HystInt OBJECT-TYPE
	SYNTAX		INTEGER (0..10000)
	ACCESS		read-only
	STATUS		mandatory
	DESCRIPTION	"CO2 hysteresis"
::= { settings 16 }


-----------------------------------------------------------------------
-- Trap message
-----------------------------------------------------------------------
messageString OBJECT-TYPE
	SYNTAX		DisplayString (SIZE (0..32))
	ACCESS		read-only
	STATUS		mandatory
	DESCRIPTION	"Message giving more detailed information on alarms"
::= { traps 1 }


-----------------------------------------------------------------------
-- Tables
-----------------------------------------------------------------------
historyTable OBJECT-TYPE
	SYNTAX		SEQUENCE OF HistoryEntry
	ACCESS		not-accessible
	STATUS		mandatory
	DESCRIPTION	"Table of the history values"
::= { tables 1 }

historyEntry OBJECT-TYPE
	SYNTAX		HistoryEntry
	ACCESS		not-accessible
	STATUS		optional
	DESCRIPTION	"History values entries"
	INDEX		{ histTemp }
::= { historyTable 1 }

HistoryEntry ::=
	SEQUENCE {
		histTemp
			INTEGER,
		histHum
			INTEGER,
		histCompVal
			INTEGER,
		histCO2
			INTEGER
		}

histTemp OBJECT-TYPE
	SYNTAX		INTEGER(-5000..20000)
	ACCESS		read-only
	STATUS		mandatory
	DESCRIPTION	"Temperature reading"
::= { historyEntry 1 }

histHum OBJECT-TYPE
	SYNTAX		INTEGER(-5000..20000)
	ACCESS		read-only
	STATUS		mandatory
	DESCRIPTION	"Humidity reading"
::= { historyEntry 2 }

histCompVal OBJECT-TYPE
	SYNTAX		INTEGER (-5000..20000)
	ACCESS		read-only
	STATUS		mandatory
	DESCRIPTION	"Computed value reading"
::= { historyEntry 3 }

histCO2 OBJECT-TYPE
	SYNTAX		INTEGER(-5000..20000)
	ACCESS		read-only
	STATUS		mandatory
	DESCRIPTION	"CO2 level reading"
::= { historyEntry 4 }


-----------------------------------------------------------------------
-- Traps definition
-----------------------------------------------------------------------

trapTest TRAP-TYPE
	ENTERPRISE	comet
	VARIABLES	{ sensorName, messageString }
	DESCRIPTION
		"Testing trap, testing trap by TSensor software"
	::= 0

trapNTPError TRAP-TYPE
	ENTERPRISE	comet
	VARIABLES	{ sensorName, messageString }
	DESCRIPTION
		"Error on time synchronisation via NTP"
	::= 1

trapEmailErrLogin TRAP-TYPE
	ENTERPRISE	comet
	VARIABLES	{ sensorName, messageString }
	DESCRIPTION
		"SMTP error - unknown server"
	::= 2

trapEmailErrAuth TRAP-TYPE
	ENTERPRISE	comet
	VARIABLES	{ sensorName, messageString }
	DESCRIPTION
		"SMTP error - authentication error"
	::= 3

trapEmailErrSome TRAP-TYPE
	ENTERPRISE	comet
	VARIABLES	{ sensorName, messageString }
	DESCRIPTION
		"SMTP error - error during communication with server, unexpected return code"
	::= 4

trapEmailErrSocket TRAP-TYPE
	ENTERPRISE	comet
	VARIABLES	{ sensorName, messageString }
	DESCRIPTION
		"SMTP error - socket error, server is not available"
	::= 5

trapEmailErrDNS TRAP-TYPE
	ENTERPRISE	comet
	VARIABLES	{ sensorName, messageString }
	DESCRIPTION
		"SMTP error - DNS error"
	::= 6

trapSOAPErrFile TRAP-TYPE
	ENTERPRISE	comet
	VARIABLES	{ sensorName, messageString }
	DESCRIPTION
		"SOAP error - file SOAP not found"
	::= 7

trapSOAPErrDNS TRAP-TYPE
	ENTERPRISE	comet
	VARIABLES	{ sensorName, messageString }
	DESCRIPTION
		"SOAP error - DNS error"
	::= 8

trapSOAPErrSocket TRAP-TYPE
	ENTERPRISE	comet
	VARIABLES	{ sensorName, messageString }
	DESCRIPTION
		"SOAP error - socket error, server is not available"
	::= 9

trapSOAPErrDelivery TRAP-TYPE
	ENTERPRISE	comet
	VARIABLES	{ sensorName, messageString }
	DESCRIPTION
		"SOAP error - delivery error, wrong return code from server"
	::= 10

trapTempHighAlarm TRAP-TYPE
	ENTERPRISE	comet
	VARIABLES	{ sensorName, messageString, temp, tempAlarmInt }
	DESCRIPTION
		"Trap for high alarm on temperature"
	::= 11

trapHumHighAlarm TRAP-TYPE
	ENTERPRISE	comet
	VARIABLES	{ sensorName, messageString, hum, humAlarmInt }
	DESCRIPTION
		"Trap for high alarm on relative humidity"
	::= 12

trapCompValHighAlarm TRAP-TYPE
	ENTERPRISE	comet
	VARIABLES	{ sensorName, messageString, compVal, compValAlarmInt }
	DESCRIPTION
		"Trap for high alarm on computed value"
	::= 13

trapCo2HighAlarm TRAP-TYPE
	ENTERPRISE	comet
	VARIABLES	{ sensorName, messageString, co2, co2AlarmInt }
	DESCRIPTION
		"Trap for high alarm on CO2 level"
	::= 14

trapTempLowAlarm TRAP-TYPE
	ENTERPRISE	comet
	VARIABLES	{ sensorName, messageString, temp, tempAlarmInt }
	DESCRIPTION
		"Trap for low alarm on temperature"
	::= 21

trapHumLowAlarm TRAP-TYPE
	ENTERPRISE	comet
	VARIABLES	{ sensorName, messageString, hum, humAlarmInt }
	DESCRIPTION
		"Trap for low alarm on relative humidity"
	::= 22

trapCompValLowAlarm TRAP-TYPE
	ENTERPRISE	comet
	VARIABLES	{ sensorName, messageString, compVal, compValAlarmInt }
	DESCRIPTION
		"Trap for low alarm on computed value"
	::= 23

trapCo2LowAlarm TRAP-TYPE
	ENTERPRISE	comet
	VARIABLES	{ sensorName, messageString, co2, co2AlarmInt }
	DESCRIPTION
		"Trap for low alarm on CO2 level"
	::= 24

trapTempClrAlarm TRAP-TYPE
	ENTERPRISE	comet
	VARIABLES	{ sensorName, messageString, temp, tempAlarmInt }
	DESCRIPTION
		"Trap for clearing alarm on temperature"
	::= 31

trapHumClrAlarm TRAP-TYPE
	ENTERPRISE	comet
	VARIABLES	{ sensorName, messageString, hum, humAlarmInt }
	DESCRIPTION
		"Trap for clearing alarm on relative humidity"
	::= 32

trapCompValClrAlarm TRAP-TYPE
	ENTERPRISE	comet
	VARIABLES	{ sensorName, messageString, compVal, compValAlarmInt }
	DESCRIPTION
		"Trap for clearing alarm on computed value"
	::= 33

trapCo2ClrAlarm TRAP-TYPE
	ENTERPRISE	comet
	VARIABLES	{ sensorName, messageString, co2, co2AlarmInt }
	DESCRIPTION
		"Trap for clearing alarm on CO2 level"
	::= 34

trapTempError TRAP-TYPE
	ENTERPRISE	comet
	VARIABLES	{ sensorName, messageString, temp, tempAlarmInt }
	DESCRIPTION
		"Trap for error on temperature"
	::= 41

trapHumError TRAP-TYPE
	ENTERPRISE	comet
	VARIABLES	{ sensorName, messageString, hum, humAlarmInt }
	DESCRIPTION
		"Trap for error on relative humidity"
	::= 42

trapCompValError TRAP-TYPE
	ENTERPRISE	comet
	VARIABLES	{ sensorName, messageString, compVal, compValAlarmInt }
	DESCRIPTION
		"Trap for error on computed value"
	::= 43

trapCo2Error TRAP-TYPE
	ENTERPRISE	comet
	VARIABLES	{ sensorName, messageString, co2, co2AlarmInt }
	DESCRIPTION
		"Trap for error on CO2 level"
	::= 44


END
