-----------------------------------------------------------------------
-- MIB table for H3531
--
-- v1.0 for firmware 9-5-0-0, 2017-04-19
-----------------------------------------------------------------------
H3531-MIB DEFINITIONS ::= BEGIN


IMPORTS
	enterprises
		FROM RFC1155-SMI
	OBJECT-TYPE
		FROM RFC-1212
	TRAP-TYPE
		FROM RFC-1215;

  DisplayString ::= OCTET STRING


comet      OBJECT IDENTIFIER ::= { enterprises 22626 }
products   OBJECT IDENTIFIER ::= { comet 1 }
h3531      OBJECT IDENTIFIER ::= { products 2 }
values     OBJECT IDENTIFIER ::= { h3531 1 }
global     OBJECT IDENTIFIER ::= { h3531 2 }
valuesInt  OBJECT IDENTIFIER ::= { h3531 3 }
settings   OBJECT IDENTIFIER ::= { h3531 4 }
traps      OBJECT IDENTIFIER ::= { h3531 5 }
tables	   OBJECT IDENTIFIER ::= { h3531 6 }


-----------------------------------------------------------------------
-- Measured values - String
-----------------------------------------------------------------------
temp OBJECT-TYPE
	SYNTAX		DisplayString (SIZE (0..8))
	ACCESS		read-only
	STATUS		mandatory
	DESCRIPTION	"Temperature"
::= { values 1 }

hum OBJECT-TYPE
	SYNTAX		DisplayString (SIZE (0..8))
	ACCESS		read-only
	STATUS		mandatory
	DESCRIPTION	"Relative humidity"
::= { values 2 }

compVal OBJECT-TYPE
	SYNTAX		DisplayString (SIZE (0..8))
	ACCESS		read-only
	STATUS		mandatory
	DESCRIPTION	"Computed value"
::= { values 3 }

bin1 OBJECT-TYPE
	SYNTAX  	DisplayString (SIZE (0..8))
	ACCESS		read-only
	STATUS		mandatory
	DESCRIPTION	"BIN Input 1 state; 0 state description, 1 state description"
::= { values 5 }

bin2 OBJECT-TYPE
	SYNTAX  	DisplayString (SIZE (0..8))
	ACCESS		read-only
	STATUS		mandatory
	DESCRIPTION	"BIN Input 2 state; 0 state description, 1 state description"
::= { values 6 }

bin3 OBJECT-TYPE
	SYNTAX  	DisplayString (SIZE (0..8))
	ACCESS		read-only
	STATUS		mandatory
	DESCRIPTION	"BIN Input 3 state; 0 state description, 1 state description"
::= { values 7 }

re1 OBJECT-TYPE
	SYNTAX  	DisplayString (SIZE (0..8))
	ACCESS		read-only
	STATUS		mandatory
	DESCRIPTION	"Relay 1 state; open, closed"
::= { values 8 }

re2 OBJECT-TYPE
	SYNTAX  	DisplayString (SIZE (0..8))
	ACCESS		read-only
	STATUS		mandatory
	DESCRIPTION	"Relay 2 state; open, closed"
::= { values 9 }

tempAlarm1 OBJECT-TYPE
	SYNTAX		DisplayString (SIZE (0..8))
	ACCESS		read-only
	STATUS		mandatory
	DESCRIPTION	"Alarm1 on Temperature; none, active"
::= { values 10 }

humAlarm1 OBJECT-TYPE
	SYNTAX		DisplayString (SIZE (0..8))
	ACCESS		read-only
	STATUS		mandatory
	DESCRIPTION	"Alarm1 on Relative humidity; none, active"
::= { values 11 }

compValAlarm1 OBJECT-TYPE
	SYNTAX		DisplayString (SIZE (0..8))
	ACCESS		read-only
	STATUS		mandatory
	DESCRIPTION	"Alarm1 on Computed value; none, active"
::= { values 12 }

tempAlarm2 OBJECT-TYPE
	SYNTAX		DisplayString (SIZE (0..8))
	ACCESS		read-only
	STATUS		mandatory
	DESCRIPTION	"Alarm2 on Temperature; none, active"
::= { values 14 }

humAlarm2 OBJECT-TYPE
	SYNTAX		DisplayString (SIZE (0..8))
	ACCESS		read-only
	STATUS		mandatory
	DESCRIPTION	"Alarm2 on Relative humidity; none, active"
::= { values 15 }

compValAlarm2 OBJECT-TYPE
	SYNTAX		DisplayString (SIZE (0..8))
	ACCESS		read-only
	STATUS		mandatory
	DESCRIPTION	"Alarm2 on Computed value; none, active"
::= { values 16 }

bin1Alarm OBJECT-TYPE
	SYNTAX  	DisplayString (SIZE (0..8))
	ACCESS		read-only
	STATUS		mandatory
	DESCRIPTION	"Alarm on BIN Input 1; none, active"
::= { values 18 }

bin2Alarm OBJECT-TYPE
	SYNTAX  	DisplayString (SIZE (0..8))
	ACCESS		read-only
	STATUS		mandatory
	DESCRIPTION	"Alarm on BIN Input 2; none, active"
::= { values 19 }

bin3Alarm OBJECT-TYPE
	SYNTAX  	DisplayString (SIZE (0..8))
	ACCESS		read-only
	STATUS		mandatory
	DESCRIPTION	"Alarm on BIN Input 3; none, active"
::= { values 20 }

tempUnit OBJECT-TYPE
	SYNTAX  	DisplayString (SIZE (0..8))
	ACCESS		read-only
	STATUS		mandatory
	DESCRIPTION	"Temperature Unit"
::= { values 21 }

humUnit OBJECT-TYPE
	SYNTAX  	DisplayString (SIZE (0..8))
	ACCESS		read-only
	STATUS		mandatory
	DESCRIPTION	"Relative humidity Unit"
::= { values 22 }

compValUnit OBJECT-TYPE
	SYNTAX  	DisplayString (SIZE (0..8))
	ACCESS		read-only
	STATUS		mandatory
	DESCRIPTION	"Computed value Unit"
::= { values 23 }


-----------------------------------------------------------------------
-- Device informations
-----------------------------------------------------------------------
sensorName OBJECT-TYPE
	SYNTAX		DisplayString (SIZE (0..68))
	ACCESS		read-only
	STATUS		mandatory
	DESCRIPTION	"Device name"
::= { global 1 }

serialNumber OBJECT-TYPE
	SYNTAX		DisplayString (SIZE (0..16))
	ACCESS		read-only
	STATUS		mandatory
	DESCRIPTION	"Serial number"
::= { global 2 }

deviceType OBJECT-TYPE
	SYNTAX		INTEGER (0..65534)
	ACCESS		read-only
	STATUS		mandatory
	DESCRIPTION	"Device type"
::= { global 3 }


-----------------------------------------------------------------------
-- Measured values - Integer
-----------------------------------------------------------------------
tempInt OBJECT-TYPE
	SYNTAX		INTEGER (-5000..20000)
	ACCESS		read-only
	STATUS		mandatory
	DESCRIPTION	"Temperature (value*10)"
::= { valuesInt 1 }

humInt OBJECT-TYPE
	SYNTAX		INTEGER (-5000..20000)
	ACCESS		read-only
	STATUS		mandatory
	DESCRIPTION	"Relative humidity (value*10)"
::= { valuesInt 2 }

compValInt OBJECT-TYPE
	SYNTAX		INTEGER (-5000..20000)
	ACCESS		read-only
	STATUS		mandatory
	DESCRIPTION	"Computed value (value*10)"
::= { valuesInt 3 }

bin1Int OBJECT-TYPE
	SYNTAX		INTEGER (0..1)
	ACCESS		read-only
	STATUS		mandatory
	DESCRIPTION	"BIN Input 1 state"
::= { valuesInt 5 }

bin2Int OBJECT-TYPE
	SYNTAX		INTEGER (0..1)
	ACCESS		read-only
	STATUS		mandatory
	DESCRIPTION	"BIN Input 2 state"
::= { valuesInt 6 }

bin3Int OBJECT-TYPE
	SYNTAX		INTEGER (0..1)
	ACCESS		read-only
	STATUS		mandatory
	DESCRIPTION	"BIN Input 3 state"
::= { valuesInt 7 }

re1Int OBJECT-TYPE
	SYNTAX		INTEGER (0..1)
	ACCESS		read-only
	STATUS		mandatory
	DESCRIPTION	"Relay 1 state"
::= { valuesInt 8 }

re2Int OBJECT-TYPE
	SYNTAX		INTEGER (0..1)
	ACCESS		read-only
	STATUS		mandatory
	DESCRIPTION	"Relay 2 state"
::= { valuesInt 9 }

tempAlarm1Int OBJECT-TYPE
	SYNTAX		INTEGER (0..1)
	ACCESS		read-only
	STATUS		mandatory
	DESCRIPTION	"Alarm1 on Temperature"
::= { valuesInt 10 }

humAlarm1Int OBJECT-TYPE
	SYNTAX		INTEGER (0..1)
	ACCESS		read-only
	STATUS		mandatory
	DESCRIPTION	"Alarm1 on Relative humidity"
::= { valuesInt 11 }

compValAlarm1Int OBJECT-TYPE
	SYNTAX		INTEGER (0..1)
	ACCESS		read-only
	STATUS		mandatory
	DESCRIPTION	"Alarm1 on Computed value"
::= { valuesInt 12 }

tempAlarm2Int OBJECT-TYPE
	SYNTAX		INTEGER (0..1)
	ACCESS		read-only
	STATUS		mandatory
	DESCRIPTION	"Alarm2 on Temperature"
::= { valuesInt 14 }

humAlarm2Int OBJECT-TYPE
	SYNTAX		INTEGER (0..1)
	ACCESS		read-only
	STATUS		mandatory
	DESCRIPTION	"Alarm2 on Relative humidity"
::= { valuesInt 15 }

compValAlarm2Int OBJECT-TYPE
	SYNTAX		INTEGER (0..1)
	ACCESS		read-only
	STATUS		mandatory
	DESCRIPTION	"Alarm2 on Computed value"
::= { valuesInt 16 }

bin1AlarmInt OBJECT-TYPE
	SYNTAX		INTEGER (0..1)
	ACCESS		read-only
	STATUS		mandatory
	DESCRIPTION	"Alarm on BIN Input 1"
::= { valuesInt 18 }

bin2AlarmInt OBJECT-TYPE
	SYNTAX		INTEGER (0..1)
	ACCESS		read-only
	STATUS		mandatory
	DESCRIPTION	"Alarm on BIN Input 2"
::= { valuesInt 19 }

bin3AlarmInt OBJECT-TYPE
	SYNTAX		INTEGER (0..1)
	ACCESS		read-only
	STATUS		mandatory
	DESCRIPTION	"Alarm on BIN Input 3"
::= { valuesInt 20 }


-----------------------------------------------------------------------
-- Alarm settings
-----------------------------------------------------------------------
tempLim1Int OBJECT-TYPE
	SYNTAX		INTEGER (-5000..20000)
	ACCESS		read-only
	STATUS		mandatory
	DESCRIPTION	"Temperature Alarm1 Limit (value*10)"
::= { settings 1 }

humLim1Int OBJECT-TYPE
	SYNTAX		INTEGER (-5000..20000)
	ACCESS		read-only
	STATUS		mandatory
	DESCRIPTION	"Humidity Alarm1 Limit (value*10)"
::= { settings 2 }

compValLim1Int OBJECT-TYPE
	SYNTAX		INTEGER (-5000..20000)
	ACCESS		read-only
	STATUS		mandatory
	DESCRIPTION	"Computed Alarm1 Limit (value*10)"
::= { settings 3 }

tempLim2Int OBJECT-TYPE
	SYNTAX		INTEGER (-5000..20000)
	ACCESS		read-only
	STATUS		mandatory
	DESCRIPTION	"Temperature Alarm2 Limit (value*10)"
::= { settings 5 }

humLim2Int OBJECT-TYPE
	SYNTAX		INTEGER (-5000..20000)
	ACCESS		read-only
	STATUS		mandatory
	DESCRIPTION	"Humidity Alarm2 Limit (value*10)"
::= { settings 6 }

compValLim2Int OBJECT-TYPE
	SYNTAX		INTEGER (-5000..20000)
	ACCESS		read-only
	STATUS		mandatory
	DESCRIPTION	"Computed value Alarm2 Limit (value*10)"
::= { settings 7 }

tempHyst1Int OBJECT-TYPE
	SYNTAX		INTEGER (0..10000)
	ACCESS		read-only
	STATUS		mandatory
	DESCRIPTION	"Temperature Alarm1 Hysteresis (value*10)"
::= { settings 9 }

humHyst1Int OBJECT-TYPE
	SYNTAX		INTEGER (0..10000)
	ACCESS		read-only
	STATUS		mandatory
	DESCRIPTION	"Humidity Alarm1 Hysteresis (value*10)"
::= { settings 10 }

compValHyst1Int OBJECT-TYPE
	SYNTAX		INTEGER (0..10000)
	ACCESS		read-only
	STATUS		mandatory
	DESCRIPTION	"Computed value Alarm1 Hysteresis (value*10)"
::= { settings 11 }

tempHyst2Int OBJECT-TYPE
	SYNTAX		INTEGER (0..10000)
	ACCESS		read-only
	STATUS		mandatory
	DESCRIPTION	"Temperature Alarm2 Hysteresis (value*10)"
::= { settings 13 }

humHyst2Int OBJECT-TYPE
	SYNTAX		INTEGER (0..10000)
	ACCESS		read-only
	STATUS		mandatory
	DESCRIPTION	"Humidity Alarm2 Hysteresis (value*10)"
::= { settings 14 }

compValHyst2Int OBJECT-TYPE
	SYNTAX		INTEGER (0..10000)
	ACCESS		read-only
	STATUS		mandatory
	DESCRIPTION	"Computed value Alarm2 Hysteresis (value*10)"
::= { settings 15 }

tempDelay1Int OBJECT-TYPE
	SYNTAX		INTEGER (0..30000)
	ACCESS		read-only
	STATUS		mandatory
	DESCRIPTION	"Temperature Alarm1 Delay [sec]"
::= { settings 17 }

humDelay1Int OBJECT-TYPE
	SYNTAX		INTEGER (0..30000)
	ACCESS		read-only
	STATUS		mandatory
	DESCRIPTION	"Humidity Alarm1 Delay [sec]"
::= { settings 18 }

compValDelay1Int OBJECT-TYPE
	SYNTAX		INTEGER (0..30000)
	ACCESS		read-only
	STATUS		mandatory
	DESCRIPTION	"Computed value Alarm1 Delay [sec]"
::= { settings 19 }

tempDelay2Int OBJECT-TYPE
	SYNTAX		INTEGER (0..30000)
	ACCESS		read-only
	STATUS		mandatory
	DESCRIPTION	"Temperature Alarm2 Delay [sec]"
::= { settings 21 }

humDelay2Int OBJECT-TYPE
	SYNTAX		INTEGER (0..30000)
	ACCESS		read-only
	STATUS		mandatory
	DESCRIPTION	"Humidity Alarm2 Delay [sec]"
::= { settings 22 }

compValDelay2Int OBJECT-TYPE
	SYNTAX		INTEGER (0..30000)
	ACCESS		read-only
	STATUS		mandatory
	DESCRIPTION	"Computed value Alarm2 Delay [sec]"
::= { settings 23 }

tempType1Int OBJECT-TYPE
	SYNTAX		INTEGER (0..2)
	ACCESS		read-only
	STATUS		mandatory
	DESCRIPTION	"Temperature Alarm1 Type; 0-disbaled, 1-low, 2-high"
::= { settings 25 }

humType1Int OBJECT-TYPE
	SYNTAX		INTEGER (0..2)
	ACCESS		read-only
	STATUS		mandatory
	DESCRIPTION	"Humidity Alarm1 Type; 0-disbaled, 1-low, 2-high"
::= { settings 26 }

compValType1Int OBJECT-TYPE
	SYNTAX		INTEGER (0..2)
	ACCESS		read-only
	STATUS		mandatory
	DESCRIPTION	"Computed value Alarm1 Type; 0-disbaled, 1-low, 2-high"
::= { settings 27 }

tempType2Int OBJECT-TYPE
	SYNTAX		INTEGER (0..2)
	ACCESS		read-only
	STATUS		mandatory
	DESCRIPTION	"Temperature Alarm2 Type; 0-disbaled, 1-low, 2-high"
::= { settings 29 }

humType2Int OBJECT-TYPE
	SYNTAX		INTEGER (0..2)
	ACCESS		read-only
	STATUS		mandatory
	DESCRIPTION	"Humidity Alarm2 Type; 0-disbaled, 1-low, 2-high"
::= { settings 30 }

compValType2Int OBJECT-TYPE
	SYNTAX		INTEGER (0..2)
	ACCESS		read-only
	STATUS		mandatory
	DESCRIPTION	"Computed value Alarm2 Type; 0-disbaled, 1-low, 2-high"
::= { settings 31 }

bin1DelayInt OBJECT-TYPE
	SYNTAX		INTEGER (0..30000)
	ACCESS		read-only
	STATUS		mandatory
	DESCRIPTION	"BIN Input 1 Delay [sec]"
::= { settings 33 }

bin2DelayInt OBJECT-TYPE
	SYNTAX		INTEGER (0..30000)
	ACCESS		read-only
	STATUS		mandatory
	DESCRIPTION	"BIN Input 2 Delay [sec]"
::= { settings 34 }

bin3DelayInt OBJECT-TYPE
	SYNTAX		INTEGER (0..30000)
	ACCESS		read-only
	STATUS		mandatory
	DESCRIPTION	"BIN Input 3 Delay [sec]"
::= { settings 35 }

bin1TypeInt OBJECT-TYPE
	SYNTAX		INTEGER (0..2)
	ACCESS		read-only
	STATUS		mandatory
	DESCRIPTION	"BIN Input 1 Type; 0-disbaled, 1-low state, 2-high state"
::= { settings 36 }

bin2TypeInt OBJECT-TYPE
	SYNTAX		INTEGER (0..2)
	ACCESS		read-only
	STATUS		mandatory
	DESCRIPTION	"BIN Input 2 Type; 0-disbaled, 1-low state, 2-high state"
::= { settings 37 }

bin3TypeInt OBJECT-TYPE
	SYNTAX		INTEGER (0..2)
	ACCESS		read-only
	STATUS		mandatory
	DESCRIPTION	"BIN Input 3 Type; 0-disbaled, 1-low state, 2-high state"
::= { settings 38 }


-----------------------------------------------------------------------
-- Trap message
-----------------------------------------------------------------------
messageString OBJECT-TYPE
	SYNTAX		DisplayString (SIZE (0..32))
	ACCESS		read-only
	STATUS		mandatory
	DESCRIPTION	"Message giving more detailed information on trap"
::= { traps 1 }


-----------------------------------------------------------------------
-- Tables
-----------------------------------------------------------------------
historyTable OBJECT-TYPE
	SYNTAX		SEQUENCE OF HistoryEntry
	ACCESS		not-accessible
	STATUS		mandatory
	DESCRIPTION	"Table of the history values"
::= { tables 1 }

historyEntry OBJECT-TYPE
	SYNTAX		HistoryEntry
	ACCESS		not-accessible
	STATUS		optional
	DESCRIPTION	"History values entries"
	INDEX		{ histTemp }
::= { historyTable 1 }

HistoryEntry ::=
	SEQUENCE {
		histTemp
			INTEGER,
		histHum
			INTEGER,
		histCompVal
			INTEGER
		}

histTemp OBJECT-TYPE
	SYNTAX		INTEGER(-5000..20000)
	ACCESS		read-only
	STATUS		mandatory
	DESCRIPTION	"Temperature reading"
::= { historyEntry 1 }

histHum OBJECT-TYPE
	SYNTAX		INTEGER(-5000..20000)
	ACCESS		read-only
	STATUS		mandatory
	DESCRIPTION	"Humidity reading"
::= { historyEntry 2 }

histCompVal OBJECT-TYPE
	SYNTAX		INTEGER (-5000..20000)
	ACCESS		read-only
	STATUS		mandatory
	DESCRIPTION	"Computed value reading"
::= { historyEntry 3 }


-----------------------------------------------------------------------
-- Traps definition
-----------------------------------------------------------------------

trapTest TRAP-TYPE
	ENTERPRISE	comet
	VARIABLES	{ sensorName, messageString }
	DESCRIPTION	"Testing trap, testing trap by TSensor software"
	::= 0

trapNTPError TRAP-TYPE
	ENTERPRISE	comet
	VARIABLES	{ sensorName, messageString }
	DESCRIPTION	"Error on time synchronisation via NTP"
	::= 1

trapEmailErrLogin TRAP-TYPE
	ENTERPRISE	comet
	VARIABLES	{ sensorName, messageString }
	DESCRIPTION	"SMTP error - unknown server"
	::= 2

trapEmailErrAuth TRAP-TYPE
	ENTERPRISE	comet
	VARIABLES	{ sensorName, messageString }
	DESCRIPTION	"SMTP error - authentication error"
	::= 3

trapEmailErrSome TRAP-TYPE
	ENTERPRISE	comet
	VARIABLES	{ sensorName, messageString }
	DESCRIPTION	"SMTP error - error during communication with server, unexpected return code"
	::= 4

trapEmailErrSocket TRAP-TYPE
	ENTERPRISE	comet
	VARIABLES	{ sensorName, messageString }
	DESCRIPTION	"SMTP error - socket error, server is not available"
	::= 5

trapEmailErrDNS TRAP-TYPE
	ENTERPRISE	comet
	VARIABLES	{ sensorName, messageString }
	DESCRIPTION	"SMTP error - DNS error"
	::= 6

trapSOAPErrFile TRAP-TYPE
	ENTERPRISE	comet
	VARIABLES	{ sensorName, messageString }
	DESCRIPTION	"SOAP error - file SOAP not found"
	::= 7

trapSOAPErrDNS TRAP-TYPE
	ENTERPRISE	comet
	VARIABLES	{ sensorName, messageString }
	DESCRIPTION	"SOAP error - DNS error"
	::= 8

trapSOAPErrSocket TRAP-TYPE
	ENTERPRISE	comet
	VARIABLES	{ sensorName, messageString }
	DESCRIPTION	"SOAP error - socket error, server is not available"
	::= 9

trapSOAPErrDelivery TRAP-TYPE
	ENTERPRISE	comet
	VARIABLES	{ sensorName, messageString }
	DESCRIPTION	"SOAP error - delivery error, wrong return code from server"
	::= 10

trapTempAlarm1 TRAP-TYPE
	ENTERPRISE	comet
	VARIABLES	{ sensorName, messageString, temp, tempAlarm1Int }
	DESCRIPTION	"Trap for alarm1 on Temperature"
	::= 11

trapHumAlarm1 TRAP-TYPE
	ENTERPRISE	comet
	VARIABLES	{ sensorName, messageString, hum, humAlarm1Int }
	DESCRIPTION	"Trap for alarm1 on Relative humidity"
	::= 12

trapCompValAlarm1 TRAP-TYPE
	ENTERPRISE	comet
	VARIABLES	{ sensorName, messageString, compVal, compValAlarm1Int }
	DESCRIPTION	"Trap for alarm1 on Computed value"
	::= 13

trapTempAlarm2 TRAP-TYPE
	ENTERPRISE	comet
	VARIABLES	{ sensorName, messageString, temp, tempAlarm2Int }
	DESCRIPTION	"Trap for alarm2 on Temperature"
	::= 21

trapHumAlarm2 TRAP-TYPE
	ENTERPRISE	comet
	VARIABLES	{ sensorName, messageString, hum, humAlarm2Int }
	DESCRIPTION	"Trap for alarm2 on Relative humidity"
	::= 22

trapCompValAlarm2 TRAP-TYPE
	ENTERPRISE	comet
	VARIABLES	{ sensorName, messageString, compVal, compValAlarm2Int }
	DESCRIPTION	"Trap for alarm2 on Computed value"
	::= 23

trapTempClrAlarm1 TRAP-TYPE
	ENTERPRISE	comet
	VARIABLES	{ sensorName, messageString, temp, tempAlarm1Int }
	DESCRIPTION	"Trap for clearing alarm 1 on Temperature"
	::= 31

trapHumClrAlarm1 TRAP-TYPE
	ENTERPRISE	comet
	VARIABLES	{ sensorName, messageString, hum, humAlarm1Int }
	DESCRIPTION	"Trap for clearing alarm 1 on Relative humidity"
	::= 32

trapCompValClrAlarm1 TRAP-TYPE
	ENTERPRISE	comet
	VARIABLES	{ sensorName, messageString, compVal, compValAlarm1Int }
	DESCRIPTION	"Trap for clearing alarm 1 on Computed value"
	::= 33

trapTempClrAlarm2 TRAP-TYPE
	ENTERPRISE	comet
	VARIABLES	{ sensorName, messageString, temp, tempAlarm2Int }
	DESCRIPTION	"Trap for clearing alarm 2 on Temperature"
	::= 41

trapHumClrAlarm2 TRAP-TYPE
	ENTERPRISE	comet
	VARIABLES	{ sensorName, messageString, hum, humAlarm2Int }
	DESCRIPTION	"Trap for clearing alarm 2 on Relative humidity"
	::= 42

trapCompValClrAlarm2 TRAP-TYPE
	ENTERPRISE	comet
	VARIABLES	{ sensorName, messageString, compVal, compValAlarm2Int }
	DESCRIPTION	"Trap for clearing alarm 2 on Computed value"
	::= 43

trapBin1Alarm TRAP-TYPE
	ENTERPRISE	comet
	VARIABLES	{ sensorName, messageString, bin1Int, bin1AlarmInt }
	DESCRIPTION	"Trap for alarm on BIN Input 1"
	::= 51

trapBin2Alarm TRAP-TYPE
	ENTERPRISE	comet
	VARIABLES	{ sensorName, messageString, bin2Int, bin2AlarmInt }
	DESCRIPTION	"Trap for alarm on BIN Input 2"
	::= 52

trapBin3Alarm TRAP-TYPE
	ENTERPRISE	comet
	VARIABLES	{ sensorName, messageString, bin3Int, bin3AlarmInt }
	DESCRIPTION	"Trap for alarm on BIN Input 3"
	::= 53

trapBin1ClrAlarm TRAP-TYPE
	ENTERPRISE	comet
	VARIABLES	{ sensorName, messageString, bin1Int, bin1AlarmInt }
	DESCRIPTION	"Trap for clearing alarm on BIN Input 1"
	::= 61

trapBin2ClrAlarm TRAP-TYPE
	ENTERPRISE	comet
	VARIABLES	{ sensorName, messageString, bin2Int, bin2AlarmInt }
	DESCRIPTION	"Trap for clearing alarm on BIN Input 2"
	::= 62

trapBin3ClrAlarm TRAP-TYPE
	ENTERPRISE	comet
	VARIABLES	{ sensorName, messageString, bin3Int, bin3AlarmInt }
	DESCRIPTION	"Trap for clearing alarm on BIN Input 3"
	::= 63

trapRelay1Closed TRAP-TYPE
	ENTERPRISE	comet
	VARIABLES	{ sensorName, messageString, re1Int }
	DESCRIPTION	"Trap for closed Relay 1"
	::= 70

trapRelay2Closed TRAP-TYPE
	ENTERPRISE	comet
	VARIABLES	{ sensorName, messageString, re2Int }
	DESCRIPTION	"Trap for closed Relay 2"
	::= 71

trapRelay1Open TRAP-TYPE
	ENTERPRISE	comet
	VARIABLES	{ sensorName, messageString, re1Int }
	DESCRIPTION	"Trap for open Relay 1"
	::= 72

trapRelay2Open TRAP-TYPE
	ENTERPRISE	comet
	VARIABLES	{ sensorName, messageString, re2Int }
	DESCRIPTION	"Trap for open Relay 2"
	::= 73

trapAcousticActivated TRAP-TYPE
	ENTERPRISE	comet
	VARIABLES	{ sensorName, messageString }
	DESCRIPTION	"Trap for activated acoustic"
	::= 74

trapAcousticDeactivated TRAP-TYPE
	ENTERPRISE	comet
	VARIABLES	{ sensorName, messageString }
	DESCRIPTION	"Trap for deactivated acoustic"
	::= 75


END
