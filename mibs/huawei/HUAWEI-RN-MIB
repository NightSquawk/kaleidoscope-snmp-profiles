-- =============================================================================================================
-- Copyright (C) 2014 by  HUAWEI TECHNOLOGIES. All rights reserved.
-- Description: This MIB file defines the MIB objects of the remote network equipment (RN) management.
-- Reference:      
-- Version: V1.02
-- ==============================================================================================================
    HUAWEI-RN-MIB DEFINITIONS ::= BEGIN
 
        IMPORTS    
            huaweiUtility            
                FROM HUAWEI-MIB
            ifIndex
                FROM IF-MIB 
            IpAddress, Integer32, OBJECT-TYPE, 
            MODULE-IDENTITY, OBJECT-IDENTITY, NOTIFICATION-TYPE
                FROM SNMPv2-SMI
            RowStatus        
                FROM SNMPv2-TC            
            OBJECT-GROUP, MODULE-COMPLIANCE, NOTIFICATION-GROUP        
                FROM SNMPv2-CONF ;            
            
        hwRemoteNetworkEquipmentMib MODULE-IDENTITY
            LAST-UPDATED "201409220000Z"           
            ORGANIZATION "Huawei Technologies Co.,Ltd."
            CONTACT-INFO                                       
                "Huawei Industrial Base
                 Bantian, Longgang
                 Shenzhen 518129
                 People's Republic of China
                 Website: http://www.huawei.com
                 Email: support@huawei.com
                "                                     
            DESCRIPTION 
                "This MIB file defines the MIB objects of the remote network equipment (RN) management.
                "
                                 
            --  Revision history
            REVISION     "201409220000Z"
            DESCRIPTION  "V1.02, changes in this revision:
                         - Add the table of hwRnDeviceInfoTable .
                         - Modify the name of leaf hwRnDeviceSnmpProfileName to hwRnDeviceSnmpFirstProfileName.
                         - Add the leaf hwRnDeviceSnmpSecondProfileName for hwRnDeviceConfigTable.
                         " 
  
            REVISION     "201408140000Z"
            DESCRIPTION  "V1.01, changes in this revision:
                         - Modify the description of hwRnDeviceConfigTable.
                         - Modify the description of hwRnDeviceIpConfigTable.
                         "
                         
            REVISION     "201406100000Z"
            DESCRIPTION  "V1.00, initial version."
                
            ::= { huaweiUtility 188 }

        hwRnDeviceConfigObjects OBJECT IDENTIFIER ::= { hwRemoteNetworkEquipmentMib 1 }
        
        hwRnDeviceConfigTable OBJECT-TYPE
            SYNTAX SEQUENCE OF HwRnDeviceConfigEntry
            MAX-ACCESS not-accessible
            STATUS current
            DESCRIPTION
                "This table is used to manage the configuration profile information to be sent to the RN.
                 The indexes of this table are ifIndex and hwRnDeviceOntIndex.
                "
            ::= { hwRnDeviceConfigObjects 1 }
        
        hwRnDeviceConfigEntry OBJECT-TYPE
            SYNTAX HwRnDeviceConfigEntry
            MAX-ACCESS not-accessible
            STATUS current
            DESCRIPTION
                "This table is used to manage the configuration profile information to be sent to the RN. 
                 The indexes of this entry are ifIndex and hwRnDeviceOntIndex.
                "
            INDEX { ifIndex, hwRnDeviceOntIndex }
            ::= { hwRnDeviceConfigTable 1 }
        
        HwRnDeviceConfigEntry ::=
            SEQUENCE 
                { 
                hwRnDeviceOntIndex
                    Integer32,
                hwRnDeviceSnmpFirstProfileName
                    OCTET STRING,
                hwRnDeviceDeployProfileName
                    OCTET STRING,
                hwRnDeviceSnmpSecondProfileName
                    OCTET STRING
                }
        
        hwRnDeviceOntIndex OBJECT-TYPE
            SYNTAX Integer32 (0..255 | 2147483647)
            MAX-ACCESS not-accessible
            STATUS current
            DESCRIPTION
                 "Indicates the ont ID of the RN, ranging from 0 to 255.
                  A special value of 0x7FFFFFFF (2147483647) indicates that this parameter is not supported.
                  This node is mandatory for the configuration of RN parameters.
                "
            ::= { hwRnDeviceConfigEntry 1 }
        
        hwRnDeviceSnmpFirstProfileName   OBJECT-TYPE
            SYNTAX OCTET STRING (SIZE(0..32))
            MAX-ACCESS read-write
            STATUS current
            DESCRIPTION
                "Indicates the name of the first SNMP profile for the RN.
                 The invalid value, a null character string, indicates that the SNMP profile is not bound. 
                 This node is optional for the configuration of RN parameters. 
                "
            ::= { hwRnDeviceConfigEntry 2 }
        
        hwRnDeviceDeployProfileName OBJECT-TYPE
            SYNTAX OCTET STRING (SIZE(0..32))
            MAX-ACCESS read-write
            STATUS current
            DESCRIPTION
                "Indicates the name of the deploy profile for the RN.
                 The invalid value, a null character string, indicates that the deploy profile is not bound. 
                 This node is optional for the configuration of RN parameters. 
                "
            ::= { hwRnDeviceConfigEntry 3 }   
 
        hwRnDeviceSnmpSecondProfileName OBJECT-TYPE
            SYNTAX OCTET STRING (SIZE(0..32))
            MAX-ACCESS read-write
            STATUS current
            DESCRIPTION
                "Indicates the name of the second SNMP profile for the RN.
                 The invalid value, a null character string, indicates that the SNMP profile is not bound. 
                 This node is optional for the configuration of RN parameters. 
                "
            ::= { hwRnDeviceConfigEntry 4 }          

        hwRnDeviceIpConfigTable OBJECT-TYPE
            SYNTAX SEQUENCE OF HwRnDeviceIpConfigEntry
            MAX-ACCESS not-accessible
            STATUS current
            DESCRIPTION
                "This table is used to manage the ip configuration information to be sent to the RN.
                 The indexes of this table are ifIndex, hwRnDeviceOntIndex and hwRnDeviceIpIndex.
                "
            ::= { hwRnDeviceConfigObjects 2 }
        
        hwRnDeviceIpConfigEntry OBJECT-TYPE
            SYNTAX HwRnDeviceIpConfigEntry
            MAX-ACCESS not-accessible
            STATUS current
            DESCRIPTION
                "This table is used to manage the ip configuration information to be sent to the RN. 
                 The indexes of this entry are ifIndex, hwRnDeviceOntIndex and hwRnDeviceIpIndex.
                "
            INDEX { ifIndex, hwRnDeviceOntIndex, hwRnDeviceIpIndex }
            ::= { hwRnDeviceIpConfigTable 1 }
        
        HwRnDeviceIpConfigEntry ::=
            SEQUENCE 
                { 
                hwRnDeviceIpIndex
                    Integer32,
                hwRnDeviceIpAddress
                    IpAddress,
                hwRnDeviceNetMask
                    IpAddress,
                hwRnDeviceNetGateway
                    IpAddress,  
                hwRnDeviceIpConfigVlan
                    Integer32,
                hwRnDeviceIpConfigPriority
                    Integer32,
                hwRnDeviceIpConfigRowStaus
                    RowStatus
                }

        hwRnDeviceIpIndex OBJECT-TYPE
            SYNTAX Integer32 (0)
            MAX-ACCESS not-accessible
            STATUS current
            DESCRIPTION
                 "Indicates the IPv4 index of the ont IP host.
                  This node is mandatory for the configuration of RN parameters.
                "
            ::= { hwRnDeviceIpConfigEntry 1 }        
        
        hwRnDeviceIpAddress OBJECT-TYPE
            SYNTAX IpAddress
            MAX-ACCESS read-write
            STATUS current
            DESCRIPTION
                "Indicates the IPv4 address of the RN.
                 The invalid value 255.255.255.255 indicates that the IPv4 address is not configured.
                 This node is mandatory for the configuration of RN parameters.
                "
            ::= { hwRnDeviceIpConfigEntry 2 }
        
        hwRnDeviceNetMask OBJECT-TYPE
            SYNTAX IpAddress
            MAX-ACCESS read-write
            STATUS current
            DESCRIPTION
                "Indicates the subnet mask of the IPv4 address for the RN.
                 The invalid value 0.0.0.0 indicates that the subnet mask is not configured.
                 This node is mandatory for the configuration of RN parameters.
                "
            ::= { hwRnDeviceIpConfigEntry 3 }
        
        hwRnDeviceNetGateway OBJECT-TYPE
            SYNTAX IpAddress
            MAX-ACCESS read-write
            STATUS current
            DESCRIPTION
                "Indicates the default gateway of the RN.
                 The invalid value 255.255.255.255 indicates that the default gateway is not configured.
                 This node is optional for the configuration of RN parameters.
                "
            ::= { hwRnDeviceIpConfigEntry 4 }

        hwRnDeviceIpConfigVlan OBJECT-TYPE
            SYNTAX Integer32 (0..4096)
            MAX-ACCESS read-write
            STATUS current
            DESCRIPTION
                 "Indicates the VLAN ID of the RN, ranging from 0 to 4095.
                  The invalid value 4096 indicates that the VLAN ID is not configured.
                  This node is mandatory for the configuration of RN parameters.
                "
            ::= { hwRnDeviceIpConfigEntry 5 }
        
        hwRnDeviceIpConfigPriority OBJECT-TYPE
            SYNTAX Integer32 (0..7|255)
            MAX-ACCESS read-write
            STATUS current
            DESCRIPTION
                "Indicates the VLAN priority.
                 The invalid value 255 indicates that the VLAN priority is not configured.
                 This node is optional for the configuration of RN parameters.
                 The default VLAN priority is 0.
                "
            ::= { hwRnDeviceIpConfigEntry 6 }   
            
        hwRnDeviceIpConfigRowStaus OBJECT-TYPE
            SYNTAX RowStatus
            MAX-ACCESS read-create
            STATUS current
            DESCRIPTION
                "RowStatus.
                 1. active(1)      -indicates the query or set operation.
                 2. createAndGo(4) -indicates sending a RN config
                 3. destroy(6)     -indicates delete a RN config
                "
            ::= { hwRnDeviceIpConfigEntry 7 }                

       hwRnDeviceInfoTable OBJECT-TYPE
            SYNTAX SEQUENCE OF HwRnDeviceInfoEntry
            MAX-ACCESS not-accessible
            STATUS current
            DESCRIPTION
                "This table is used to query remote network equipment (RN) information.
                 The indexes of this table are ifIndex and hwRnDeviceOntIndex.
                "
            ::= { hwRnDeviceConfigObjects 3 }
        
        hwRnDeviceInfoEntry OBJECT-TYPE
            SYNTAX HwRnDeviceInfoEntry
            MAX-ACCESS not-accessible
            STATUS current
            DESCRIPTION
                "This table is used to query remote network equipment (RN) information. 
                 The indexes of this entry are ifIndex and hwRnDeviceOntIndex.
                "
            INDEX { ifIndex, hwRnDeviceOntIndex }
            ::= { hwRnDeviceInfoTable 1 }
        
        HwRnDeviceInfoEntry ::=
            SEQUENCE 
                { 
                hwRnDeviceObjectRunState                  INTEGER,
                hwRnDeviceObjectConfigResult              INTEGER,
                hwRnDeviceObjectEquipmentId               OCTET STRING,
                hwRnDeviceObjectEffectiveSnmpProfileName  OCTET STRING
                }
        
        hwRnDeviceObjectRunState OBJECT-TYPE
           SYNTAX INTEGER
              {
              online(1),
              offline(2),
              invalidValue(-1)
              }
            MAX-ACCESS read-only
            STATUS current
            DESCRIPTION
                "Indicates the running status of the RN.
                Options:
                1. online(1)        - Online
                2. offline(2)       - Offline
                3. invalidValue(-1) - Invalid value
                "
            ::= { hwRnDeviceInfoEntry 1 }
        
        hwRnDeviceObjectConfigResult OBJECT-TYPE
           SYNTAX INTEGER
              {
              normal(1),
              failed(2),
              notConfig(3),
              config(4),
              invalidValue(-1)
              }
            MAX-ACCESS read-only
            STATUS current
            DESCRIPTION
                "Indicates the RN configuration status. When the running status is online, 
                ETH RN status can be one of the following.
                Options:
                1. normal(1)         - Normal
                2. failed(2)         - Failed
                3. notConfig(3)      - Not config
                4. config(4)         - Config
                5. invalidValue(-1)  - Invalid value
                "
            ::= { hwRnDeviceInfoEntry 2 }
        
        hwRnDeviceObjectEquipmentId OBJECT-TYPE
            SYNTAX OCTET STRING (SIZE(0..20))
            MAX-ACCESS read-only
            STATUS current
            DESCRIPTION
                "Indicates the equipment name of the RN. 
                "
            ::= { hwRnDeviceInfoEntry 3 } 
	      
        hwRnDeviceObjectEffectiveSnmpProfileName OBJECT-TYPE
            SYNTAX OCTET STRING (SIZE(0..32))
            MAX-ACCESS read-only
            STATUS current
            DESCRIPTION
                "Indicates the effective SNMP profile name of the RN. 
                "
            ::= { hwRnDeviceInfoEntry 4 }                      
                    
                    
    END
