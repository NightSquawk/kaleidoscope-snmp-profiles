-- ===================================================================
-- Copyright (C) 2015 by HUAWEI TECHNOLOGIES. All rights reserved.
-- Description: 
-- Reference:
-- Version: V1.00
-- ===================================================================

RC-QosPolicy-MIB DEFINITIONS ::= BEGIN

IMPORTS
    OBJECT-TYPE, MODULE-IDENTITY, Unsigned32, IpAddress, Integer32
            FROM SNMPv2-SMI
    MacAddress, DisplayString, RowStatus
            FROM SNMPv2-TC 
    rc 
            FROM RC-SMI; 

rcQoSPolicy MODULE-IDENTITY
                LAST-UPDATED 
                    "201503110000Z"
                ORGANIZATION
                    "Huawei Technologies Co.,Ltd."
                CONTACT-INFO
                    "Huawei Industrial Base
  Bantian, Longgang
   Shenzhen 518129
   People's Republic of China
   Website: http://www.huawei.com
   Email: support@huawei.com
 "
                DESCRIPTION
                    "The MIB module to describe RC-QosPolicy-MIB."
                REVISION 
                    "201503110000Z"
                DESCRIPTION
                    "V1.0 Initial version of this MIB module"
                ::= { rc 3}



--------------------------------------------------------------
--  rcQoSClassMapTable
--------------------------------------------------------------   
    rcQoSClassMapTable OBJECT-TYPE
        SYNTAX  SEQUENCE OF RcQoSClassMapEntry
        MAX-ACCESS  not-accessible
        STATUS  current
        DESCRIPTION
                "class map table"
        ::= { rcQoSPolicy 1  }

    rcQoSClassMapEntry OBJECT-TYPE
        SYNTAX   RcQoSClassMapEntry
        MAX-ACCESS  not-accessible
        STATUS  current
        DESCRIPTION
                "class map"
        INDEX {rcQoSClassMapname,rcQoSClassMapMatchACL}
        ::= { rcQoSClassMapTable 1 }

    RcQoSClassMapEntry ::=SEQUENCE {
                rcQoSClassMapname                                  DisplayString,
                rcQoSClassMapMatchACL                              DisplayString,
                rcQoSClassMapRowSta                                RowStatus
        }

    rcQoSClassMapname OBJECT-TYPE
        SYNTAX   DisplayString(SIZE(1..31))
        MAX-ACCESS  not-accessible
        STATUS  current
        DESCRIPTION
                "ClassMap name"
        ::= { rcQoSClassMapEntry  1  }
        
    rcQoSClassMapMatchACL OBJECT-TYPE
        SYNTAX   DisplayString(SIZE(1..31))
        MAX-ACCESS  not-accessible
        STATUS  current
        DESCRIPTION
                "Acl Name"
        ::= { rcQoSClassMapEntry  2  }

    rcQoSClassMapRowSta OBJECT-TYPE
        SYNTAX   RowStatus
        MAX-ACCESS  read-create
        STATUS  current
        DESCRIPTION
           "This variable is used to create, modify, and/or
            delete a row in this table. "
      ::= { rcQoSClassMapEntry 3 }    
     
--------------------------------------------------------------
--------------------------------------------------------------
--rcQoSPolicyMapTable  
--------------------------------------------------------------
rcQoSPolicyMapTable OBJECT-TYPE
        SYNTAX  SEQUENCE OF RcQoSPolicyMapEntry
        MAX-ACCESS  not-accessible
        STATUS  current
        DESCRIPTION
                "POLICY MAP TABLE"
        ::= { rcQoSPolicy 2  }

rcQoSPolicyMapEntry OBJECT-TYPE
        SYNTAX   RcQoSPolicyMapEntry
        MAX-ACCESS  not-accessible
        STATUS  current
        DESCRIPTION
                "IP POLICY"
        INDEX {rcQoSPolicyMapname,rcQoSPolicyMapClassName}
        ::= { rcQoSPolicyMapTable 1 }

RcQoSPolicyMapEntry ::=
        SEQUENCE {
                rcQoSPolicyMapname                                DisplayString,  
                rcQoSPolicyMapClassName                           DisplayString,
                rcQoSPolicyMapSetIPDSCP                           Unsigned32,
                rcQoSPolicyMapRowSta                              RowStatus
        }

rcQoSPolicyMapname OBJECT-TYPE
        SYNTAX   DisplayString(SIZE(1..31))
        MAX-ACCESS  not-accessible
        STATUS  current
        DESCRIPTION
                "The policymap name"
        ::= { rcQoSPolicyMapEntry  1  } 
        
rcQoSPolicyMapClassName OBJECT-TYPE
        SYNTAX   DisplayString(SIZE(1..31))
        MAX-ACCESS  not-accessible
        STATUS  current
        DESCRIPTION
                "Classmap name"
        ::= { rcQoSPolicyMapEntry  2  }   
        
        
rcQoSPolicyMapSetIPDSCP OBJECT-TYPE
      SYNTAX       Unsigned32(0..63)
      MAX-ACCESS   read-create
      STATUS        current
      DESCRIPTION
           "Type of service value.
            The range of config is 0 to 63. "
      ::= { rcQoSPolicyMapEntry 3 }   
        
rcQoSPolicyMapRowSta OBJECT-TYPE
      SYNTAX       RowStatus
      MAX-ACCESS   read-create
      STATUS        current
      DESCRIPTION
           "This variable is used to create, modify, and/or
            delete a row in this table. "
      ::= { rcQoSPolicyMapEntry 4 }    
        
        
--------------------------------------------------------------
--------------------------------------------------------------
--rcApplyQoSPolicyMapTable 
--------------------------------------------------------------
rcApplyQoSPolicyMapTable OBJECT-TYPE
        SYNTAX  SEQUENCE OF RcApplyQoSPolicyMapEntry
        MAX-ACCESS  not-accessible
        STATUS  current
        DESCRIPTION
                "SERVICE POLICY Table"
        ::= { rcQoSPolicy 3  }

rcApplyQoSPolicyMapEntry OBJECT-TYPE
        SYNTAX   RcApplyQoSPolicyMapEntry
        MAX-ACCESS  not-accessible
        STATUS  current
        DESCRIPTION
                "Access list"
        INDEX {rcApplyQoSPolicyInterfacename}
        ::= { rcApplyQoSPolicyMapTable 1 }

RcApplyQoSPolicyMapEntry ::=
        SEQUENCE {
                rcApplyQoSPolicyInterfacename                     DisplayString,
                rcApplyQoSPolicyMapname                           DisplayString,
                rcApplyQoSPolicyMapRowSta                         RowStatus
        }

rcApplyQoSPolicyInterfacename OBJECT-TYPE
        SYNTAX   DisplayString(SIZE(1..31))
        MAX-ACCESS  not-accessible
        STATUS  current
        DESCRIPTION
                "Name of interface (1-31 characters)"
        ::= { rcApplyQoSPolicyMapEntry  1  } 
        
rcApplyQoSPolicyMapname OBJECT-TYPE
        SYNTAX   DisplayString(SIZE(1..31))
        MAX-ACCESS  read-create
        STATUS  current
        DESCRIPTION
                "Name of service policy (1-31 characters)"
        ::= { rcApplyQoSPolicyMapEntry  2  }
 
                
rcApplyQoSPolicyMapRowSta OBJECT-TYPE
        SYNTAX   RowStatus
        MAX-ACCESS  read-create
        STATUS  current
        DESCRIPTION
                "This variable is used to create, modify, and/or
                delete a row in this table. "
        ::= { rcApplyQoSPolicyMapEntry 3 }            
    
END
