-- ============================================================================
-- Copyright (C) 2010 by  HUAWEI TECHNOLOGIES. All rights reserved.
-- Description: The mib entity to describe voice overload controll.       
-- Reference:  
-- Version: V1.08
-- ============================================================================

 HUAWEI-VOLC-MIB DEFINITIONS ::= BEGIN
      IMPORTS
            MODULE-IDENTITY, OBJECT-TYPE, NOTIFICATION-TYPE, private
                FROM SNMPv2-SMI
            MODULE-COMPLIANCE, OBJECT-GROUP, NOTIFICATION-GROUP
                FROM SNMPv2-CONF
            TEXTUAL-CONVENTION
                FROM SNMPv2-TC
            IpAddress,TimeTicks,Counter32,Integer32
                FROM SNMPv2-SMI
            RowStatus,DisplayString
                FROM SNMPv2-TC
            huaweiUtility
                FROM HUAWEI-MIB;
        
      hwVoip MODULE-IDENTITY
                LAST-UPDATED "201011172222Z"
                ORGANIZATION "Huawei Technologies Co.,Ltd."
                CONTACT-INFO                                        
                             "Huawei Industrial Base                
                              Bantian, Longgang                     
                              Shenzhen 518129                       
                              People's Republic of China            
                              Website: http://www.huawei.com        
                              Email: support@huawei.com             
                             "                                                                                
                DESCRIPTION 
                             "
                              The mib entity to describe voice overload controll.
                             "
                                
--  Revision history
            REVISION     "201011172222Z"        
            DESCRIPTION  "V1.08, change in this revision:
                         -Modified the description of the head of the mib.
                         "
                         
            REVISION     "201011090000Z"        
            DESCRIPTION  "V1.05, change in this revision:
                         -Modified the description of some tables.
                         -Added the definition of the leaves,including:
                         hwMgOverloadCtrlCfgBraAccessSetupRate
                         hwMgOverloadCtrlCfgPraAccessSetupRate
                         hwMgOverloadCtrlCfgAccessSetupRateBucketDepth
                         "
                         
            REVISION     "201007230000Z"        
            DESCRIPTION  "V1.04, change in this revision:
                         -Modified the description of all tables 
                         "

            REVISION    "201003240000Z"
            DESCRIPTION "V1.03, change in this revision:
                        -Removed the description in Chinese, and kept it in English
                        all through the file.
                        -Corrected the SYNTAX."
                    
                        ::= { huaweiUtility 36 }
               

 hwIASVoipObjects OBJECT IDENTIFIER ::= { hwVoip 1 }
  
 hwIASVoipTraps OBJECT IDENTIFIER ::= { hwVoip 2 }
 

    
hwMgMGCOverloadCfgTable OBJECT-TYPE
     SYNTAX      SEQUENCE OF HwMgMGCOverloadCfgEntry
     MAX-ACCESS  not-accessible
     STATUS      current
     DESCRIPTION
       "
       Indicates the MGC overload configuration table of the MG interface.
       The index of this table is hwMGCOverloadCfgMgId.
       "
     ::= { hwIASVoipObjects 53 }
 
   hwMgMGCOverloadCfgEntry OBJECT-TYPE
     SYNTAX      HwMgMGCOverloadCfgEntry
     MAX-ACCESS  not-accessible
     STATUS      current
     DESCRIPTION
       "
       Indicates the MGC overload configuration table of the MG interface.
       The index of this entry is hwMGCOverloadCfgMgId.
       "
     INDEX    {  
               hwMGCOverloadCfgMgId
              }
     ::= { hwMgMGCOverloadCfgTable 1 }
 
   HwMgMGCOverloadCfgEntry ::=
     SEQUENCE
     {
       hwMGCOverloadCfgMgId                   Integer32,
       hwMGCOverloadCfgT3                     Integer32, 
       hwMGCOverloadCfgT2                     Integer32,
       hwMGCOverloadCfgT1                     Integer32,
       hwMGCOverloadCfgCallGappingTimer       Integer32,
       hwMGCOverloadCfgMaxAdmitRate           Integer32,
       hwMGCOverloadCfgthrottlingCallTreat    Integer32,
       hwMGCOverloadCfgnotratControl          Integer32,
       hwMGCOverloadCfgnotratValue            Integer32,
       hwMGCOverloadnotratValue               Integer32,
       hwMGCOverloadCfgSupport                INTEGER,    
       hwMGCOverloadCfgBraWeightExchange      Integer32,    
       hwMGCOverloadCfgPraWeightExchange      Integer32,
       hwMGCOverloadCfgIsdnCapabExchange      Integer32
     }
 
   hwMGCOverloadCfgMgId OBJECT-TYPE
     SYNTAX      Integer32(0..16777215)
     MAX-ACCESS  not-accessible
     STATUS      current
     DESCRIPTION
         "
         Indicates the MG interface ID.
         Range:0-16777215
         "
     ::= { hwMgMGCOverloadCfgEntry 1 }      
     
   hwMGCOverloadCfgT3 OBJECT-TYPE
     SYNTAX      Integer32(0..50) 
     MAX-ACCESS  read-write
     STATUS      current
     DESCRIPTION
         "
         Indicates the maximum channel occupancy rate (T3) of calls at the highest level.(50>=T3>=T2>=T1>=0).
         Range:0-50
         Default:50
         "    
         DEFVAL      {50}

     ::= { hwMgMGCOverloadCfgEntry 2 }
     
   hwMGCOverloadCfgT2 OBJECT-TYPE
     SYNTAX      Integer32(0..50) 
     MAX-ACCESS  read-write
     STATUS      current
     DESCRIPTION
         "
         Indicates the maximum channel occupancy rate (T2) of calls at the second highest level.(50>=T3>=T2>=T1>=0).
         Range:0-50
         Default:50
         "    
         DEFVAL      {50}

     ::= { hwMgMGCOverloadCfgEntry 3 }

   hwMGCOverloadCfgT1 OBJECT-TYPE
     SYNTAX      Integer32(0..50) 
     MAX-ACCESS  read-write
     STATUS      current
     DESCRIPTION
         "
         Indicates the maximum channel occupancy rate (T1) of calls at the common level.(50>=T3>=T2>=T1>=0).
         Range:0-50
         Default:50
         "        
         DEFVAL      {50}

     ::= { hwMgMGCOverloadCfgEntry 4 }

   hwMGCOverloadCfgCallGappingTimer OBJECT-TYPE
     SYNTAX      Integer32(1..120) 
     MAX-ACCESS  read-write
     STATUS      current
     DESCRIPTION
         "
         Indicates the length of the call-gapping timer.
         Range:0-120
         "  
     ::= { hwMgMGCOverloadCfgEntry 5 }
     
   hwMGCOverloadCfgMaxAdmitRate OBJECT-TYPE
     SYNTAX      Integer32(0..10000) 
     MAX-ACCESS  read-write
     STATUS      current
     DESCRIPTION
         "
         Indicates the maximum pass rate of the leaky bucket.
         Range:0-10000
         "  
     ::= { hwMgMGCOverloadCfgEntry 6 }
     
   hwMGCOverloadCfgthrottlingCallTreat OBJECT-TYPE
     SYNTAX      Integer32(1..2) 
     MAX-ACCESS  read-write
     STATUS      current
     DESCRIPTION
         "
         Indicates the announcement indicating that the subscriber-side network is busy after the call leaks to the leaky bucket:1:EET 2:announcement
         Range:1-2
         Default:1
         "                            
         DEFVAL      {1}

     ::= { hwMgMGCOverloadCfgEntry 7 }
     
   hwMGCOverloadCfgnotratControl OBJECT-TYPE
     SYNTAX      Integer32(1..2) 
     MAX-ACCESS  read-write
     STATUS      deprecated
     DESCRIPTION
         "
         Indicates the notrat control switch:1:on 2:off
         "  
     ::= { hwMgMGCOverloadCfgEntry 8 }
     
   hwMGCOverloadCfgnotratValue OBJECT-TYPE
     SYNTAX      Integer32(0..999999) 
     MAX-ACCESS  read-write
     STATUS      current
     DESCRIPTION
         "
         Indicates the maximum pass rate issued by the softswitch.
         "  
     ::= { hwMgMGCOverloadCfgEntry 9 }
     
   hwMGCOverloadnotratValue OBJECT-TYPE
     SYNTAX      Integer32(0..10000) 
     MAX-ACCESS  read-only
     STATUS      current
     DESCRIPTION
         "
         Indicates the actual pass rate of the overload leaky bucket of the current MGC.
         Range:0-10000
         "  
     ::= { hwMgMGCOverloadCfgEntry 10 }  
     
     hwMGCOverloadCfgSupport OBJECT-TYPE
     SYNTAX      INTEGER{enable(1),disable(2)} 
     MAX-ACCESS  read-write
     STATUS      current
     DESCRIPTION
         "
         Indicates the overload control switch of the MGC.
         Options:
         1.enable(1)    -indicates the overload control switch of the MGC is enable
         2.disable(2)   -indicates the overload control switch of the MGC is disable
         Default:enable(1)
         "  
         DEFVAL      { enable }
     ::= { hwMgMGCOverloadCfgEntry 11 }
     
    hwMGCOverloadCfgBraWeightExchange OBJECT-TYPE
     SYNTAX      Integer32(1..10000) 
     MAX-ACCESS  read-write
     STATUS      current
     DESCRIPTION
         "
          Indicates the BRA user weight in the case of MGC overload.
          Range:0-10000
          Default:200
         "  
         DEFVAL { 200 }
     ::= { hwMgMGCOverloadCfgEntry 12 }   
     
    hwMGCOverloadCfgPraWeightExchange OBJECT-TYPE
     SYNTAX      Integer32(1..10000) 
     MAX-ACCESS  read-write
     STATUS      current
     DESCRIPTION
         "
          Indicates the PRA user weight in the case of MGC overload.
          Range:0-10000
          Default:3000
         "                         
         DEFVAL      {3000}

     ::= { hwMgMGCOverloadCfgEntry 13 }   
     
     hwMGCOverloadCfgIsdnCapabExchange OBJECT-TYPE
     SYNTAX      Integer32(1..10000) 
     MAX-ACCESS  read-write
     STATUS      current
     DESCRIPTION
         "
          Indicates the conversion of the ISDN call capacity to the POTS call capacity in the case of MGC overload.
          Range:0-10000
          Default:100
         "         
         DEFVAL      {100}

     ::= { hwMgMGCOverloadCfgEntry 14 } 


hwMgMGCOverloadRecordTable OBJECT-TYPE
     SYNTAX      SEQUENCE OF HwMgMGCOverloadRecordEntry
     MAX-ACCESS  not-accessible
     STATUS      current
     DESCRIPTION
       "
       Indicates the call record of the MG interface in the case of MGC overload.
       The index of this table is hwMGCOverloadRecordIndex.
       "
     ::= { hwIASVoipObjects 54 }
 
   hwMgMGCOverloadRecordEntry OBJECT-TYPE
     SYNTAX      HwMgMGCOverloadRecordEntry
     MAX-ACCESS  not-accessible
     STATUS      current
     DESCRIPTION
       "
       Indicates the call record of the MG interface in the case of MGC overload.
       The index of this entry is hwMGCOverloadRecordIndex.
       "
     INDEX    {  
               hwMGCOverloadRecordIndex
              }
     ::= { hwMgMGCOverloadRecordTable 1 }
 
   HwMgMGCOverloadRecordEntry ::=
     SEQUENCE
     {
       hwMGCOverloadRecordIndex     Integer32,
       hwMGCOverloadStartYear       Integer32,      
       hwMGCOverloadStartMonth      Integer32,
       hwMGCOverloadStartDay        Integer32,   
       hwMGCOverloadStartHour       Integer32,
       hwMGCOverloadStartMinute     Integer32,
       hwMGCOverloadStartSecond     Integer32,  
       hwMGCOverloadMgId            Integer32,
       hwMGCOverloadMgcIp           IpAddress, 
       hwMGCOverloadMgcPort         Integer32,
       hwMGCOverloadEndYear         Integer32,      
       hwMGCOverloadEndMonth        Integer32,
       hwMGCOverloadEndDay          Integer32,   
       hwMGCOverloadEndHour         Integer32,
       hwMGCOverloadEndMinute       Integer32,
       hwMGCOverloadEndSecond       Integer32,
       hwMGCOverloadOffHookNum      Integer32,
       hwMGCOverloadOffHookPassNum  Integer32   
    }
 
   hwMGCOverloadRecordIndex OBJECT-TYPE
     SYNTAX      Integer32(0..16777215)
     MAX-ACCESS  not-accessible
     STATUS      current
     DESCRIPTION
         "
         Indicates the MGC overload record index of the MG interface.
         Range:0-16777215
         "
     ::= { hwMgMGCOverloadRecordEntry 1 }      
     
   hwMGCOverloadStartYear OBJECT-TYPE
     SYNTAX      Integer32 
     MAX-ACCESS  read-only
     STATUS      current
     DESCRIPTION
         "
         Indicates the MGC overload start time of the MG interface(year).
         "  
     ::= { hwMgMGCOverloadRecordEntry 2 }
     
   hwMGCOverloadStartMonth OBJECT-TYPE
     SYNTAX      Integer32 
     MAX-ACCESS  read-only
     STATUS      current
     DESCRIPTION
         "
         Indicates the MGC overload start time of the MG interface(month).
         "  
     ::= { hwMgMGCOverloadRecordEntry 3 }

   hwMGCOverloadStartDay OBJECT-TYPE
     SYNTAX      Integer32 
     MAX-ACCESS  read-only
     STATUS      current
     DESCRIPTION
         "
         Indicates the MGC overload start time of the MG interface(day).
         "  
     ::= { hwMgMGCOverloadRecordEntry 4 }

   hwMGCOverloadStartHour OBJECT-TYPE
     SYNTAX      Integer32 
     MAX-ACCESS  read-only
     STATUS      current
     DESCRIPTION
         "
         Indicates the MGC overload start time of the MG interface(hour).
         "  
     ::= { hwMgMGCOverloadRecordEntry 5 }

   hwMGCOverloadStartMinute OBJECT-TYPE
     SYNTAX      Integer32 
     MAX-ACCESS  read-only
     STATUS      current
     DESCRIPTION
         "
         Indicates the MGC overload start time of the MG interface(minute).
         "  
     ::= { hwMgMGCOverloadRecordEntry 6 }

   hwMGCOverloadStartSecond OBJECT-TYPE
     SYNTAX      Integer32 
     MAX-ACCESS  read-only
     STATUS      current
     DESCRIPTION
         "
         Indicates the MGC overload start time of the MG interface(second).
         "  
     ::= { hwMgMGCOverloadRecordEntry 7 }

   hwMGCOverloadMgId OBJECT-TYPE
     SYNTAX      Integer32(0..16777215) 
     MAX-ACCESS  read-only
     STATUS      current
     DESCRIPTION
         "
         Indicates the MG interface ID.
         Range:0-16777215
         "  
     ::= { hwMgMGCOverloadRecordEntry 8 }       
     
   hwMGCOverloadMgcIp OBJECT-TYPE
     SYNTAX      IpAddress 
     MAX-ACCESS  read-only
     STATUS      current
     DESCRIPTION
         "
         MGC IP
         "  
     ::= { hwMgMGCOverloadRecordEntry 9 }   
     
   hwMGCOverloadMgcPort OBJECT-TYPE
     SYNTAX      Integer32 
     MAX-ACCESS  read-only
     STATUS      current
     DESCRIPTION
         "
         MGC PORT
         "  
     ::= { hwMgMGCOverloadRecordEntry 10 } 
     
   hwMGCOverloadEndYear OBJECT-TYPE
     SYNTAX      Integer32 
     MAX-ACCESS  read-only
     STATUS      current
     DESCRIPTION
         "
         Indicates the MGC overload end time of the MG interface(year).
         "
    ::= { hwMgMGCOverloadRecordEntry 11 }
           
   hwMGCOverloadEndMonth OBJECT-TYPE
     SYNTAX      Integer32 
     MAX-ACCESS  read-only
     STATUS      current
     DESCRIPTION
         "
         Indicates the MGC overload end time of the MG interface(month).
         "  
     ::= { hwMgMGCOverloadRecordEntry 12 }
   
   hwMGCOverloadEndDay OBJECT-TYPE
     SYNTAX      Integer32 
     MAX-ACCESS  read-only
     STATUS      current
     DESCRIPTION
         "
         Indicates the MGC overload end time of the MG interface(day).
         "  
     ::= { hwMgMGCOverloadRecordEntry 13 }  
   
   hwMGCOverloadEndHour OBJECT-TYPE
     SYNTAX      Integer32 
     MAX-ACCESS  read-only
     STATUS      current
     DESCRIPTION
         "
         Indicates the MGC overload end time of the MG interface(hour).
         "  
     ::= { hwMgMGCOverloadRecordEntry 14 }   
                                                   
   hwMGCOverloadEndMinute OBJECT-TYPE
     SYNTAX      Integer32 
     MAX-ACCESS  read-only
     STATUS      current
     DESCRIPTION
         "
         Indicates the MGC overload end time of the MG interface(minute).
         "  
     ::= { hwMgMGCOverloadRecordEntry 15 }                                           
          
   hwMGCOverloadEndSecond OBJECT-TYPE
     SYNTAX      Integer32 
     MAX-ACCESS  read-only
     STATUS      current
     DESCRIPTION
         "
         Indicates the MGC overload end time of the MG interface(second).
         "  
     ::= { hwMgMGCOverloadRecordEntry 16 }
 
   hwMGCOverloadOffHookNum OBJECT-TYPE
     SYNTAX      Integer32 
     MAX-ACCESS  read-only
     STATUS      current
     DESCRIPTION
         "
         Indicates the received offhooks of the MG interface in the case of MGC overload.
         "  
     ::= { hwMgMGCOverloadRecordEntry 17 }

   hwMGCOverloadOffHookPassNum OBJECT-TYPE
     SYNTAX      Integer32 
     MAX-ACCESS  read-only
     STATUS      current
     DESCRIPTION
         "
         Indicates the passed offhooks of the MG interface in the case of MGC overload.
         "  
     ::= { hwMgMGCOverloadRecordEntry 18 }


hwSystemOverloadCfgTable OBJECT IDENTIFIER ::= {  hwIASVoipObjects 153  }

   hwSystemOverloadCtrlOriginatingCallSurgeInitLeakRate OBJECT-TYPE
     SYNTAX      Integer32(1..100) 
     MAX-ACCESS  read-write
     STATUS      current
     DESCRIPTION
         "
         Indicates the initial leak rate of the system call surge leaky bucket. Initial value: 6 for BT and 15 for other carriers.
         Range:0-100
         "  
     ::= { hwSystemOverloadCfgTable 1 }        
   
   hwSystemOverloadCtrlOriginatingCallSurgeBucketThreshold1 OBJECT-TYPE
     SYNTAX      Integer32 (1..100)
     MAX-ACCESS  read-write
     STATUS      current
     DESCRIPTION
         "
         Indicates leak rate threshold 1 of the system call surge leaky bucket, that is, the maximum water level of the bucket is 1.
         Range:0-100
         "           
     ::= { hwSystemOverloadCfgTable 2 }   

   hwSystemOverloadCtrlOriginatingCallSurgeBucketThreshold2 OBJECT-TYPE
     SYNTAX      Integer32 (1..100)
     MAX-ACCESS  read-write
     STATUS      current
     DESCRIPTION
         "
         Indicates leak rate threshold 2 of the system call surge leaky bucket, that is, the maximum water level of the bucket is 2.
         Range:0-100
         "        
     ::= { hwSystemOverloadCfgTable 3 }     
    
   hwSystemOverloadCtrlOriginatingCallSurgeAdjustFactor OBJECT-TYPE
     SYNTAX      Integer32(1..1000) 
     MAX-ACCESS  read-write
     STATUS      current
     DESCRIPTION
         "
         Indicates the adjustment factor of the system call surge leaky bucket. It is used to upshift or downshift the adjustment speed of the leak rate. The smaller the adjustment factor, the higher the speed of the leak rate upshift/downshift and the greater the jitter of the leak rate. On the contrary, the lower the speed of the leak rate upshift/downshift, the smaller the jitter.
         Range:0-1000
         "      
     ::= { hwSystemOverloadCfgTable 4 } 
     
   hwSystemOverloadCtrlOriginatingCallSurgeTerminationTime OBJECT-TYPE
     SYNTAX      Integer32(1..120) 
     MAX-ACCESS  read-write
     STATUS      current
     DESCRIPTION
         "
         Indicates the delay of reporting the recovery alarm after the call surge recovers, in the unit of second.
         Range:0-100
         "  
     ::= { hwSystemOverloadCfgTable 5 }      
     
   hwSystemOverloadCtrlTerminatingCallSurgeInitLeakRate OBJECT-TYPE
     SYNTAX      Integer32(1..100) 
     MAX-ACCESS  read-write
     STATUS      current
     DESCRIPTION
         "
         Indicates the initial leak rate of the system terminating call surge leaky bucket.
         Range:0-100
         "  
     ::= { hwSystemOverloadCfgTable 6 }    
     
   hwSystemOverloadCtrlTerminatingCallSurgeBucketThreshold OBJECT-TYPE
     SYNTAX      Integer32(1..100) 
     MAX-ACCESS  read-write
     STATUS      current
     DESCRIPTION
         "
         Indicates the leak rate threshold of the system terminating call surge leaky bucket, namely, the maximum water level of the system leaky bucket.
         Range:0-100
         "  
     ::= { hwSystemOverloadCfgTable 7 }       
     
   hwSystemOverloadCtrlTerminatingCallSurgeAdjustFactor OBJECT-TYPE
     SYNTAX      Integer32(1..1000) 
     MAX-ACCESS  read-write
     STATUS      current
     DESCRIPTION
         "
         Indicates the adjustment factor of the terminating call surge leaky bucket.
         Range:0-100
         "  
     ::= { hwSystemOverloadCfgTable 8 }     
     
   hwSystemOverloadCtrlTerminatingCallSurgeTerminationTime OBJECT-TYPE
     SYNTAX      Integer32(1..120) 
     MAX-ACCESS  read-write
     STATUS      current
     DESCRIPTION
         "
         Indicates the delay of reporting the recovery alarm after the terminating call surge recovers.
         Range:0-120
         "  
     ::= { hwSystemOverloadCfgTable 9 }                   
    
   hwSystemOverloadCtrlCallClearSurgeInitLeakRate OBJECT-TYPE
     SYNTAX      Integer32(1..100) 
     MAX-ACCESS  read-write
     STATUS      current
     DESCRIPTION
         "
         Indicates the initial leak rate of the system call clear surge leaky bucket, namely, the current leak rate initialized by the system. The current leak rate is adjusted dynamically according to the CPU usage. Initial value: 10 for BT and 15 for other carriers. It is invalid for an ISDN call.
         Range:0-100
         "  
     ::= { hwSystemOverloadCfgTable 10 }       
    
   hwSystemOverloadCtrlCallClearSurgeBucketThreshold OBJECT-TYPE
     SYNTAX      Integer32(1..100) 
     MAX-ACCESS  read-write
     STATUS      current
     DESCRIPTION
         "
         Indicates the leak rate threshold of the system call clear surge leaky bucket, namely, the maximum water level of the system leaky bucket. Initial value: 30 for BT and 60 for other carriers. It is invalid for an ISDN call.
         Range:0-100
         "  
     ::= { hwSystemOverloadCfgTable 11 }     
    
   hwSystemOverloadCtrlCallClearSurgeAdjustFactor OBJECT-TYPE
     SYNTAX      Integer32(1..1000) 
     MAX-ACCESS  read-write
     STATUS      current
     DESCRIPTION
         "
         Indicates the adjustment factor of the system call clear surge leaky bucket, used to upshift or downshift the adjustment speed of the leak rate. It is invalid for an ISDN call.
         Range:0-1000
         " 
     ::= { hwSystemOverloadCfgTable 12 }     
    
   hwSystemOverloadCtrlCallClearSurgeTerminationTime OBJECT-TYPE
     SYNTAX      Integer32(1..120) 
     MAX-ACCESS  read-write
     STATUS      current
     DESCRIPTION
         "
         Indicates the delay of reporting the recovery alarm after the call clear surge recovers, in the unit of second. It is invalid for an ISDN call.
         Range:0-120
         "  
     ::= { hwSystemOverloadCfgTable 13 }  
     
    hwSystemOverloadCtrlMgBraWeightExchange OBJECT-TYPE
     SYNTAX      Integer32(1..10000) 
     MAX-ACCESS  read-write
     STATUS      current
     DESCRIPTION
         "
         Indicates the BRA user weight in the case of MG overload.
         Range:0-10000
         "  
     ::= { hwSystemOverloadCfgTable 14 }   
     
    hwSystemOverloadCtrlMgPraWeightExchange OBJECT-TYPE
     SYNTAX      Integer32(1..10000) 
     MAX-ACCESS  read-write
     STATUS      current
     DESCRIPTION
         "
          Indicates the PRA user weight in the case of MG overload.
         Range:0-10000
         "  
     ::= { hwSystemOverloadCfgTable 15 }   
     
    hwSystemOverloadCtrlMgIsdnCapabExchange OBJECT-TYPE
     SYNTAX      Integer32(1..10000) 
     MAX-ACCESS  read-write
     STATUS      current
     DESCRIPTION
         "
          Indicates the conversion of the ISDN call capacity to the POTS call capacity in the case of MG overload.
          Range:0-10000
         "  
     ::= { hwSystemOverloadCfgTable 16 }   
     
    hwSystemOverloadCtrlMgcBraWeightExchange OBJECT-TYPE
     SYNTAX      Integer32(1..10000) 
     MAX-ACCESS  read-write
     STATUS      current
     DESCRIPTION
         "
          Indicates the BRA user weight in the case of MGC overload.
          Range:0-10000
         "  
     ::= { hwSystemOverloadCfgTable 17 }   
     
    hwSystemOverloadCtrlMgcPraWeightExchange OBJECT-TYPE
     SYNTAX      Integer32(1..10000) 
     MAX-ACCESS  read-write
     STATUS      current
     DESCRIPTION
         "
          Indicates the PRA user weight in the case of MGC overload.
          Range:0-10000
         " 
     ::= { hwSystemOverloadCfgTable 18 }   
     
     hwSystemOverloadCtrlMgcIsdnCapabExchange OBJECT-TYPE
     SYNTAX      Integer32(1..10000) 
     MAX-ACCESS  read-write
     STATUS      current
     DESCRIPTION
         "
          Indicates the conversion of the ISDN call capacity to the POTS call capacity in the case of MGC overload.
          Range:0-10000
         "
     ::= { hwSystemOverloadCfgTable 19 } 


hwMgOverloadCtrlCfgTable OBJECT IDENTIFIER ::= {  hwIASVoipObjects 56  }

     hwMgOverloadCtrlCfgPstnPowerDialerSupport OBJECT-TYPE
     SYNTAX      INTEGER{enable(1),disable(2)} 
     MAX-ACCESS  read-write
     STATUS      current
     DESCRIPTION
         "
         Indicates the power dialer switch in the PSTN overload control.
         Options:
         1. enable(1)   -indicates the power dialer switch in the PSTN overload control is enable
         2. disable(2)  -indicates the power dialer switch in the PSTN overload control is disable
         Default : Enable(1)
         "  
     ::= { hwMgOverloadCtrlCfgTable 1 }

     hwMgOverloadCtrlCfgPstnPowerDialerDetectionPeriod OBJECT-TYPE
     SYNTAX      Integer32(1..20) 
     MAX-ACCESS  read-write
     STATUS      current
     DESCRIPTION
         "
         Indicates the duration of power dialer detection in the PSTN overload control.
         Range:1-20
         Default:10
         "  
     ::= { hwMgOverloadCtrlCfgTable 2 }
     
     hwMgOverloadCtrlCfgPstnPowerDialerEventsNum OBJECT-TYPE
     SYNTAX      Integer32(2..50) 
     MAX-ACCESS  read-write
     STATUS      current
     DESCRIPTION
         "
         Indicates the count of offhooks within the duration of power dialer detection in the PSTN overload control.
         Range:2-50
         Default:20
         "  
     ::= { hwMgOverloadCtrlCfgTable 3 }

     hwMgOverloadCtrlCfgPstnPowerDialerBaseTimer OBJECT-TYPE
     SYNTAX      Integer32(1..10) 
     MAX-ACCESS  read-write
     STATUS      current
     DESCRIPTION
         "
         Indicates the duration of power dialer recovery detection in the PSTN overload control.
         Range:1-10
         Default:2
         "  
     ::= { hwMgOverloadCtrlCfgTable 4 }
   
   hwMgOverloadCfgCallSurgeSupport OBJECT-TYPE
     SYNTAX      INTEGER{enable(1),disable(2)} 
     MAX-ACCESS  read-write
     STATUS      current
     DESCRIPTION
         "
         Indicates the call surge switch in the MG overload control.
         Options:
         1. enable(1)   -indicates the call surge switch in the MG overload control is enable
         2. disable(2)  -indicates the call surge switch in the MG overload control is disable 
         Default : enable(1)
         "  
     ::= { hwMgOverloadCtrlCfgTable 5 }
     
   hwMgOverloadCfgOnhookSurgeSupport OBJECT-TYPE
     SYNTAX      INTEGER{enable(1),disable(2)} 
     MAX-ACCESS  read-write
     STATUS      current
     DESCRIPTION
         "
         Indicates the onhook surge switch in the MG overload control.
         Options:
         1. enable(1)   -indicates the onhook surge switch in the MG overload control is enable
         2. disable(2)  -indicates the onhook surge switch in the MG overload control is disable
         Default : enable(1)
         "  
     ::= { hwMgOverloadCtrlCfgTable 6 }

     hwMgOverloadCfgRestrictCpuLevel OBJECT-TYPE
     SYNTAX      Integer32(1..99)
     MAX-ACCESS  read-write
     STATUS      current
     DESCRIPTION
         "
         Indicates the expected CPU usage in the case of MG overload.
         Range: 1-99
         Default : 70
         "  
     ::= { hwMgOverloadCtrlCfgTable 7 }
     
     hwMgOverloadCfgCalledSurgeSupport OBJECT-TYPE
     SYNTAX      INTEGER{enable(1),disable(2)} 
     MAX-ACCESS  read-write
     STATUS      current
     DESCRIPTION
         "
         Indicates the called surge switch in the MG overload control.
         Options:
         1. enable(1)   -indicates the called surge switch in the MG overload control is enable
         2. disable(2)  -indicates the called surge switch in the MG overload control is disable
         Default : enable(1)
         "  
     ::= { hwMgOverloadCtrlCfgTable 8 }
    
    hwMgOverloadCfgInitLeakRate OBJECT-TYPE
     SYNTAX      Integer32(1..100) 
     MAX-ACCESS  read-write
     STATUS      current
     DESCRIPTION
         "
         Indicates the initial leak rate of the leaky bucket for MG overload control. Initial value: 6 for BT and 15 for other carriers.
         Range: 1-100
         "  
     ::= { hwMgOverloadCtrlCfgTable 9 }        
   
   hwMgOverloadCfgThreshold1 OBJECT-TYPE
     SYNTAX      Integer32 (1..100)
     MAX-ACCESS  read-write
     STATUS      current
     DESCRIPTION
         "
         Indicates leak rate threshold 1 of the leaky bucket for MG overload control, that is, the maximum water level of the leaky bucket is 1.
         Range: 1-100
         Default : 45
         "     
      ::= { hwMgOverloadCtrlCfgTable 10 } 

   hwMgOverloadCfgThreshold2 OBJECT-TYPE
     SYNTAX      Integer32 (1..100)
     MAX-ACCESS  read-write
     STATUS      current
     DESCRIPTION
         "
         Indicates leak rate threshold 2 of the leaky bucket for MG overload control, that is, the maximum water level of the leaky bucket is 2.
         Range: 1-100
         Default : 55
         "         
     ::= { hwMgOverloadCtrlCfgTable 11 }     
    
   hwMgOverloadCfgAdjustFactor OBJECT-TYPE
     SYNTAX      Integer32(1..1000) 
     MAX-ACCESS  read-write
     STATUS      current
     DESCRIPTION
         "
         Indicates the adjustment factor of the leaky bucket for MG overload control. It is used to upshift or downshift the adjustment speed of the leak rate. The smaller the adjustment factor, the higher the speed of the leak rate upshift/downshift and the greater the jitter of the leak rate. On the contrary, the lower the speed of the leak rate upshift/downshift, the smaller the jitter.
         Range: 1-1000
         Default : 20
         "    
     ::= { hwMgOverloadCtrlCfgTable 12 } 
     
   hwMgOverloadCfgResumeTimer OBJECT-TYPE
     SYNTAX      Integer32(1..120) 
     MAX-ACCESS  read-write
     STATUS      current
     DESCRIPTION
         "
         Indicates the delay of reporting the recovery alarm after the MG overload recovers, in the unit of second.
         Range: 1-120
         Default : 30
         "     

     ::= { hwMgOverloadCtrlCfgTable 13 }      
     
    hwMgOverloadCfgBraWeightExchange OBJECT-TYPE
     SYNTAX      Integer32(1..10000) 
     MAX-ACCESS  read-write
     STATUS      current
     DESCRIPTION
         "
          Indicates the BRA user weight in the case of MG overload.
          Range: 1-10000
          Default : 200
         "           
     ::= { hwMgOverloadCtrlCfgTable 14 }   
     
    hwMgOverloadCfgPraWeightExchange OBJECT-TYPE
     SYNTAX      Integer32(1..10000) 
     MAX-ACCESS  read-write
     STATUS      current
     DESCRIPTION
         "
          Indicates the PRA user weight in the case of MG overload.
          Range: 1-10000
          Default : 3000
         "   
     ::= { hwMgOverloadCtrlCfgTable 15 }   
     
    hwMgOverloadCfgIsdnCapabExchange OBJECT-TYPE
     SYNTAX      Integer32(1..10000) 
     MAX-ACCESS  read-write
     STATUS      current
     DESCRIPTION
         "
          Indicates the conversion of the ISDN call capacity to the POTS call capacity in the case of MG overload.
          Range: 1-10000
          Default : 120
         "         
     ::= { hwMgOverloadCtrlCfgTable 16 }   
     
     hwMgOverloadCtrlCfgBraPowerDialerSupport OBJECT-TYPE
     SYNTAX      INTEGER{enable(1),disable(2)} 
     MAX-ACCESS  read-write
     STATUS      current
     DESCRIPTION
         "
         abandoned.
         Options:
         1. enable(1)   -abandoned
         2. disable(2)  -abandoned
         Default: enable
         "  
     ::= { hwMgOverloadCtrlCfgTable 17 }

     hwMgOverloadCtrlCfgBraPowerDialerDetectionPeriod OBJECT-TYPE
     SYNTAX      Integer32(1..100) 
     MAX-ACCESS  read-write
     STATUS      current
     DESCRIPTION
         "
         Indicates the duration of power dialer detection in the BRA overload control.
         Range: 1-100
         Default : 10
         "  
     ::= { hwMgOverloadCtrlCfgTable 18 }
     
     hwMgOverloadCtrlCfgBraPowerDialerEventsNum OBJECT-TYPE
     SYNTAX      Integer32(1..10000) 
     MAX-ACCESS  read-write
     STATUS      current
     DESCRIPTION
         "
         Indicates the number of non-retransmitted setup messages within the duration of power dialer detection in the BRA overload control.
         Range: 1-10000
         Default : 20
         "  
     ::= { hwMgOverloadCtrlCfgTable 19 }

     hwMgOverloadCtrlCfgBraPowerDialerBaseTimer OBJECT-TYPE
     SYNTAX      Integer32(1..10) 
     MAX-ACCESS  read-write
     STATUS      current
     DESCRIPTION
         "
         Indicates the duration of power dialer recovery detection in the BRA overload control.
         Range: 1-10
         Default : 2
         "  
     ::= { hwMgOverloadCtrlCfgTable 20 }
     
     hwMgOverloadCtrlCfgIsdn30ePowerDialerSupport OBJECT-TYPE
     SYNTAX      INTEGER{enable(1),disable(2)} 
     MAX-ACCESS  read-write
     STATUS      current
     DESCRIPTION
         "
         abandoned.
         Options:
         1. enable(1)   -abandoned
         2. disable(2)  -abandoned
         "  
     ::= { hwMgOverloadCtrlCfgTable 21 }

     hwMgOverloadCtrlCfgIsdn30ePowerDialerDetectionPeriod OBJECT-TYPE
     SYNTAX      Integer32(1..100) 
     MAX-ACCESS  read-write
     STATUS      current
     DESCRIPTION
         "
         Indicates the duration of power dialer detection in the ISDN30E overload control.
         Range: 1-100
         Default : 10
         "  
     ::= { hwMgOverloadCtrlCfgTable 22 }
     
     hwMgOverloadCtrlCfgIsdn30ePowerDialerEventsNum OBJECT-TYPE
     SYNTAX      Integer32(1..10000) 
     MAX-ACCESS  read-write
     STATUS      current
     DESCRIPTION
         "
         Indicates the number of non-retransmitted setup messages within the duration of power dialer detection in the ISDN30E overload control.
         Range: 1-10000
         Default : 200
         "  
     ::= { hwMgOverloadCtrlCfgTable 23 }

     hwMgOverloadCtrlCfgIsdn30ePowerDialerBaseTimer OBJECT-TYPE
     SYNTAX      Integer32(1..10) 
     MAX-ACCESS  read-write
     STATUS      current
     DESCRIPTION
         "
         Indicates the duration of power dialer recovery detection in the ISDN30E overload control.
         Range: 1-10
         Default : 2
         "  
     ::= { hwMgOverloadCtrlCfgTable 24 }
     
     hwMgOverloadCtrlCfgDpnssPowerDialerSupport OBJECT-TYPE
     SYNTAX      INTEGER{enable(1),disable(2)} 
     MAX-ACCESS  read-write
     STATUS      current
     DESCRIPTION
         "
         abandoned.
         Options:
         1. enable(1)   -abandoned
         2. disable(2)  -abandoned
         "  
     ::= { hwMgOverloadCtrlCfgTable 25 }

     hwMgOverloadCtrlCfgDpnssPowerDialerDetectionPeriod OBJECT-TYPE
     SYNTAX      Integer32(1..100) 
     MAX-ACCESS  read-write
     STATUS      current
     DESCRIPTION
         "
         Indicates the duration of power dialer detection in the DPNSS overload control.
         Range: 1-100
         Default : 10
         "  
     ::= { hwMgOverloadCtrlCfgTable 26 }
     
     hwMgOverloadCtrlCfgDpnssPowerDialerEventsNum OBJECT-TYPE
     SYNTAX      Integer32(1..10000) 
     MAX-ACCESS  read-write
     STATUS      current
     DESCRIPTION
         "
         Indicates the number of non-retransmitted ISRM messages within the duration of power dialer detection in the DPNSS overload control.
         Range: 1-10000
         Default : 200
         "  
     ::= { hwMgOverloadCtrlCfgTable 27 }

     hwMgOverloadCtrlCfgDpnssPowerDialerBaseTimer OBJECT-TYPE
     SYNTAX      Integer32(1..10) 
     MAX-ACCESS  read-write
     STATUS      current
     DESCRIPTION
         "
         Indicates the duration of power dialer recovery detection in the DPNSS overload control.
         Range: 1-10
         Default : 2
         "  
     ::= { hwMgOverloadCtrlCfgTable 28 }
     
     hwMgOverloadCtrlCfgDass2PowerDialerSupport OBJECT-TYPE
     SYNTAX      INTEGER{enable(1),disable(2)} 
     MAX-ACCESS  read-write
     STATUS      current
     DESCRIPTION
         "
         abandoned.
         Options:
         1. enable(1)   -abandoned
         2. disable(2)  -abandoned
         "  
     ::= { hwMgOverloadCtrlCfgTable 29 }

     hwMgOverloadCtrlCfgDass2PowerDialerDetectionPeriod OBJECT-TYPE
     SYNTAX      Integer32(1..100) 
     MAX-ACCESS  read-write
     STATUS      current
     DESCRIPTION
         "
         Indicates the duration of power dialer detection in the DASS2 overload control.
         Range: 1-100
         Default : 10
         "  
     ::= { hwMgOverloadCtrlCfgTable 30 }
     
     hwMgOverloadCtrlCfgDass2PowerDialerEventsNum OBJECT-TYPE
     SYNTAX      Integer32(1..10000) 
     MAX-ACCESS  read-write
     STATUS      current
     DESCRIPTION
         "
         Indicates the number of non-retransmitted ISRM messages within the duration of power dialer detection in the DASS2 overload control.
         Range: 1-10000
         Default : 200
         "  
     ::= { hwMgOverloadCtrlCfgTable 31 }

     hwMgOverloadCtrlCfgDass2PowerDialerBaseTimer OBJECT-TYPE
     SYNTAX      Integer32(1..10) 
     MAX-ACCESS  read-write
     STATUS      current
     DESCRIPTION
         "
         Indicates the duration of power dialer recovery detection in the DASS2 overload control.
         Range: 1-10
         Default : 2
         "  
     ::= { hwMgOverloadCtrlCfgTable 32 }
     
     hwMgOverloadCtrlCfgL3ProxyTimerti01 OBJECT-TYPE
     SYNTAX      Integer32(0..30) 
     MAX-ACCESS  read-write
     STATUS      current
     DESCRIPTION
         "
         Indicates the length of the protection timer when the ISDN proxy is in the BlackHole state, at a step of 5.
         Range: 0-30
         Default : 20
         "  
     ::= { hwMgOverloadCtrlCfgTable 33 }
     
     hwMgOverloadCtrlCfgL3ProxyTimerti02 OBJECT-TYPE
     SYNTAX      Integer32(10..20) 
     MAX-ACCESS  read-write
     STATUS      current
     DESCRIPTION
         "
         Indicates the length of the protection timer when the DSS2 proxy is in the Overlap state, at a step of 1.
         Range: 10-20
         Default : 10
         "  
     ::= { hwMgOverloadCtrlCfgTable 34 }
     
     hwMgOverloadCtrlCfgL3ProxyTimerti03 OBJECT-TYPE
     SYNTAX      Integer32(0..15) 
     MAX-ACCESS  read-write
     STATUS      current
     DESCRIPTION
         "
         Indicates the length of the protection timer when the ISDN proxy is in the Fail_call state, at a step of 1.
         Range: 0-15
         Default : 10
         "  
     ::= { hwMgOverloadCtrlCfgTable 35 }
     
     hwMgOverloadCtrlCfgL3ProxyTimerti05 OBJECT-TYPE
     SYNTAX      Integer32(0..30) 
     MAX-ACCESS  read-write
     STATUS      current
     DESCRIPTION
         "
         Indicates the length of the protection timer when the ISDN proxy is in the Clash state, at a step of 5.
         Range: 0-30
         Default : 20
         "  
     ::= { hwMgOverloadCtrlCfgTable 36 }
     
     hwMgOverloadCtrlCfgL3ProxyTimerti06 OBJECT-TYPE
     SYNTAX      Integer32(0..30) 
     MAX-ACCESS  read-write
     STATUS      current
     DESCRIPTION
         "
         Indicates the length of the protection timer when the ISDN proxy is in the Fail_delay state, at a step of 5.
         Range: 0-30
         Default : 20
         "  
     ::= { hwMgOverloadCtrlCfgTable 37 }
     
     hwMgOverloadCtrlCfgL3ProxyTimert302 OBJECT-TYPE
     SYNTAX      Integer32(10..15) 
     MAX-ACCESS  read-write
     STATUS      current
     DESCRIPTION
         "
         Indicates the length of the protection timer when the ISDN proxy is in the Fail_delay state, at a step of 1.
         Range: 10-15
         Default : 10
         "  
     ::= { hwMgOverloadCtrlCfgTable 38 }
     
     hwMgOverloadCtrlCfgBraAccessSetupRate OBJECT-TYPE
     SYNTAX      Integer32(0..10000) 
     MAX-ACCESS  read-write
     STATUS      current
     DESCRIPTION
         "
         Bra access rate.
         Unit: 0.01caps
         Default: 10
         "  
     ::= { hwMgOverloadCtrlCfgTable 39 }
     
     hwMgOverloadCtrlCfgPraAccessSetupRate OBJECT-TYPE
     SYNTAX      Integer32(0..10000) 
     MAX-ACCESS  read-write
     STATUS      current
     DESCRIPTION
         "
         PRA(ISDN30e/ISDN30/DPNSS1) access rate.
         Unit: 0.01caps
         Default: 100
         "  
     ::= { hwMgOverloadCtrlCfgTable 40 }     
     
     hwMgOverloadCtrlCfgAccessSetupRateBucketDepth OBJECT-TYPE
     SYNTAX      Integer32(0..50) 
     MAX-ACCESS  read-write
     STATUS      current
     DESCRIPTION
         "
         ISDN Access rate bucket threshold
         Default: 10
         "  
     ::= { hwMgOverloadCtrlCfgTable 41 }    
          
   
END
