-- OPTIX-NE-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-NE-MIB DEFINITIONS ::= BEGIN
    IMPORTS
        optixProvisionEqpt
            FROM OPTIX-OID-MIB
        OBJECT-GROUP,MODULE-COMPLIANCE
            FROM SNMPv2-CONF
        Unsigned32,OBJECT-TYPE,MODULE-IDENTITY,IpAddress,NOTIFICATION-TYPE
            FROM SNMPv2-SMI
        ;

    optixNe MODULE-IDENTITY
        LAST-UPDATED "201204240000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies NE information"
        REVISION "201204240000Z"
        DESCRIPTION
            "The initial revision of this MIB module."
        REVISION "201204240000Z"
        DESCRIPTION
            "The initial revision of this MIB module."
        ::={ optixProvisionEqpt 21 }

    -- 1.3.6.1.4.1.2011.2.25.4.30.21.1
    optixNeGroup OBJECT IDENTIFIER ::= { optixNe 1 }

    -- 1.3.6.1.4.1.2011.2.25.4.30.21.1.1
    optixNeName OBJECT-TYPE
        SYNTAX OCTET STRING (SIZE(0..64))
        MAX-ACCESS read-write
        STATUS current
        DESCRIPTION
            "This object indicates the NE name."
        ::= { optixNeGroup 1 }

    -- 1.3.6.1.4.1.2011.2.25.4.30.21.1.2
    optixNePosition OBJECT-TYPE
        SYNTAX OCTET STRING (SIZE(0..32))
        MAX-ACCESS read-write
        STATUS current
        DESCRIPTION
            "This object indicates the NE position."
        ::= { optixNeGroup 2 }

    -- 1.3.6.1.4.1.2011.2.25.4.30.21.1.3
    optixNeMemo OBJECT-TYPE
        SYNTAX OCTET STRING (SIZE(0..32))
        MAX-ACCESS read-write
        STATUS current
        DESCRIPTION
            "This object indicates the note of the NE."
        ::= { optixNeGroup 3 }

    -- 1.3.6.1.4.1.2011.2.25.4.30.21.1.4
    optixNeH4mode OBJECT-TYPE
        SYNTAX Unsigned32
        MAX-ACCESS read-write
        STATUS current
        DESCRIPTION
            "This object indicates the H4 mode. Values of the higher six bits of an H4 byte: 0: all 0s, 1: all 1s. The default value is 0."
        ::= { optixNeGroup 4 }

    -- 1.3.6.1.4.1.2011.2.25.4.30.21.1.5
    optixNeDbBackupDelay OBJECT-TYPE
        SYNTAX Unsigned32
        MAX-ACCESS read-write
        STATUS current
        DESCRIPTION
            "This object indicates the datbase backup delay time. Value range: 5 to 1440 (unit: minute)"
        ::= { optixNeGroup 5 }

    -- 1.3.6.1.4.1.2011.2.25.4.30.21.1.6
    optixNeInsertmode OBJECT-TYPE
        SYNTAX INTEGER
        {
            uneq(0),
            ais(1)
        }
        MAX-ACCESS read-write
        STATUS current
        DESCRIPTION
            "This object indicates the insertion mode of the service channel. 0: uneq, 1: ais"
        ::= { optixNeGroup 6 }

    -- 1.3.6.1.4.1.2011.2.25.4.30.21.1.7
    optixNeState OBJECT-TYPE
        SYNTAX INTEGER
        {
            install(0),
            running(1)
        }
        MAX-ACCESS read-only
        STATUS current
        DESCRIPTION
            "This object indicates the NE status. 0: install, 1: running"
        ::= { optixNeGroup 7 }

    -- 1.3.6.1.4.1.2011.2.25.4.30.21.1.8
    optixNeDeviceType OBJECT-TYPE
        SYNTAX INTEGER
        {
            optixrtn910(76),
            optixrtn950(77),
            optixrtn980(83),
            optixrtn905(95),
            optixrtn950a(114),
            optiXRTN380(115),
            optiXRTN980L(140),
            optixrtn310(92),
            optixrtn320(151),
            optixrtn360(138),
            optixrtn380H(160),
            optixrtn905e(183),
            optixrtn910a(152),
            optixrtn380e(180),
            powercube500(191),
            optixRTN380AX(206),
            optixRTN380A(203)
        }
        MAX-ACCESS read-write
        STATUS current
        DESCRIPTION
            "This object indicates the device type. 76: Optix RTN 910, 77: Optix RTN 950, 83: Optix RTN 980,92:Optix RTN 310, 95: Optix RTN 905, 114: Optix RTN 950A, 115: OptiXRTN380, 140: OptiXRTN980L, 151: Optix RTN320, 138: Optix RTN360, 160: Optix RTN380H, 183:optixrtn905e, 152:optixrtn910a, 180:optixrtn380e, 191:PowerCube 500"
        ::= { optixNeGroup 8 }

    -- 1.3.6.1.4.1.2011.2.25.4.30.21.1.9
    optixNeShelfType OBJECT-TYPE
        SYNTAX INTEGER
        {
            subracki1A(1),
            subrackii2A(2),
            subracki1C(3),
            subracki1E(4),
            subrackii2E(5),
            standard310320360380380H910(146),
            standard950950A(148),
            standard980(150),
            standardOutdoor(163),
            split310320(167),
            standard910A(175),
            standardIndoor(177),
            subracki(184),
            subrackii(18),
            subrackii2F(194),
            standard380AX(206),
            standard380A(203)
        }
        MAX-ACCESS read-write
        STATUS current
        DESCRIPTION
            "This object indicates the subrack type. 1: subracki1A, 2: subrackii2A, 3: subracki1C, 4: subracki1E, 5: subrackii2E, 146: standard310320360380380H910, 148: standard950950A, 150: standard980, 163: standardOutdoor, 167: split310320, 175: standard910A, 177: standardIndoor, 184: subracki, 194: subrackii2F"
        ::= { optixNeGroup 9 }

    -- 1.3.6.1.4.1.2011.2.25.4.30.21.1.10
    optixNeAutoLoad OBJECT-TYPE
        SYNTAX INTEGER
        {
            disable(0),
            enable(1)
        }
        MAX-ACCESS read-only
        STATUS current
        DESCRIPTION
            "This object indicates the auto load status. 0: disable, 1: enable"
        ::= { optixNeGroup 10 }

    -- 1.3.6.1.4.1.2011.2.25.4.30.21.1.11
    optixNeOdcDeviceType OBJECT-TYPE
        SYNTAX INTEGER
        {
            null(0),
            apm30Ac(1),
            apm30Dc(2),
            ombAc(3),
            ombDc(4),
            apm5930Ac(11),
            apm5930Dc(12)
        }
        MAX-ACCESS read-write
        STATUS current
        DESCRIPTION
            "This object indicates the ODC devicetype. 0: null, 1: apm30Ac, 2: apm30Dc, 3: ombAc, 4: ombDc, 11: apm5930Ac, 12: apm5930Dc"
        ::= { optixNeGroup 11 }

    -- 1.3.6.1.4.1.2011.2.25.4.30.21.1.12
    optixNeGcpNodeId OBJECT-TYPE
        SYNTAX IpAddress
        MAX-ACCESS read-write
        STATUS current
        DESCRIPTION
            "This object indicates the node id of gcp system."
        ::= { optixNeGroup 12 }

    -- 1.3.6.1.4.1.2011.2.25.4.30.21.1.13
    optixNeSmokeAlm OBJECT-TYPE
        SYNTAX INTEGER
        {
            invalid(255),
            clear(1)
        }
        MAX-ACCESS read-write
        STATUS current
        DESCRIPTION
            "This object indicates the smoke alarm of the device. 1: clear, 255: invalid"
        ::= { optixNeGroup 13 }

    -- 1.3.6.1.4.1.2011.2.25.4.30.21.1.14
    optixNePnpFilePath OBJECT-TYPE
        SYNTAX OCTET STRING
        MAX-ACCESS read-only
        STATUS current
        DESCRIPTION
            "This object indicates the pnp file path and name of the device manage module."
        ::= { optixNeGroup 14 }

    -- 1.3.6.1.4.1.2011.2.25.4.30.21.1.15
    optixNe1j1status OBJECT-TYPE
        SYNTAX INTEGER
        {
            unknow(0),
            start(1),
            running(2),
            finished(3)
        }
        MAX-ACCESS read-write
        STATUS current
        DESCRIPTION
            "This object indicates the NE 1+1 status."
        ::= { optixNeGroup 15 }
		
	-- 1.3.6.1.4.1.2011.2.25.4.30.21.1.16
    optixNeNEWMemo OBJECT-TYPE
        SYNTAX OCTET STRING (SIZE(0..128))
        MAX-ACCESS read-write
        STATUS current
        DESCRIPTION
            "This object indicates the new note of the NE."
        ::= { optixNeGroup 16 }

    -- 1.3.6.1.4.1.2011.2.25.4.30.21.1.17
    optixNe1j1cfgcheck OBJECT-TYPE
        SYNTAX Unsigned32
        MAX-ACCESS read-only
        STATUS current
        DESCRIPTION
            "This object indicates the NE 1+1 config check."
        ::= { optixNeGroup 17 }

    -- 1.3.6.1.4.1.2011.2.25.4.30.21.1.18
    optixNeInitAll OBJECT-TYPE
        SYNTAX INTEGER
        {
            init(0)
        }
        MAX-ACCESS read-write
        STATUS current
        DESCRIPTION
            "This object indicates that all services on the NE need to be deleted. 0: init"
        ::= { optixNeGroup 18 }

    -- 1.3.6.1.4.1.2011.2.25.4.30.21.1.20
    optixNeFeatureNum OBJECT-TYPE
        SYNTAX Unsigned32
        MAX-ACCESS read-only
        STATUS current
        DESCRIPTION
            "This object indicates the length of the feature list."
        ::= { optixNeGroup 20 }

    -- 1.3.6.1.4.1.2011.2.25.4.30.21.1.21
    optixNeFeatureList OBJECT-TYPE
        SYNTAX OCTET STRING
        MAX-ACCESS read-only
        STATUS current
        DESCRIPTION
            "This object indicates the list of feature IDs."
        ::= { optixNeGroup 21 }

    -- 1.3.6.1.4.1.2011.2.25.4.30.21.2
    optixNeTableGroup OBJECT IDENTIFIER ::= { optixNe 2 }

    -- 1.3.6.1.4.1.2011.2.25.4.30.21.2.1
    optixNe1j1ResultTrapMember OBJECT IDENTIFIER ::= { optixNeTableGroup 1 }

    -- 1.3.6.1.4.1.2011.2.25.4.30.21.2.1.1
    optixNe1j1Resultinfo OBJECT-TYPE
        SYNTAX INTEGER
        {
            success(0),
            failed(1)
        }
        MAX-ACCESS accessible-for-notify
        STATUS current
        DESCRIPTION
            "This object indicates the NE 1+1 result."
        ::= { optixNe1j1ResultTrapMember 1 }

    -- 1.3.6.1.4.1.2011.2.25.4.30.21.2.2
    optixNeLicenseTable OBJECT-TYPE
        SYNTAX SEQUENCE OF OptixNeLicenseEntry
        MAX-ACCESS not-accessible
        STATUS current
        DESCRIPTION
            "This table describes the device licenses."
        ::= { optixNeTableGroup 2 }

    -- 1.3.6.1.4.1.2011.2.25.4.30.21.2.2.1
    optixNeLicenseEntry OBJECT-TYPE
        SYNTAX OptixNeLicenseEntry
        MAX-ACCESS not-accessible
        STATUS current
        DESCRIPTION
            "This entry describes the license of device configurations."
        INDEX{ optixNeLicenseFuncID }
        ::= { optixNeLicenseTable 1 }

    OptixNeLicenseEntry ::=
        SEQUENCE {
            optixNeLicenseFuncID
                INTEGER,
            optixNeLicenseLevel
                INTEGER,
            optixNeLicenseState
                Unsigned32,
            optixNeLicenseNum
                Unsigned32
        }

    -- 1.3.6.1.4.1.2011.2.25.4.30.21.2.2.1.1
    optixNeLicenseFuncID OBJECT-TYPE
        SYNTAX INTEGER
        {
            tpbasic(1),
            tpenhance(2),
            tpinterwork(3),
            sanaccess(4),
            sdhfee(5),
            pktfee(6),
            t32sup100g(7),
            snmp7500sup10g(100),
            flexgrid(8)
        }
        MAX-ACCESS not-accessible
        STATUS current
        DESCRIPTION
            "This object indicates the license function ID.1:tpbasic,2:tpenhance,3:tpinterwork,4:sanaccess,5:sdhfee,6:pktfee,7:t32sup100g,100:snmp7500sup10g,8:flexgrid"
        ::= { optixNeLicenseEntry 1 }

    -- 1.3.6.1.4.1.2011.2.25.4.30.21.2.2.1.2
    optixNeLicenseLevel OBJECT-TYPE
        SYNTAX INTEGER
        {
            ne(1),
            shelf(2),
            board(3),
            subcard(4),
            port(5)
        }
        MAX-ACCESS read-write
        STATUS current
        DESCRIPTION
            "This object indicates the function level."
        ::= { optixNeLicenseEntry 2 }

    -- 1.3.6.1.4.1.2011.2.25.4.30.21.2.2.1.3
    optixNeLicenseState OBJECT-TYPE
        SYNTAX Unsigned32
        MAX-ACCESS read-write
        STATUS current
        DESCRIPTION
            "This object indicates the license state."
        ::= { optixNeLicenseEntry 3 }

    -- 1.3.6.1.4.1.2011.2.25.4.30.21.2.2.1.4
    optixNeLicenseNum OBJECT-TYPE
        SYNTAX Unsigned32
        MAX-ACCESS read-only
        STATUS current
        DESCRIPTION
            "This object indicates the number of licenses."
        ::= { optixNeLicenseEntry 4 }

    -- 1.3.6.1.4.1.2011.2.25.4.30.21.2.3
    optixNe1j1ResultTrapReport OBJECT IDENTIFIER ::= { optixNeTableGroup 3 }

    -- 1.3.6.1.4.1.2011.2.25.4.30.21.2.3.1
    optixNe1j1ResultTrap NOTIFICATION-TYPE
        OBJECTS{ optixNe1j1Resultinfo }
        STATUS current
        DESCRIPTION
            "This trap indicates the NE 1+1 result."
        ::= { optixNe1j1ResultTrapReport 1 }

END
