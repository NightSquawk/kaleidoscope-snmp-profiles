--
-- HUAWEI-WLAN-SECURITY-MIB.mib
-- MIB generated by MG-SOFT Visual MIB Builder Version 2.5 Build 225
-- Tuesday, February 19, 2013 at 16:43:20
--
--  ============================================================================
-- Copyright (C) 2014 by  HUAWEI TECHNOLOGIES. All rights reserved.
-- Description:  The mib is used for configuring the information of the security, including
--               security profile and so on.
-- Reference:  
-- Version:      V1.02
-- 
-- ============================================================================

	HUAWEI-WLAN-SECURITY-MIB DEFINITIONS ::= BEGIN

		IMPORTS 
			hwApRegionIndex, hwApIndex, hwApMac			
				FROM HUAWEI-WLAN-DEVICE-MIB			
			hwWlan			
				FROM HUAWEI-WLAN-MIB			
			hwRadioID			
				FROM HUAWEI-WLAN-RADIO-MIB			
			hwWlanServiceEssSsid, hwWlanServiceStaMac			
				FROM HUAWEI-WLAN-SERVICE-MIB			
			OBJECT-GROUP, MODULE-COMPLIANCE, NOTIFICATION-GROUP			
				FROM SNMPv2-CONF			
			IpAddress, Integer32, Unsigned32, Counter32, OBJECT-TYPE, 
			MODULE-IDENTITY, NOTIFICATION-TYPE			
				FROM SNMPv2-SMI			
			MacAddress, TruthValue, RowStatus, DisplayString			
				FROM SNMPv2-TC;
	
	
		hwWlanSecurity MODULE-IDENTITY
			LAST-UPDATED "201402131000Z"    -- Feb 13, 2014 at 10:00 GMT
			ORGANIZATION
				"Huawei Technologies Co.,Ltd."
			CONTACT-INFO
				"Huawei Industrial Base
				Bantian, Longgang
				Shenzhen 518129
				People's Republic of China
				Website: http://www.huawei.com
				Email: support@huawei.com
				"
			DESCRIPTION
				"
				huawei HUAWEI-WLAN-SECURITY-MIB.
				"
			REVISION "201402131000Z"		-- Feb 13, 2014 at 10:00 GMT
			DESCRIPTION
				"Version: V1.02, add changes for V2R5"
				
                                                    REVISION "201308121000Z"		-- Aug 12, 2013 at 10:00 GMT
			DESCRIPTION
				"Version: V1.01, add changes for V2R3"

			REVISION "201006011000Z"
			DESCRIPTION
				" V1.00, The first Draft."
			::= { hwWlan 6 }
		
	
	
--
-- Node definitions
--
	
--  Node definitions
-- 
-- 1.3.6.1.4.1.2011.6.139.6.1
		-- 1.3.6.1.4.1.2011.6.139.6.1
		hwWsecProfileTable OBJECT-TYPE
			SYNTAX SEQUENCE OF HwWsecProfileEntry
			MAX-ACCESS not-accessible
			STATUS current
			DESCRIPTION
				"WLAN access security profile table."
			::= { hwWlanSecurity 1 }

		
--  1.3.6.1.4.1.2011.6.139.6.1.1
		-- 1.3.6.1.4.1.2011.6.139.6.1.1
		hwWsecProfileEntry OBJECT-TYPE
			SYNTAX HwWsecProfileEntry
			MAX-ACCESS not-accessible
			STATUS current
			DESCRIPTION
				"WLAN access security profile entry."
			INDEX { hwWsecProfileName }
			::= { hwWsecProfileTable 1 }

		
		HwWsecProfileEntry ::=
			SEQUENCE { 
				hwWsecProfileName
					OCTET STRING,
				hwWsecProfileWEPDataEncrypt
					TruthValue,
				hwWsecProfileWEPDefaultKeyID
					Integer32,
				hwWsecProfileWEPKeyMappingLength
					Integer32,
				hwWsecProfileAsuIpAddr
					IpAddress,
				hwWsecProfileCaCertFileName
					OCTET STRING,
				hwWsecProfileAsuCertFileName
					OCTET STRING,
				hwWsecProfileAcCertFileName
					OCTET STRING,
				hwWsecProfileAcPrvKeyFileName
					OCTET STRING,
				hwWsecProfileRsnaVersion
					Integer32,
				hwWsecProfileWapiVersion
					Integer32,
				hwWsecProfileRowStatus
					RowStatus,
				hwWsecProfileCaPfxPassword
					OCTET STRING,
				hwWsecProfileCaCertState
					INTEGER,
				hwWsecProfileAsuPfxPassword
					OCTET STRING,
				hwWsecProfileAsuCertState
					INTEGER,
				hwWsecProfileAcPfxPassword
					OCTET STRING,
				hwWsecProfileAcCertState
					INTEGER,
				hwWsecProfileKeyPfxPassword
					OCTET STRING,
				hwWsecProfileAsuType
					INTEGER,
				hwWsecProfileWpaPtkRekeySwitch
					INTEGER,
				hwWsecProfileWpa2PtkRekeySwitch
					INTEGER,
				hwWsecProfileWpaWpa2PtkRekeySwitch
					INTEGER,
				hwWsecProfileWpaPtkRekeyInterval
					Integer32,
				hwWsecProfileWpa2PtkRekeyInterval
					Integer32,
				hwWsecProfileWpaWpa2PtkRekeyInterval
					Integer32
			 }

--  1.3.6.1.4.1.2011.6.139.6.1.1.1
		-- 1.3.6.1.4.1.2011.6.139.6.1.1.1
		hwWsecProfileName OBJECT-TYPE
			SYNTAX OCTET STRING (SIZE (1..31))
			MAX-ACCESS read-write
			STATUS current
			DESCRIPTION
				"
				WLAN access security profile Name.
				"
			::= { hwWsecProfileEntry 1 }

		
--  1.3.6.1.4.1.2011.6.139.6.1.1.2
		-- 1.3.6.1.4.1.2011.6.139.6.1.1.2
		hwWsecProfileWEPDataEncrypt OBJECT-TYPE
			SYNTAX TruthValue
			MAX-ACCESS read-write
			STATUS current
			DESCRIPTION
				"When this attribute is TRUE, WEP data will be encrypted.
				When this attribute is FALSE, WEP data will not be encrypted. 
				The default value of this attribute is FALSE."
			::= { hwWsecProfileEntry 2 }

		
--  1.3.6.1.4.1.2011.6.139.6.1.1.3
		-- 1.3.6.1.4.1.2011.6.139.6.1.1.3
		hwWsecProfileWEPDefaultKeyID OBJECT-TYPE
			SYNTAX Integer32 (0..3)
			MAX-ACCESS read-write
			STATUS current
			DESCRIPTION
				"This attribute shall indicate the use of the first,
				second, third, or fourth element of the WEPDefaultKeys
				array when set to values of zero, one, two, or three. The
				default value of this attribute shall be 0."
			REFERENCE
				"IEEE Std 802.11-2007, 8.3.2"
			::= { hwWsecProfileEntry 3 }

		
--  1.3.6.1.4.1.2011.6.139.6.1.1.4
		-- 1.3.6.1.4.1.2011.6.139.6.1.1.4
		hwWsecProfileWEPKeyMappingLength OBJECT-TYPE
			SYNTAX Integer32
			MAX-ACCESS read-write
			STATUS current
			DESCRIPTION
				"The maximum number of tuples that hwWsecWEPKeyMappings can hold."
			REFERENCE
				"IEEE Std 802.11-2007, 8.3.2"
			::= { hwWsecProfileEntry 4 }

		
--  1.3.6.1.4.1.2011.6.139.6.1.1.5
		-- 1.3.6.1.4.1.2011.6.139.6.1.1.5
		hwWsecProfileAsuIpAddr OBJECT-TYPE
			SYNTAX IpAddress
			MAX-ACCESS read-write
			STATUS current
			DESCRIPTION
				"ASU IP address for WAPI certification authentication"
			::= { hwWsecProfileEntry 5 }

		
--  1.3.6.1.4.1.2011.6.139.6.1.1.6
		-- 1.3.6.1.4.1.2011.6.139.6.1.1.6
		hwWsecProfileCaCertFileName OBJECT-TYPE
			SYNTAX OCTET STRING
			MAX-ACCESS read-write
			STATUS current
			DESCRIPTION
				"CA certification file name"
			::= { hwWsecProfileEntry 6 }

		
--  1.3.6.1.4.1.2011.6.139.6.1.1.7
		-- 1.3.6.1.4.1.2011.6.139.6.1.1.7
		hwWsecProfileAsuCertFileName OBJECT-TYPE
			SYNTAX OCTET STRING
			MAX-ACCESS read-write
			STATUS current
			DESCRIPTION
				"ASU certification file name"
			::= { hwWsecProfileEntry 7 }

		
--  1.3.6.1.4.1.2011.6.139.6.1.1.8
		-- 1.3.6.1.4.1.2011.6.139.6.1.1.8
		hwWsecProfileAcCertFileName OBJECT-TYPE
			SYNTAX OCTET STRING
			MAX-ACCESS read-write
			STATUS current
			DESCRIPTION
				"AC certification file name"
			::= { hwWsecProfileEntry 8 }

		
--  1.3.6.1.4.1.2011.6.139.6.1.1.9
		-- 1.3.6.1.4.1.2011.6.139.6.1.1.9
		hwWsecProfileAcPrvKeyFileName OBJECT-TYPE
			SYNTAX OCTET STRING
			MAX-ACCESS read-write
			STATUS current
			DESCRIPTION
				"AC private key file name"
			::= { hwWsecProfileEntry 9 }

		
--  1.3.6.1.4.1.2011.6.139.6.1.1.10
		-- 1.3.6.1.4.1.2011.6.139.6.1.1.10
		hwWsecProfileRsnaVersion OBJECT-TYPE
			SYNTAX Integer32
			MAX-ACCESS read-only
			STATUS current
			DESCRIPTION
				"The highest WAPI/RSNA version this entity supports. See 7.3.2.9."
			::= { hwWsecProfileEntry 10 }

		
--  1.3.6.1.4.1.2011.6.139.6.1.1.11
		-- 1.3.6.1.4.1.2011.6.139.6.1.1.11
		hwWsecProfileWapiVersion OBJECT-TYPE
			SYNTAX Integer32
			MAX-ACCESS read-only
			STATUS current
			DESCRIPTION
				"This object indicates the highest WAPI version that this entity supports."
			::= { hwWsecProfileEntry 11 }

		
--  1.3.6.1.4.1.2011.6.139.6.1.1.12
		-- 1.3.6.1.4.1.2011.6.139.6.1.1.12
		hwWsecProfileRowStatus OBJECT-TYPE
			SYNTAX RowStatus
			MAX-ACCESS read-create
			STATUS current
			DESCRIPTION
				"Row status"
			::= { hwWsecProfileEntry 12 }

		
		-- 1.3.6.1.4.1.2011.6.139.6.1.1.13
		hwWsecProfileCaPfxPassword OBJECT-TYPE
			SYNTAX OCTET STRING (SIZE (0..32))
			MAX-ACCESS read-write
			STATUS current
			DESCRIPTION
				"Description."
			::= { hwWsecProfileEntry 13 }

		
		-- 1.3.6.1.4.1.2011.6.139.6.1.1.14
		hwWsecProfileCaCertState OBJECT-TYPE
			SYNTAX INTEGER
				{
				valid(1),
				invalid(2)
				}
			MAX-ACCESS read-only
			STATUS current
			DESCRIPTION
				"Description."
			::= { hwWsecProfileEntry 14 }

		
		-- 1.3.6.1.4.1.2011.6.139.6.1.1.15
		hwWsecProfileAsuPfxPassword OBJECT-TYPE
			SYNTAX OCTET STRING (SIZE (0..32))
			MAX-ACCESS read-write
			STATUS current
			DESCRIPTION
				"Description."
			::= { hwWsecProfileEntry 15 }

		
		-- 1.3.6.1.4.1.2011.6.139.6.1.1.16
		hwWsecProfileAsuCertState OBJECT-TYPE
			SYNTAX INTEGER
				{
				valid(1),
				invalid(2)
				}
			MAX-ACCESS read-only
			STATUS current
			DESCRIPTION
				"Description."
			::= { hwWsecProfileEntry 16 }

		
		-- 1.3.6.1.4.1.2011.6.139.6.1.1.17
		hwWsecProfileAcPfxPassword OBJECT-TYPE
			SYNTAX OCTET STRING (SIZE (0..32))
			MAX-ACCESS read-write
			STATUS current
			DESCRIPTION
				"Description."
			::= { hwWsecProfileEntry 17 }

		
		-- 1.3.6.1.4.1.2011.6.139.6.1.1.18
		hwWsecProfileAcCertState OBJECT-TYPE
			SYNTAX INTEGER
				{
				valid(1),
				invalid(2)
				}
			MAX-ACCESS read-only
			STATUS current
			DESCRIPTION
				"Description."
			::= { hwWsecProfileEntry 18 }

		
		-- 1.3.6.1.4.1.2011.6.139.6.1.1.19
		hwWsecProfileKeyPfxPassword OBJECT-TYPE
			SYNTAX OCTET STRING (SIZE (0..32))
			MAX-ACCESS read-write
			STATUS current
			DESCRIPTION
				"Description."
			::= { hwWsecProfileEntry 19 }

		
		-- 1.3.6.1.4.1.2011.6.139.6.1.1.20
		hwWsecProfileAsuType OBJECT-TYPE
			SYNTAX INTEGER
				{
				remote(1),
				local(2)
				}
			MAX-ACCESS read-write
			STATUS current
			DESCRIPTION
				"Description."
			::= { hwWsecProfileEntry 20 }

		-- 1.3.6.1.4.1.2011.6.139.6.1.1.21
		hwWsecProfileWpaPtkRekeySwitch OBJECT-TYPE
			SYNTAX INTEGER
				{
				disable(1),
				enable(2)
				}
			MAX-ACCESS read-write
			STATUS current
			DESCRIPTION
				"Description."
			::= { hwWsecProfileEntry 21 }
		
		-- 1.3.6.1.4.1.2011.6.139.6.1.1.22
		hwWsecProfileWpa2PtkRekeySwitch OBJECT-TYPE
			SYNTAX INTEGER
				{
				disable(1),
				enable(2)
				}
			MAX-ACCESS read-write
			STATUS current
			DESCRIPTION
				"Description."
			::= { hwWsecProfileEntry 22 }
		
		-- 1.3.6.1.4.1.2011.6.139.6.1.1.23
		hwWsecProfileWpaWpa2PtkRekeySwitch OBJECT-TYPE
			SYNTAX INTEGER
				{
				disable(1),
				enable(2)
				}
			MAX-ACCESS read-write
			STATUS current
			DESCRIPTION
				"Description."
			::= { hwWsecProfileEntry 23 }
		
		-- 1.3.6.1.4.1.2011.6.139.6.1.1.24
		hwWsecProfileWpaPtkRekeyInterval OBJECT-TYPE
			SYNTAX Integer32 (30..86400)
			MAX-ACCESS read-write
			STATUS current
			DESCRIPTION
				"Description."
			DEFVAL { 43200 }
			::= { hwWsecProfileEntry 24 }
		
		-- 1.3.6.1.4.1.2011.6.139.6.1.1.25
		hwWsecProfileWpa2PtkRekeyInterval OBJECT-TYPE
			SYNTAX Integer32 (30..86400)
			MAX-ACCESS read-write
			STATUS current
			DESCRIPTION
				"Description."
			DEFVAL { 43200 }
			::= { hwWsecProfileEntry 25 }
		
		-- 1.3.6.1.4.1.2011.6.139.6.1.1.26
		hwWsecProfileWpaWpa2PtkRekeyInterval OBJECT-TYPE
			SYNTAX Integer32 (30..86400)
			MAX-ACCESS read-write
			STATUS current
			DESCRIPTION
				"Description."
			DEFVAL { 43200 }
			::= { hwWsecProfileEntry 26 }
		
--  1.3.6.1.4.1.2011.6.139.6.2
		-- 1.3.6.1.4.1.2011.6.139.6.2
		hwWsecWEPDefaultKeysTable OBJECT-TYPE
			SYNTAX SEQUENCE OF HwWsecWEPDefaultKeysEntry
			MAX-ACCESS not-accessible
			STATUS current
			DESCRIPTION
				"Conceptual table for WEP default keys. This table shall
				contain the four WEP default secret key values
				corresponding to the four possible KeyID values. The WEP
				default secret keys are logically WRITE-ONLY. Attempts to
				read the entries in this table shall return unsuccessful
				status and values of null or zero. The default value of
				each WEP default key shall be null."
			REFERENCE
				"IEEE Std 802.11-2007, 8.3.2"
			::= { hwWlanSecurity 2 }

		
--  1.3.6.1.4.1.2011.6.139.6.2.1
		-- 1.3.6.1.4.1.2011.6.139.6.2.1
		hwWsecWEPDefaultKeysEntry OBJECT-TYPE
			SYNTAX HwWsecWEPDefaultKeysEntry
			MAX-ACCESS not-accessible
			STATUS current
			DESCRIPTION
				"An Entry (conceptual row) in the WEP Default Keys Table."
			INDEX { hwWsecProfileName, hwWsecWEPDefaultKeyIndex }
			::= { hwWsecWEPDefaultKeysTable 1 }

		
		HwWsecWEPDefaultKeysEntry ::=
			SEQUENCE { 
				hwWsecWEPDefaultKeyIndex
					Integer32,
				hwWsecWEPDefaultKeyValue
					OCTET STRING,
				hwWsecWEPPassPhrase
					DisplayString
			 }

--  1.3.6.1.4.1.2011.6.139.6.2.1.1
		-- 1.3.6.1.4.1.2011.6.139.6.2.1.1
		hwWsecWEPDefaultKeyIndex OBJECT-TYPE
			SYNTAX Integer32 (1..4)
			MAX-ACCESS not-accessible
			STATUS current
			DESCRIPTION
				"The auxiliary variable used to identify instances
				of the columnar objects in the WEP Default Keys Table.
				The value of this variable is equal to the WEPDefaultKeyID + 1"
			::= { hwWsecWEPDefaultKeysEntry 1 }

		
--  1.3.6.1.4.1.2011.6.139.6.2.1.2
		-- 1.3.6.1.4.1.2011.6.139.6.2.1.2
		hwWsecWEPDefaultKeyValue OBJECT-TYPE
			SYNTAX OCTET STRING
			MAX-ACCESS read-write
			STATUS current
			DESCRIPTION
				"A WEP default secret hexadecimal key value.
				10 byte for WEP-40, 26 byte for WEP-104, 32 byte for WEP-128.
				Reading this variable shall return unsuccessful status or null or zero."
			::= { hwWsecWEPDefaultKeysEntry 2 }

		
--  1.3.6.1.4.1.2011.6.139.6.2.1.4
		-- 1.3.6.1.4.1.2011.6.139.6.2.1.4
		hwWsecWEPPassPhrase OBJECT-TYPE
			SYNTAX DisplayString
			MAX-ACCESS read-write
			STATUS current
			DESCRIPTION
				"A WEP default secret ASCII key value.
				5 byte for WEP-40, 13 byte for WEP-104, 16 byte for WEP-128.
				Reading this variable shall return unsuccessful status or null or zero."
			::= { hwWsecWEPDefaultKeysEntry 4 }

		
--  1.3.6.1.4.1.2011.6.139.6.3
		-- 1.3.6.1.4.1.2011.6.139.6.3
		hwWsecWEPKeyMappingsTable OBJECT-TYPE
			SYNTAX SEQUENCE OF HwWsecWEPKeyMappingsEntry
			MAX-ACCESS not-accessible
			STATUS current
			DESCRIPTION
				"Conceptual table for WEP Key Mappings. The MIB supports
				the ability to share a separate WEP key for each RA/TA
				pair. The Key Mappings Table contains zero or one entry
				for each MAC address and contains two fields for each
				entry: WEPOn and the corresponding WEP key. The WEP key
				mappings are logically WRITE-ONLY. Attempts to read the
				entries in this table shall return unsuccessful status and
				values of null or zero. The default value for all WEPOn
				fields is FALSE."
			REFERENCE
				"IEEE Std 802.11-2007, 8.3.2"
			::= { hwWlanSecurity 3 }

		
--  1.3.6.1.4.1.2011.6.139.6.3.1
		-- 1.3.6.1.4.1.2011.6.139.6.3.1
		hwWsecWEPKeyMappingsEntry OBJECT-TYPE
			SYNTAX HwWsecWEPKeyMappingsEntry
			MAX-ACCESS not-accessible
			STATUS current
			DESCRIPTION
				"An Entry (conceptual row) in the WEP Key Mappings Table."
			INDEX { hwWsecProfileName, hwWsecWEPKeyMappingIndex }
			::= { hwWsecWEPKeyMappingsTable 1 }

		
		HwWsecWEPKeyMappingsEntry ::=
			SEQUENCE { 
				hwWsecWEPKeyMappingIndex
					Integer32,
				hwWsecWEPKeyMappingAddress
					MacAddress,
				hwWsecWEPKeyMappingWEPOn
					TruthValue,
				hwWsecWEPKeyMappingValue
					OCTET STRING,
				hwWsecWEPKeyMappingStatus
					RowStatus
			 }

--  1.3.6.1.4.1.2011.6.139.6.3.1.1
		-- 1.3.6.1.4.1.2011.6.139.6.3.1.1
		hwWsecWEPKeyMappingIndex OBJECT-TYPE
			SYNTAX Integer32
			MAX-ACCESS not-accessible
			STATUS current
			DESCRIPTION
				"The auxiliary variable used to identify instances
				of the columnar objects in the WEP Key Mappings Table."
			::= { hwWsecWEPKeyMappingsEntry 1 }

		
--  1.3.6.1.4.1.2011.6.139.6.3.1.2
		-- 1.3.6.1.4.1.2011.6.139.6.3.1.2
		hwWsecWEPKeyMappingAddress OBJECT-TYPE
			SYNTAX MacAddress
			MAX-ACCESS read-create
			STATUS current
			DESCRIPTION
				"The MAC address of the STA for which the values from this
				key mapping entry are to be used."
			::= { hwWsecWEPKeyMappingsEntry 2 }

		
--  1.3.6.1.4.1.2011.6.139.6.3.1.3
		-- 1.3.6.1.4.1.2011.6.139.6.3.1.3
		hwWsecWEPKeyMappingWEPOn OBJECT-TYPE
			SYNTAX TruthValue
			MAX-ACCESS read-create
			STATUS current
			DESCRIPTION
				"Boolean as to whether WEP is to be used when communicating
				with the hwWsecWEPKeyMappingAddress STA."
			::= { hwWsecWEPKeyMappingsEntry 3 }

		
--  1.3.6.1.4.1.2011.6.139.6.3.1.4
		-- 1.3.6.1.4.1.2011.6.139.6.3.1.4
		hwWsecWEPKeyMappingValue OBJECT-TYPE
			SYNTAX OCTET STRING
			MAX-ACCESS read-create
			STATUS current
			DESCRIPTION
				"A WEP secret key value."
			::= { hwWsecWEPKeyMappingsEntry 4 }

		
--  1.3.6.1.4.1.2011.6.139.6.3.1.5
		-- 1.3.6.1.4.1.2011.6.139.6.3.1.5
		hwWsecWEPKeyMappingStatus OBJECT-TYPE
			SYNTAX RowStatus
			MAX-ACCESS read-create
			STATUS current
			DESCRIPTION
				"The status column used for creating, modifying, and
				deleting instances of the columnar objects in the WEP key
				mapping Table."
			DEFVAL { active }
			::= { hwWsecWEPKeyMappingsEntry 5 }

		
--  1.3.6.1.4.1.2011.6.139.6.4
		-- 1.3.6.1.4.1.2011.6.139.6.4
		hwWsecAuthSuitesTable OBJECT-TYPE
			SYNTAX SEQUENCE OF HwWsecAuthSuitesEntry
			MAX-ACCESS not-accessible
			STATUS current
			DESCRIPTION
				"This table lists the AKM suites supported by this entity. Each AKM
				suite can be individually enabled and disabled. The AKM suite list
				in the RSN information element is formed using the information in
				this table."
			::= { hwWlanSecurity 4 }

		
--  1.3.6.1.4.1.2011.6.139.6.4.1
		-- 1.3.6.1.4.1.2011.6.139.6.4.1
		hwWsecAuthSuitesEntry OBJECT-TYPE
			SYNTAX HwWsecAuthSuitesEntry
			MAX-ACCESS not-accessible
			STATUS current
			DESCRIPTION
				"An entry (row) in the hwWsecAuthSuitesTable."
			INDEX { hwWsecProfileName, hwWsecAuthSuiteIndex }
			::= { hwWsecAuthSuitesTable 1 }

		
		HwWsecAuthSuitesEntry ::=
			SEQUENCE { 
				hwWsecAuthSuiteIndex
					INTEGER,
				hwWsecAuthSuite
					OCTET STRING,
				hwWsecAuthSuiteEnabled
					TruthValue,
				hwWsecAuthPreauthenticationImplemented
					TruthValue,
				hwWsecAuthPreauthenticationEnabled
					TruthValue,
				hwWsecAuthUnicastKeysSupported
					Integer32,
				hwWsecAuthPairwiseCipher
					INTEGER,
				hwWsecAuthPairwiseCipherSize
					Integer32,
				hwWsecAuthUnicastRekeyMethod
					INTEGER,
				hwWsecAuthUnicastRekeyTime
					Unsigned32,
				hwWsecAuthUnicastRekeyPackets
					Unsigned32,
				hwWsecAuthMulticastCipher
					INTEGER,
				hwWsecAuthMulticastCipherSize
					Integer32,
				hwWsecAuthMulticastRekeyMethod
					INTEGER,
				hwWsecAuthMulticastRekeyTime
					Unsigned32,
				hwWsecAuthMulticastRekeyPackets
					Unsigned32,
				hwWsecAuthMulticastRekeyStrict
					TruthValue,
				hwWsecAuthPSKValue
					OCTET STRING,
				hwWsecAuthPSKPassPhrase
					DisplayString,
				hwWsecAuthCertificateUpdateCount
					Unsigned32,
				hwWsecAuthMulticastUpdateCount
					Unsigned32,
				hwWsecAuthUnicastUpdateCount
					Unsigned32,
				hwWsecAuthBKLifetime
					Unsigned32,
				hwWsecAuthBKReauthThreshold
					Unsigned32,
				hwWsecAuthSATimeout
					Unsigned32,
				hwWsecAuthExcludeUnencrypted
					TruthValue,
				hwWsecAuthDot1XMethod
					Integer32,
				hwWsecAuthControlledAuthControl
					TruthValue,
				hwWsecAuthControlledPortControl
					Integer32,
				hwWsecAuthOptionalImplemented
					TruthValue
			 }

--  1.3.6.1.4.1.2011.6.139.6.4.1.1
		-- 1.3.6.1.4.1.2011.6.139.6.4.1.1
		hwWsecAuthSuiteIndex OBJECT-TYPE
			SYNTAX INTEGER
				{
				wapiCertification(1),
				wapiPreShareKey(2),
				wpa18021x(3),
				wpa1PreShareKey(4),
				wpa28021x(5),
				wpa2PreShareKey(6),
				shareKey(7),
				openSystem(8),
				wpa1wpa2PreShareKey(9),
				wpa1wpa28021x(10)
				}
			MAX-ACCESS not-accessible
			STATUS current
			DESCRIPTION
				"The auxiliary variable used as an index into the
				hwWsecAuthSuitesTable."
			::= { hwWsecAuthSuitesEntry 1 }

		
--  1.3.6.1.4.1.2011.6.139.6.4.1.2
		-- 1.3.6.1.4.1.2011.6.139.6.4.1.2
		hwWsecAuthSuite OBJECT-TYPE
			SYNTAX OCTET STRING (SIZE (4))
			MAX-ACCESS read-only
			STATUS current
			DESCRIPTION
				"The selector of an AKM suite. It consists of an OUI (the first 3
				octets) and a cipher suite identifier (the last octet).
				
				0x00147201 : WAPI certification authentication
				0x00147202 : WAPI preShare key authentication
				0x000FAC01 : WPA1(WPA version 1) 802.1X authentication
				0x000FAC02 : WPA1(WPA version 1) preShare key authentication                
				0x00E0FC01 : WPA2(WPA version 2) 802.1X authentication
				0x00E0FC02 : WPA2(WPA version 2) preShare key authentication
				0x00E0FC03 : share key (for WEP)
				0x00E0FC04 : open system (no authentication)  
				0x00E0FC05 : wpa-wpa2-preShareKey  
				0x00E0FC06 : wpa-wpa2-8021x                                                      
				
				"
			::= { hwWsecAuthSuitesEntry 2 }

		
--  1.3.6.1.4.1.2011.6.139.6.4.1.3
		-- 1.3.6.1.4.1.2011.6.139.6.4.1.3
		hwWsecAuthSuiteEnabled OBJECT-TYPE
			SYNTAX TruthValue
			MAX-ACCESS read-write
			STATUS current
			DESCRIPTION
				"This variable indicates whether the corresponding AKM suite is
				enabled/disabled."
			::= { hwWsecAuthSuitesEntry 3 }

		
--  1.3.6.1.4.1.2011.6.139.6.4.1.4
		-- 1.3.6.1.4.1.2011.6.139.6.4.1.4
		hwWsecAuthPreauthenticationImplemented OBJECT-TYPE
			SYNTAX TruthValue
			MAX-ACCESS read-only
			STATUS current
			DESCRIPTION
				"This variable indicates whether the entity supports WAPI pre-authentication. This cannot
				be TRUE unless hwWsecAuthOptionImplemented is TRUE."
			::= { hwWsecAuthSuitesEntry 4 }

		
--  1.3.6.1.4.1.2011.6.139.6.4.1.5
		-- 1.3.6.1.4.1.2011.6.139.6.4.1.5
		hwWsecAuthPreauthenticationEnabled OBJECT-TYPE
			SYNTAX TruthValue
			MAX-ACCESS read-write
			STATUS current
			DESCRIPTION
				"When this object is set to TRUE, this shall indicate that WAPI pre-authentication is
				enabled on this entity. This object requires that WAPI authentication of this profile Enabled."
			::= { hwWsecAuthSuitesEntry 5 }

		
--  1.3.6.1.4.1.2011.6.139.6.4.1.6
		-- 1.3.6.1.4.1.2011.6.139.6.4.1.6
		hwWsecAuthUnicastKeysSupported OBJECT-TYPE
			SYNTAX Integer32
			MAX-ACCESS read-only
			STATUS current
			DESCRIPTION
				"This object indicates the number of the unicast keys that a WAPI/RSNA of this entity supports."
			::= { hwWsecAuthSuitesEntry 6 }

		
--  SYNTAX OCTET STRING 
-- 1.3.6.1.4.1.2011.6.139.6.4.1.7
		-- 1.3.6.1.4.1.2011.6.139.6.4.1.7
		hwWsecAuthPairwiseCipher OBJECT-TYPE
			SYNTAX INTEGER
				{
				wpiSms4(1),
				wep40(2),
				wep104(3),
				tkip(4),
				ccmp(5),
				null(6),
				tkipCcmp(7),
				wep128(8)
				}
			MAX-ACCESS read-write
			STATUS current
			DESCRIPTION
				"The selector of a supported pairwise cipher. It consists of an OUI
				(the first 3 octets) and a cipher suite identifier (the last octet).
				
				0x00147201 : WPI-SMS4
				0x000FAC00 : Use group cipher suite
				0x000FAC01 : WEP-40
				0x000FAC02 : TKIP
				0x000FAC04 : CCMP-default in an RSNA
				0x000FAC05 : WEP-104
				0x000FAC06 : wep-128
 	                        0x000FAC07 : tkip-ccmp
				0x00E0FC01 : null (no encryption), only for open system authentication                       
				
				The cipher suite selector 00-0F-AC:4 (CCMP) shall be the default cipher suite value.
				The cipher suite selectors 00-0F-AC:1 (WEP-40) and 00-0F-AC:5 (WEP-104) are only valid as a group
				cipher suite in a transition security network (TSN) to allow pre-RSNA devices to join the BSS.
				
				Use of CCMP as the group cipher suite with TKIP as the pairwise cipher suite shall not be supported.
				
				NOTE?If the STAs can support CCMP, then there is no need for a weaker data confidentiality protocol.
				
				The cipher suite selector 00-0F-AC:0 (Use group cipher suite) is only valid as the pairwise cipher suite. An
				AP may specify the selector 00-0F-AC:0 (Use group cipher suite) for a pairwise cipher suite if it does not              
				cipher selection, this shall be the only pairwise cipher selection the AP advertises.
				
				If CCMP is enabled, then the AP supports pairwise keys, and thus the suite selector 00-0F-AC:0 (Use group
				cipher suite) shall not be a valid option.
				"
			::= { hwWsecAuthSuitesEntry 7 }

		
--  1.3.6.1.4.1.2011.6.139.6.4.1.8
		-- 1.3.6.1.4.1.2011.6.139.6.4.1.8
		hwWsecAuthPairwiseCipherSize OBJECT-TYPE
			SYNTAX Integer32
			MAX-ACCESS read-only
			STATUS current
			DESCRIPTION
				"This object indicates the length in bits of the pairwise cipher
				key. This should be 256 for TKIP and 128 for CCMP."
			::= { hwWsecAuthSuitesEntry 8 }

		
--  1.3.6.1.4.1.2011.6.139.6.4.1.9
		-- 1.3.6.1.4.1.2011.6.139.6.4.1.9
		hwWsecAuthUnicastRekeyMethod OBJECT-TYPE
			SYNTAX INTEGER
				{
				disabled(1),
				timeBased(2),
				packetBased(3),
				timepacketBased(4)
				}
			MAX-ACCESS read-write
			STATUS current
			DESCRIPTION
				"This object selects a mechanism for rekeying the WAPI/RSNA USK. The default is time-based,
				once per day. Rekeying the USK is only applicable to an entity acting in the AE or ASUE
				role."
			DEFVAL { timeBased }
			::= { hwWsecAuthSuitesEntry 9 }

		
--  1.3.6.1.4.1.2011.6.139.6.4.1.10
		-- 1.3.6.1.4.1.2011.6.139.6.4.1.10
		hwWsecAuthUnicastRekeyTime OBJECT-TYPE
			SYNTAX Unsigned32
			UNITS "seconds"
			MAX-ACCESS read-write
			STATUS current
			DESCRIPTION
				"The time in seconds after which the WAPI/RSNA USK shall be refreshed. The timer shall start
				at the moment the USK was set using the MLME-SETWPIKEYS.request primitive."
			DEFVAL { 86400 }
			::= { hwWsecAuthSuitesEntry 10 }

		
--  1.3.6.1.4.1.2011.6.139.6.4.1.11
		-- 1.3.6.1.4.1.2011.6.139.6.4.1.11
		hwWsecAuthUnicastRekeyPackets OBJECT-TYPE
			SYNTAX Unsigned32
			UNITS "1000 packets"
			MAX-ACCESS read-write
			STATUS current
			DESCRIPTION
				"A packet count (in 1000s of packets) after which the WAPI/RSNA USK shall be refreshed. The
				packet counter shall start at the moment the USK was set using the
				MLME-SETWPIKEYS.request primitive and it shall count all packets encrypted using
				the current USK."
			::= { hwWsecAuthSuitesEntry 11 }

		
--  SYNTAX OCTET STRING 
-- 1.3.6.1.4.1.2011.6.139.6.4.1.12
		-- 1.3.6.1.4.1.2011.6.139.6.4.1.12
		hwWsecAuthMulticastCipher OBJECT-TYPE
			SYNTAX INTEGER
				{
				wpiSms4(1),
				wep40(2),
				wep104(3),
				tkip(4),
				ccmp(5),
				null(6),
				tkipCcmp(7),
				wep128(8)
				}
			MAX-ACCESS read-write
			STATUS current
			DESCRIPTION
				"This object indicates the multicast cipher suite that this entity must adopt. The WAPI/RSNA
				information element shall adopt the value of this variable, which contains a 3-octet OUI and
				a one-octet cipher suite identifier.
				
				0x00147201 : WPI-SMS4               
				0x000FAC01 : WEP-40
				0x000FAC02 : TKIP
				0x000FAC04 : CCMP-default in an RSNA
				0x000FAC05 : WEP-104
				0x000FAC06 : wep-128
 	                        0x000FAC07 : tkip-ccmp
				0x00E0FC01 : null (no encryption), only for open system authentication                                                                               
				"
			::= { hwWsecAuthSuitesEntry 12 }

		
--  1.3.6.1.4.1.2011.6.139.6.4.1.13
		-- 1.3.6.1.4.1.2011.6.139.6.4.1.13
		hwWsecAuthMulticastCipherSize OBJECT-TYPE
			SYNTAX Integer32
			MAX-ACCESS read-only
			STATUS current
			DESCRIPTION
				"This object indicates the length in bit of the multicast cipher key. 
				
				This should be 256 for in SMS4. 
				The former 128bits is the encryption key and the latter 128bits is the message
				integrity check key.
				
				This should be 256 for in TKIP.
				The former 128bits is the encryption key and the latter 128bits is the message
				integrity check key.
				
				This should be 128 for in CCMP. 
				The 128bits is the encryption key and the message integrity check key.                                                
				
				This should be 40 for in WEP-40. 
				The 40bits is the encryption key. 
				
				This should be 40 for in WEP-104. 
				The 104bits is the encryption key. 

				This should be 40 for in WEP-128. 
				The 128bits is the encryption key.                                                
				"
			::= { hwWsecAuthSuitesEntry 13 }

		
--  1.3.6.1.4.1.2011.6.139.6.4.1.14
		-- 1.3.6.1.4.1.2011.6.139.6.4.1.14
		hwWsecAuthMulticastRekeyMethod OBJECT-TYPE
			SYNTAX INTEGER
				{
				disabled(1),
				timeBased(2),
				packetBased(3),
				timepacketBased(4)
				}
			MAX-ACCESS read-write
			STATUS current
			DESCRIPTION
				"This object selects a mechanism for rekeying the WAPI/RSNA MSK. The default is time-based,
				once per day. Rekeying the MSK is only applicable to an entity acting in the
				Authenticator role."
			DEFVAL { timeBased }
			::= { hwWsecAuthSuitesEntry 14 }

		
--  1.3.6.1.4.1.2011.6.139.6.4.1.15
		-- 1.3.6.1.4.1.2011.6.139.6.4.1.15
		hwWsecAuthMulticastRekeyTime OBJECT-TYPE
			SYNTAX Unsigned32
			UNITS "seconds"
			MAX-ACCESS read-write
			STATUS current
			DESCRIPTION
				"The time in seconds after which the WAPI/RSNA MSK shall be refreshed. The timer shall start
				at the moment the MSK was set using the MLME-SETWPIKEYS.request primitive."
			DEFVAL { 86400 }
			::= { hwWsecAuthSuitesEntry 15 }

		
--  1.3.6.1.4.1.2011.6.139.6.4.1.16
		-- 1.3.6.1.4.1.2011.6.139.6.4.1.16
		hwWsecAuthMulticastRekeyPackets OBJECT-TYPE
			SYNTAX Unsigned32
			UNITS "1000 packets"
			MAX-ACCESS read-write
			STATUS current
			DESCRIPTION
				"A packet count (in 1000s of packets) after which the WAPI/RSNA MSK shall be refreshed. The
				packet counter shall start at the moment the MSK was set using the
				MLME-SETWPIKEYS.request primitive and it shall count all packets encrypted using
				the current MSK."
			::= { hwWsecAuthSuitesEntry 16 }

		
--  1.3.6.1.4.1.2011.6.139.6.4.1.17
		-- 1.3.6.1.4.1.2011.6.139.6.4.1.17
		hwWsecAuthMulticastRekeyStrict OBJECT-TYPE
			SYNTAX TruthValue
			MAX-ACCESS read-write
			STATUS current
			DESCRIPTION
				"This object signals that the MSK shall be refreshed whenever a STA leaves the BSS that
				possesses the MSK."
			::= { hwWsecAuthSuitesEntry 17 }

		
--  1.3.6.1.4.1.2011.6.139.6.4.1.18
		-- 1.3.6.1.4.1.2011.6.139.6.4.1.18
		hwWsecAuthPSKValue OBJECT-TYPE
			SYNTAX OCTET STRING
			MAX-ACCESS read-write
			STATUS current
			DESCRIPTION
				"The PSK for when WAPI/RSNA in PSK mode is the selected AKM suite. In that case, the BK/PMK
				will obtain its value from this object. This object is logically write-only. Reading this
				variable shall return unsuccessful status or null or zero.
				WAPI need 16 byte Hex, RSNA need 32 byte Hex. User should input Hex data for this node."
			::= { hwWsecAuthSuitesEntry 18 }

		
--  1.3.6.1.4.1.2011.6.139.6.4.1.19
		-- 1.3.6.1.4.1.2011.6.139.6.4.1.19
		hwWsecAuthPSKPassPhrase OBJECT-TYPE
			SYNTAX DisplayString
			MAX-ACCESS read-write
			STATUS current
			DESCRIPTION
				"The PSK, for when WAPI/RSNA in PSK mode is the selected AKM suite, is configured by
				hwWsecAuthPSKValue. An alternative manner of setting the PSK uses the
				password-to-key algorithm. This variable provides a means to enter a pass-phrase. When
				this object is written, the WAPI/RSNA entity shall use the password-to-key algorithm to derive a
				pre-shared and populate hwWsecAuthPSKValue with this key. This object is
				logically write-only. Reading this variable shall return unsuccessful status or null or zero."
			::= { hwWsecAuthSuitesEntry 19 }

		
--  1.3.6.1.4.1.2011.6.139.6.4.1.20
		-- 1.3.6.1.4.1.2011.6.139.6.4.1.20
		hwWsecAuthCertificateUpdateCount OBJECT-TYPE
			SYNTAX Unsigned32
			MAX-ACCESS read-write
			STATUS current
			DESCRIPTION
				"The number of times messages in the WAPI Certificate Authentication Handshake
				protocol will be retried per Certificate Authentication Handshake attempt."
			DEFVAL { 3 }
			::= { hwWsecAuthSuitesEntry 20 }

		
--  1.3.6.1.4.1.2011.6.139.6.4.1.21
		-- 1.3.6.1.4.1.2011.6.139.6.4.1.21
		hwWsecAuthMulticastUpdateCount OBJECT-TYPE
			SYNTAX Unsigned32
			MAX-ACCESS read-write
			STATUS current
			DESCRIPTION
				"The number of times Message 1 in the WAPI Multicast Key Announcement Handshake
				will be retried per MSK Handshake attempt.
				
				The number of times Message 1 in the RSNA Group Key Handshake will
				be retried per GTK Handshake attempt.
				"
			DEFVAL { 3 }
			::= { hwWsecAuthSuitesEntry 21 }

		
--  1.3.6.1.4.1.2011.6.139.6.4.1.22
		-- 1.3.6.1.4.1.2011.6.139.6.4.1.22
		hwWsecAuthUnicastUpdateCount OBJECT-TYPE
			SYNTAX Unsigned32
			MAX-ACCESS read-write
			STATUS current
			DESCRIPTION
				"The number of times Message 1 and Message 3 in the WAPI Unicast Key Negotiation
				Handshake will be retried per USK Handshake attempt.
				
				The number of times Message 1 and Message 3 in the RSNA 4-Way Handshake
				will be retried per 4-Way Handshake attempt.
				"
			DEFVAL { 3 }
			::= { hwWsecAuthSuitesEntry 22 }

		
--  1.3.6.1.4.1.2011.6.139.6.4.1.23
		-- 1.3.6.1.4.1.2011.6.139.6.4.1.23
		hwWsecAuthBKLifetime OBJECT-TYPE
			SYNTAX Unsigned32
			UNITS "seconds"
			MAX-ACCESS read-write
			STATUS current
			DESCRIPTION
				"The maximum lifetime of a BK in the BK cache."
			DEFVAL { 43200 }
			::= { hwWsecAuthSuitesEntry 23 }

		
--  1.3.6.1.4.1.2011.6.139.6.4.1.24
		-- 1.3.6.1.4.1.2011.6.139.6.4.1.24
		hwWsecAuthBKReauthThreshold OBJECT-TYPE
			SYNTAX Unsigned32
			UNITS "percentage"
			MAX-ACCESS read-write
			STATUS current
			DESCRIPTION
				"The percentage of the BK lifetime that should expire before a WAI/RSNA re-authentication
				occurs."
			DEFVAL { 70 }
			::= { hwWsecAuthSuitesEntry 24 }

		
--  1.3.6.1.4.1.2011.6.139.6.4.1.25
		-- 1.3.6.1.4.1.2011.6.139.6.4.1.25
		hwWsecAuthSATimeout OBJECT-TYPE
			SYNTAX Unsigned32
			UNITS "seconds"
			MAX-ACCESS read-write
			STATUS current
			DESCRIPTION
				"The maximum time a security association shall take to set up."
			DEFVAL { 60 }
			::= { hwWsecAuthSuitesEntry 25 }

		
--  1.3.6.1.4.1.2011.6.139.6.4.1.26
		-- 1.3.6.1.4.1.2011.6.139.6.4.1.26
		hwWsecAuthExcludeUnencrypted OBJECT-TYPE
			SYNTAX TruthValue
			MAX-ACCESS read-write
			STATUS current
			DESCRIPTION
				"When this attribute is TRUE, the STA shall not indicate at the MAC service
				interface received MSDUs that have the Protected Frame subfield of
				the Frame Control field equal to zero. When this attribute is FALSE,
				the STA may accept MSDUs that have the Protected Frame subfield of
				the Frame Control field equal to zero. The default value of this attribute
				shall be FALSE."
			::= { hwWsecAuthSuitesEntry 26 }

		
--  1.3.6.1.4.1.2011.6.139.6.4.1.27
		-- 1.3.6.1.4.1.2011.6.139.6.4.1.27
		hwWsecAuthDot1XMethod OBJECT-TYPE
			SYNTAX Integer32
			MAX-ACCESS read-write
			STATUS current
			DESCRIPTION
				"
				Leaf don't sustain for V2R3 on 2012/11/26.
				"
			::= { hwWsecAuthSuitesEntry 27 }

		
--  1.3.6.1.4.1.2011.6.139.6.4.1.28
		-- 1.3.6.1.4.1.2011.6.139.6.4.1.28
		hwWsecAuthControlledAuthControl OBJECT-TYPE
			SYNTAX TruthValue
			MAX-ACCESS read-only
			STATUS current
			DESCRIPTION
				"This attribute indicates whether the entity enable the authentication. If the value is '0'
				which means 'authentication disabled', the state of the controlled port shall be set to
				'authenticated'; else the value is '1' which means 'authentication enabled', the state of the
				controlled port shall be based on the hwWsecAuthControlledPortControl."
			::= { hwWsecAuthSuitesEntry 28 }

		
--  1.3.6.1.4.1.2011.6.139.6.4.1.29
		-- 1.3.6.1.4.1.2011.6.139.6.4.1.29
		hwWsecAuthControlledPortControl OBJECT-TYPE
			SYNTAX Integer32
			MAX-ACCESS read-only
			STATUS current
			DESCRIPTION
				"This attribute, when the hwWsecAuthControlledAuthControl is set to true, shall be
				effective and indicate the methods by which the port is controlled. If the value is '0' which
				means 'auto', the state of the controlled port shall be based on the result of the
				authentication; else the value is '1' which means 'force unauthenticated', the state of the
				controlled port shall be unconditionally set to 'unauthenticated'."
			::= { hwWsecAuthSuitesEntry 29 }

		
--  1.3.6.1.4.1.2011.6.139.6.4.1.30
		-- 1.3.6.1.4.1.2011.6.139.6.4.1.30
		hwWsecAuthOptionalImplemented OBJECT-TYPE
			SYNTAX TruthValue
			MAX-ACCESS read-only
			STATUS current
			DESCRIPTION
				"This attribute, when true, shall indicate that the WAPI, WPA, RSNA option is implemented; else, this
				attribute shall be false."
			::= { hwWsecAuthSuitesEntry 30 }

		
--  1.3.6.1.4.1.2011.6.139.6.5
		-- 1.3.6.1.4.1.2011.6.139.6.5
		hwWsecStatsTable OBJECT-TYPE
			SYNTAX SEQUENCE OF HwWsecStatsEntry
			MAX-ACCESS not-accessible
			STATUS current
			DESCRIPTION
				"This table maintains per-STA statistics in an RSN. The entry with
				hwWsecStatsSTAAddress set to FF-FF-FF-FF-FF-FF shall contain
				statistics for broadcast/multicast traffic."
			::= { hwWlanSecurity 5 }

		
--  1.3.6.1.4.1.2011.6.139.6.5.1
		-- 1.3.6.1.4.1.2011.6.139.6.5.1
		hwWsecStatsEntry OBJECT-TYPE
			SYNTAX HwWsecStatsEntry
			MAX-ACCESS not-accessible
			STATUS current
			DESCRIPTION
				"An entry in the hwWsecStatsTable."
			INDEX { hwWsecStatsSTAAddress }
			::= { hwWsecStatsTable 1 }

		
		HwWsecStatsEntry ::=
			SEQUENCE { 
				hwWsecStatsSTAAddress
					MacAddress,
				hwWsecStatsVersion
					Integer32,
				hwWsecStatsBKIDUsed
					OCTET STRING,
				hwWsecStatsAuthenticationSuiteSelected
					INTEGER,
				hwWsecStatsUnicastCipherSelected
					INTEGER,
				hwWsecStatsMulticastCipherSelected
					INTEGER,
				hwWsecStatsAuthenticationSuiteRequested
					INTEGER,
				hwWsecStatsUnicastCipherRequested
					INTEGER,
				hwWsecStatsMulticastCipherRequested
					INTEGER,
				hwWsecStatsWEPICVErrorCount
					Counter32,
				hwWsecStatsWEPExcludedCount
					Counter32,
				hwWsecStatsWEPUndecryptableCount
					Counter32,
				hwWsecStatsTKIPICVErrors
					Counter32,
				hwWsecStatsTKIPLocalMICFailures
					Counter32,
				hwWsecStatsTKIPRemoteMICFailures
					Counter32,
				hwWsecStatsTKIPReplays
					Counter32,
				hwWsecStatsCCMPReplays
					Counter32,
				hwWsecStatsCCMPDecryptErrors
					Counter32,
				hwWsecStatsWAISignatureErrors
					Counter32,
				hwWsecStatsWAIHMACErrors
					Counter32,
				hwWsecStatsWAIAuthenticationResultFailures
					Counter32,
				hwWsecStatsWAIDiscardCounters
					Counter32,
				hwWsecStatsWAITimeoutCounters
					Counter32,
				hwWsecStatsWAIFormatErrors
					Counter32,
				hwWsecStatsWAICertificateHandshakeFailures
					Counter32,
				hwWsecStatsWAIUnicastHandshakeFailures
					Counter32,
				hwWsecStatsWAIMulticastHandshakeFailures
					Counter32,
				hwWsecStatsWPIReplayCounter
					Counter32,
				hwWsecStatsWPIDecryptableErrors
					Counter32,
				hwWsecStatsWPIMICErrors
					Counter32,
				hwWsecStatsControlledPortStatus
					TruthValue,
				hwWsecStatsNumberOfPTKSAReplayCounters
					Integer32,
				hwWsecStatsNumberOfGTKSAReplayCounters
					Integer32,
				hwWsecStatsTKIPCounterMeasuresInvoked
					Integer32,
				hwWsecStatsWpa4WayHandshakeFailures
					Integer32
			 }

--  1.3.6.1.4.1.2011.6.139.6.5.1.1
		-- 1.3.6.1.4.1.2011.6.139.6.5.1.1
		hwWsecStatsSTAAddress OBJECT-TYPE
			SYNTAX MacAddress
			MAX-ACCESS read-only
			STATUS current
			DESCRIPTION
				"The MAC address of the STA to which the statistics in this
				conceptual row belong."
			::= { hwWsecStatsEntry 1 }

		
--  1.3.6.1.4.1.2011.6.139.6.5.1.2
		-- 1.3.6.1.4.1.2011.6.139.6.5.1.2
		hwWsecStatsVersion OBJECT-TYPE
			SYNTAX Integer32
			MAX-ACCESS read-only
			STATUS current
			DESCRIPTION
				"The RSNA version with which the STA associated."
			::= { hwWsecStatsEntry 2 }

		
--  1.3.6.1.4.1.2011.6.139.6.5.1.3
		-- 1.3.6.1.4.1.2011.6.139.6.5.1.3
		hwWsecStatsBKIDUsed OBJECT-TYPE
			SYNTAX OCTET STRING
			MAX-ACCESS read-only
			STATUS current
			DESCRIPTION
				"The selector of the last BKID of WAPI used in the last Unicast Key Negotiation Handshake.              
				The selector of the last PMKID of RSNA used in the last 4-Way Handshake."
			::= { hwWsecStatsEntry 3 }

		
--  SYNTAX OCTET STRING        
-- 1.3.6.1.4.1.2011.6.139.6.5.1.4
		-- 1.3.6.1.4.1.2011.6.139.6.5.1.4
		hwWsecStatsAuthenticationSuiteSelected OBJECT-TYPE
			SYNTAX INTEGER
				{
				wapiCertification(1),
				wapiPreShareKey(2),
				wpa18021x(3),
				wpa1PreShareKey(4),
				wpa28021x(5),
				wpa2PreShareKey(6),
				shareKey(7),
				openSystem(8),
				wpa1wpa2PreShareKey(9),
				wpa1wpa28021x(10)
				}
			MAX-ACCESS read-only
			STATUS current
			DESCRIPTION
				"The selector of the last AKM suite negotiated."
			::= { hwWsecStatsEntry 4 }

		
--  SYNTAX OCTET STRING        
-- 1.3.6.1.4.1.2011.6.139.6.5.1.5
		-- 1.3.6.1.4.1.2011.6.139.6.5.1.5
		hwWsecStatsUnicastCipherSelected OBJECT-TYPE
			SYNTAX INTEGER
				{
				wpiSms4(1),
				wep40(2),
				wep104(3),
				tkip(4),
				ccmp(5),
				null(6),
				tkipCcmp(7),
				wep128(8)
				}
			MAX-ACCESS read-only
			STATUS current
			DESCRIPTION
				"The selector of the last unicast cipher suite negotiated."
			::= { hwWsecStatsEntry 5 }

		
--  SYNTAX OCTET STRING         
-- 1.3.6.1.4.1.2011.6.139.6.5.1.6
		-- 1.3.6.1.4.1.2011.6.139.6.5.1.6
		hwWsecStatsMulticastCipherSelected OBJECT-TYPE
			SYNTAX INTEGER
				{
				wpiSms4(1),
				wep40(2),
				wep104(3),
				tkip(4),
				ccmp(5),
				null(6),
				tkipCcmp(7),
				wep128(8)
				}
			MAX-ACCESS read-only
			STATUS current
			DESCRIPTION
				"The selector of the last multicast cipher suite negotiated"
			::= { hwWsecStatsEntry 6 }

		
--  SYNTAX OCTET STRING            
-- 1.3.6.1.4.1.2011.6.139.6.5.1.7
		-- 1.3.6.1.4.1.2011.6.139.6.5.1.7
		hwWsecStatsAuthenticationSuiteRequested OBJECT-TYPE
			SYNTAX INTEGER
				{
				wapiCertification(1),
				wapiPreShareKey(2),
				wpa18021x(3),
				wpa1PreShareKey(4),
				wpa28021x(5),
				wpa2PreShareKey(6),
				shareKey(7),
				openSystem(8),
				wpa1wpa2PreShareKey(9),
				wpa1wpa28021x(10)
				}
			MAX-ACCESS read-only
			STATUS current
			DESCRIPTION
				"The selector of the last AKM suite requested."
			::= { hwWsecStatsEntry 7 }

		
--  SYNTAX OCTET STRING          
-- 1.3.6.1.4.1.2011.6.139.6.5.1.8
		-- 1.3.6.1.4.1.2011.6.139.6.5.1.8
		hwWsecStatsUnicastCipherRequested OBJECT-TYPE
			SYNTAX INTEGER
				{
				wpiSms4(1),
				wep40(2),
				wep104(3),
				tkip(4),
				ccmp(5),
				null(6),
				tkipCcmp(7),
				wep128(8)
				}
			MAX-ACCESS read-only
			STATUS current
			DESCRIPTION
				"The selector of the last unicast cipher suite requested"
			::= { hwWsecStatsEntry 8 }

		
--  SYNTAX OCTET STRING        
-- 1.3.6.1.4.1.2011.6.139.6.5.1.9
		-- 1.3.6.1.4.1.2011.6.139.6.5.1.9
		hwWsecStatsMulticastCipherRequested OBJECT-TYPE
			SYNTAX INTEGER
				{
				wpiSms4(1),
				wep40(2),
				wep104(3),
				tkip(4),
				ccmp(5),
				null(6),
				tkipCcmp(7),
				wep128(8)
				}
			MAX-ACCESS read-only
			STATUS current
			DESCRIPTION
				"The selector of the last multicast cipher suite requested."
			::= { hwWsecStatsEntry 9 }

		
--  1.3.6.1.4.1.2011.6.139.6.5.1.10
		-- 1.3.6.1.4.1.2011.6.139.6.5.1.10
		hwWsecStatsWEPICVErrorCount OBJECT-TYPE
			SYNTAX Counter32
			MAX-ACCESS read-only
			STATUS current
			DESCRIPTION
				"This counter shall increment when a frame is received with the Protected
				Frame subfield of the Frame Control field set to one and the value
				of the ICV as received in the frame does not match the ICV value that
				is calculated for the contents of the received frame. ICV errors for
				TKIP are not counted in this variable but in
				hwWsecStatsTKIPICVErrors."
			::= { hwWsecStatsEntry 10 }

		
--  1.3.6.1.4.1.2011.6.139.6.5.1.11
		-- 1.3.6.1.4.1.2011.6.139.6.5.1.11
		hwWsecStatsWEPExcludedCount OBJECT-TYPE
			SYNTAX Counter32
			MAX-ACCESS read-only
			STATUS current
			DESCRIPTION
				"This counter shall increment when a frame is received with the Protected
				Frame subfield of the Frame Control field set to zero and the value
				of hwWsecProfileExcludeUnencrypted causes that frame to be discarded."
			::= { hwWsecStatsEntry 11 }

		
--  1.3.6.1.4.1.2011.6.139.6.5.1.12
		-- 1.3.6.1.4.1.2011.6.139.6.5.1.12
		hwWsecStatsWEPUndecryptableCount OBJECT-TYPE
			SYNTAX Counter32
			MAX-ACCESS read-only
			STATUS current
			DESCRIPTION
				"This counter shall increment when a frame is received with the
				Protected Frame subfield of the Frame Control field set to one and
				the WEPOn value for the key mapped to the transmitter's MAC address
				indicates that the frame should not have been encrypted or that frame
				is discarded due to the receiving STA not implementing the privacy
				option."
			::= { hwWsecStatsEntry 12 }

		
--  1.3.6.1.4.1.2011.6.139.6.5.1.13
		-- 1.3.6.1.4.1.2011.6.139.6.5.1.13
		hwWsecStatsTKIPICVErrors OBJECT-TYPE
			SYNTAX Counter32
			MAX-ACCESS read-only
			STATUS current
			DESCRIPTION
				"Counts the number of TKIP ICV errors encountered when decrypting
				packets for the STA."
			::= { hwWsecStatsEntry 13 }

		
--  1.3.6.1.4.1.2011.6.139.6.5.1.14
		-- 1.3.6.1.4.1.2011.6.139.6.5.1.14
		hwWsecStatsTKIPLocalMICFailures OBJECT-TYPE
			SYNTAX Counter32
			MAX-ACCESS read-only
			STATUS current
			DESCRIPTION
				"Counts the number of MIC failures encountered when checking the
				integrity of packets received from the STA at this entity."
			::= { hwWsecStatsEntry 14 }

		
--  1.3.6.1.4.1.2011.6.139.6.5.1.15
		-- 1.3.6.1.4.1.2011.6.139.6.5.1.15
		hwWsecStatsTKIPRemoteMICFailures OBJECT-TYPE
			SYNTAX Counter32
			MAX-ACCESS read-only
			STATUS current
			DESCRIPTION
				"Counts the number of MIC failures encountered by the STA identified
				by dot11StatsSTAAddress and reported back to this entity."
			::= { hwWsecStatsEntry 15 }

		
--  1.3.6.1.4.1.2011.6.139.6.5.1.16
		-- 1.3.6.1.4.1.2011.6.139.6.5.1.16
		hwWsecStatsTKIPReplays OBJECT-TYPE
			SYNTAX Counter32
			MAX-ACCESS read-only
			STATUS current
			DESCRIPTION
				"Counts the number of TKIP replay errors detected."
			::= { hwWsecStatsEntry 16 }

		
--  1.3.6.1.4.1.2011.6.139.6.5.1.17
		-- 1.3.6.1.4.1.2011.6.139.6.5.1.17
		hwWsecStatsCCMPReplays OBJECT-TYPE
			SYNTAX Counter32
			MAX-ACCESS read-only
			STATUS current
			DESCRIPTION
				"The number of received CCMP MPDUs discarded by the replay
				mechanism."
			::= { hwWsecStatsEntry 17 }

		
--  1.3.6.1.4.1.2011.6.139.6.5.1.18
		-- 1.3.6.1.4.1.2011.6.139.6.5.1.18
		hwWsecStatsCCMPDecryptErrors OBJECT-TYPE
			SYNTAX Counter32
			MAX-ACCESS read-only
			STATUS current
			DESCRIPTION
				"The number of received MPDUs discarded by the CCMP decryption
				algorithm."
			::= { hwWsecStatsEntry 18 }

		
--  1.3.6.1.4.1.2011.6.139.6.5.1.19
		-- 1.3.6.1.4.1.2011.6.139.6.5.1.19
		hwWsecStatsWAISignatureErrors OBJECT-TYPE
			SYNTAX Counter32
			MAX-ACCESS read-only
			STATUS current
			DESCRIPTION
				"This counter shall increment when the signature in the received WAI packet is wrong."
			::= { hwWsecStatsEntry 19 }

		
--  1.3.6.1.4.1.2011.6.139.6.5.1.20
		-- 1.3.6.1.4.1.2011.6.139.6.5.1.20
		hwWsecStatsWAIHMACErrors OBJECT-TYPE
			SYNTAX Counter32
			MAX-ACCESS read-only
			STATUS current
			DESCRIPTION
				"This counter shall increment when the message authentication code in the received WAI
				packet is wrong."
			::= { hwWsecStatsEntry 20 }

		
--  1.3.6.1.4.1.2011.6.139.6.5.1.21
		-- 1.3.6.1.4.1.2011.6.139.6.5.1.21
		hwWsecStatsWAIAuthenticationResultFailures OBJECT-TYPE
			SYNTAX Counter32
			MAX-ACCESS read-only
			STATUS current
			DESCRIPTION
				"This counter shall increment when the WAI authentication is unsuccessful."
			::= { hwWsecStatsEntry 21 }

		
--  1.3.6.1.4.1.2011.6.139.6.5.1.22
		-- 1.3.6.1.4.1.2011.6.139.6.5.1.22
		hwWsecStatsWAIDiscardCounters OBJECT-TYPE
			SYNTAX Counter32
			MAX-ACCESS read-only
			STATUS current
			DESCRIPTION
				"This counter shall increment when the received WAI packet is discarded."
			::= { hwWsecStatsEntry 22 }

		
--  1.3.6.1.4.1.2011.6.139.6.5.1.23
		-- 1.3.6.1.4.1.2011.6.139.6.5.1.23
		hwWsecStatsWAITimeoutCounters OBJECT-TYPE
			SYNTAX Counter32
			MAX-ACCESS read-only
			STATUS current
			DESCRIPTION
				"This counter shall increment when the WAI packet is timeout."
			::= { hwWsecStatsEntry 23 }

		
--  1.3.6.1.4.1.2011.6.139.6.5.1.24
		-- 1.3.6.1.4.1.2011.6.139.6.5.1.24
		hwWsecStatsWAIFormatErrors OBJECT-TYPE
			SYNTAX Counter32
			MAX-ACCESS read-only
			STATUS current
			DESCRIPTION
				"This counter shall increment when there exists format error in the WAI packet."
			::= { hwWsecStatsEntry 24 }

		
--  1.3.6.1.4.1.2011.6.139.6.5.1.25
		-- 1.3.6.1.4.1.2011.6.139.6.5.1.25
		hwWsecStatsWAICertificateHandshakeFailures OBJECT-TYPE
			SYNTAX Counter32
			MAX-ACCESS read-only
			STATUS current
			DESCRIPTION
				"This counter shall increment when the WAI certificate authentication is unsuccessful."
			::= { hwWsecStatsEntry 25 }

		
--  1.3.6.1.4.1.2011.6.139.6.5.1.26
		-- 1.3.6.1.4.1.2011.6.139.6.5.1.26
		hwWsecStatsWAIUnicastHandshakeFailures OBJECT-TYPE
			SYNTAX Counter32
			MAX-ACCESS read-only
			STATUS current
			DESCRIPTION
				"This counter shall increment when the WAI unicast key negotiation process is
				unsuccessful."
			::= { hwWsecStatsEntry 26 }

		
--  1.3.6.1.4.1.2011.6.139.6.5.1.27
		-- 1.3.6.1.4.1.2011.6.139.6.5.1.27
		hwWsecStatsWAIMulticastHandshakeFailures OBJECT-TYPE
			SYNTAX Counter32
			MAX-ACCESS read-only
			STATUS current
			DESCRIPTION
				"This counter shall increment when the WAI multicast key announcement process is
				unsuccessful."
			::= { hwWsecStatsEntry 27 }

		
--  1.3.6.1.4.1.2011.6.139.6.5.1.28
		-- 1.3.6.1.4.1.2011.6.139.6.5.1.28
		hwWsecStatsWPIReplayCounter OBJECT-TYPE
			SYNTAX Counter32
			MAX-ACCESS read-only
			STATUS current
			DESCRIPTION
				"The number of received WPI MPDUs discarded by the replay mechanism."
			::= { hwWsecStatsEntry 28 }

		
--  1.3.6.1.4.1.2011.6.139.6.5.1.29
		-- 1.3.6.1.4.1.2011.6.139.6.5.1.29
		hwWsecStatsWPIDecryptableErrors OBJECT-TYPE
			SYNTAX Counter32
			MAX-ACCESS read-only
			STATUS current
			DESCRIPTION
				"The number of received MPDUs discarded by the WPI decryption algorithm because of no
				valid key."
			::= { hwWsecStatsEntry 29 }

		
--  1.3.6.1.4.1.2011.6.139.6.5.1.30
		-- 1.3.6.1.4.1.2011.6.139.6.5.1.30
		hwWsecStatsWPIMICErrors OBJECT-TYPE
			SYNTAX Counter32
			MAX-ACCESS read-only
			STATUS current
			DESCRIPTION
				"The number of received MPDUs discarded because of the MIC check error during the WPI
				decryption."
			::= { hwWsecStatsEntry 30 }

		
--  1.3.6.1.4.1.2011.6.139.6.5.1.31
		-- 1.3.6.1.4.1.2011.6.139.6.5.1.31
		hwWsecStatsControlledPortStatus OBJECT-TYPE
			SYNTAX TruthValue
			MAX-ACCESS read-only
			STATUS current
			DESCRIPTION
				"This attribute indicates the state of the controlled port in a authenticator subsystem. If value
				is '1', the state is set to'authenticated'; else, the state is set to 'unauthenticated'."
			::= { hwWsecStatsEntry 31 }

		
--  1.3.6.1.4.1.2011.6.139.6.5.1.32
		-- 1.3.6.1.4.1.2011.6.139.6.5.1.32
		hwWsecStatsNumberOfPTKSAReplayCounters OBJECT-TYPE
			SYNTAX Integer32
			MAX-ACCESS read-only
			STATUS current
			DESCRIPTION
				"Specifies the number of PTKSA replay counters per association:
				0 ?> 1 replay counter,
				1 ?> 2 replay counters,
				2 ?> 4 replay counters,
				3 ?> 16 replay counters"
			::= { hwWsecStatsEntry 32 }

		
--  1.3.6.1.4.1.2011.6.139.6.5.1.33
		-- 1.3.6.1.4.1.2011.6.139.6.5.1.33
		hwWsecStatsNumberOfGTKSAReplayCounters OBJECT-TYPE
			SYNTAX Integer32
			MAX-ACCESS read-only
			STATUS current
			DESCRIPTION
				"Specifies the number of GTKSA replay counters per association:
				0 ?> 1 replay counter,
				1 ?> 2 replay counters,
				2 ?> 4 replay counters,
				3 ?> 16 replay counters"
			::= { hwWsecStatsEntry 33 }

		
--  1.3.6.1.4.1.2011.6.139.6.5.1.34
		-- 1.3.6.1.4.1.2011.6.139.6.5.1.34
		hwWsecStatsTKIPCounterMeasuresInvoked OBJECT-TYPE
			SYNTAX Integer32
			MAX-ACCESS read-only
			STATUS current
			DESCRIPTION
				"Counts the number of times that a TKIP MIC failure occurred two
				times within 60 s and TKIP countermeasures were invoked. This
				attribute counts both local and remote MIC failure events reported
				to this STA. It increments every time TKIP countermeasures are
				invoked"
			::= { hwWsecStatsEntry 34 }

		
--  1.3.6.1.4.1.2011.6.139.6.5.1.35
		-- 1.3.6.1.4.1.2011.6.139.6.5.1.35
		hwWsecStatsWpa4WayHandshakeFailures OBJECT-TYPE
			SYNTAX Integer32
			MAX-ACCESS read-only
			STATUS current
			DESCRIPTION
				"Counts the number of 4-Way Handshake failures."
			::= { hwWsecStatsEntry 35 }

		
--  1.3.6.1.4.1.2011.6.139.6.6
		-- 1.3.6.1.4.1.2011.6.139.6.6
		hwWsecBatchProfileInfo OBJECT IDENTIFIER ::= { hwWlanSecurity 6 }

		
--  1.3.6.1.4.1.2011.6.139.6.6.1
		-- 1.3.6.1.4.1.2011.6.139.6.6.1
		hwWsecBatchProfileStartNumber OBJECT-TYPE
			SYNTAX Integer32
			MAX-ACCESS read-write
			STATUS current
			DESCRIPTION
				"The security profile start number in batch operation. This node is used with node
				hwWsecBatchProfileWantNumber, for example, hwWsecBatchProfileStartNumber
				is set to one, and hwWsecBatchProfileWantNumber is set to three, then get
				the node hwWsecBatchProfileReturnNumber,hwWsecBatchProfileName,
				that means start from the first security profile, get three
				security profile's name list. if it dose not exist three security profile, the 
				hwWsecBatchProfileReturnNumber will be the real security profile number, otherwise,
				it is equal to hwWsecBatchProfileWantNumber."
			::= { hwWsecBatchProfileInfo 1 }

		
--  1.3.6.1.4.1.2011.6.139.6.6.2
		-- 1.3.6.1.4.1.2011.6.139.6.6.2
		hwWsecBatchProfileWantNumber OBJECT-TYPE
			SYNTAX Integer32
			MAX-ACCESS read-write
			STATUS current
			DESCRIPTION
				"The security profile number that want to get in batch operation.This node is used with node
				hwWsecBatchProfileWantNumber, for example, hwWsecBatchProfileStartNumber
				is set to one, and hwWsecBatchProfileWantNumber is set to three, then get
				the node hwWsecBatchProfileReturnNumber,hwWsecBatchProfileName,
				that means start from the first security profile, get three
				security profile's name list. if it dose not exist three security profile, the 
				hwWsecBatchProfileReturnNumber will be the real security profile number, otherwise,
				it is equal to hwWsecBatchProfileWantNumber."
			::= { hwWsecBatchProfileInfo 2 }

		
--  1.3.6.1.4.1.2011.6.139.6.6.3
		-- 1.3.6.1.4.1.2011.6.139.6.6.3
		hwWsecBatchProfileReturnNumber OBJECT-TYPE
			SYNTAX Integer32
			MAX-ACCESS read-only
			STATUS current
			DESCRIPTION
				"The ess number get in batch operation."
			::= { hwWsecBatchProfileInfo 3 }

		
--  1.3.6.1.4.1.2011.6.139.6.6.4
		-- 1.3.6.1.4.1.2011.6.139.6.6.4
		hwWsecBatchProfileName OBJECT-TYPE
			SYNTAX OCTET STRING
			MAX-ACCESS read-only
			STATUS current
			DESCRIPTION
				"The names of security profile which are determined by node hwWsecBatchProfileStratNumber
				and node hwWsecBatchProfileWantNumber.
				each hwWsecProfileName name is divided by '?'."
			::= { hwWsecBatchProfileInfo 4 }

		
--  1.3.6.1.4.1.2011.6.139.6.9
		-- 1.3.6.1.4.1.2011.6.139.6.9
		hwWsecNotifications OBJECT IDENTIFIER ::= { hwWlanSecurity 9 }

		
--  1.3.6.1.4.1.2011.6.139.6.9.1
		-- 1.3.6.1.4.1.2011.6.139.6.9.1
		hwWsecNotify OBJECT IDENTIFIER ::= { hwWsecNotifications 1 }

		
--  1.3.6.1.4.1.2011.6.139.6.9.1.1
		-- 1.3.6.1.4.1.2011.6.139.6.9.1.1
		hwStaAuthErrorNotify NOTIFICATION-TYPE
			OBJECTS { hwApIndex, hwApMac, hwRadioID, hwStaAssocBssid, hwWlanServiceEssSsid, 
				hwWlanServiceStaMac, hwStaAuthenticationMode, hwStaFailCodeType, hwStaAuthenticationFailCause, hwStaAuthenticationFailCauseStr
				 }
			STATUS current
			DESCRIPTION 
				"Description."
			::= { hwWsecNotify 1 }

		
--  1.3.6.1.4.1.2011.6.139.6.9.1.2
		-- 1.3.6.1.4.1.2011.6.139.6.9.1.2
		hwStaAssociationFailNotify NOTIFICATION-TYPE
			OBJECTS { hwApIndex, hwApMac, hwRadioID, hwStaAssocBssid, hwWlanServiceEssSsid, 
				hwWlanServiceStaMac, hwStaFailCodeType, hwStaAssociationFailCause, hwStaAssociationFailCauseStr }
			STATUS current
			DESCRIPTION 
				"Description."
			::= { hwWsecNotify 2 }

		
--  1.3.6.1.4.1.2011.6.139.6.9.1.3
		-- 1.3.6.1.4.1.2011.6.139.6.9.1.3
		hwUserWithInvalidCerficationInbreakNetworkNotify NOTIFICATION-TYPE
			OBJECTS { hwApIndex, hwRadioID, hwApMac, hwStaAssocBssid, hwWlanServiceEssSsid, 
				hwWlanServiceStaMac }
			STATUS current
			DESCRIPTION 
				"Description."
			::= { hwWsecNotify 3 }

		
--  1.3.6.1.4.1.2011.6.139.6.9.1.4
		-- 1.3.6.1.4.1.2011.6.139.6.9.1.4
		hwStationRepititiveAttackNotify NOTIFICATION-TYPE
			OBJECTS { hwApIndex, hwRadioID, hwApMac, hwStaAssocBssid, hwWlanServiceEssSsid, 
				hwWlanServiceStaMac }
			STATUS current
			DESCRIPTION 
				"Description."
			::= { hwWsecNotify 4 }

		
--  1.3.6.1.4.1.2011.6.139.6.9.1.5
		-- 1.3.6.1.4.1.2011.6.139.6.9.1.5
		hwTamperAttackNotify NOTIFICATION-TYPE
			OBJECTS { hwApIndex, hwRadioID, hwApMac, hwStaAssocBssid, hwWlanServiceEssSsid, 
				hwWlanServiceStaMac }
			STATUS current
			DESCRIPTION 
				"Description."
			::= { hwWsecNotify 5 }

		
--  1.3.6.1.4.1.2011.6.139.6.9.1.6
		-- 1.3.6.1.4.1.2011.6.139.6.9.1.6
		hwLowSafeLevelAttackNotify NOTIFICATION-TYPE
			OBJECTS { hwApIndex, hwRadioID, hwApMac, hwStaAssocBssid, hwWlanServiceEssSsid, 
				hwWlanServiceStaMac }
			STATUS current
			DESCRIPTION 
				"Description."
			::= { hwWsecNotify 6 }

		
--  1.3.6.1.4.1.2011.6.139.6.9.1.7
		-- 1.3.6.1.4.1.2011.6.139.6.9.1.7
		hwAddressRedirectionAttackNotify NOTIFICATION-TYPE
			OBJECTS { hwApIndex, hwRadioID, hwApMac, hwStaAssocBssid, hwWlanServiceEssSsid, 
				hwWlanServiceStaMac }
			STATUS current
			DESCRIPTION 
				"Description."
			::= { hwWsecNotify 7 }

		
		-- 1.3.6.1.4.1.2011.6.139.6.9.1.8
		hwWepIDConflictNotify NOTIFICATION-TYPE
			OBJECTS { hwWepIDConflictTrapAPMAC, hwWepIDConflictTrapAPID, hwWepIDConflictTrapRadioId, hwWepIDConflictTrapPreSSID, hwWepIDConflictTrapCurrSSID, 
				hwWepIDConflictTrapCipherIdx }
			STATUS current
			DESCRIPTION 
				"Description."
			::= { hwWsecNotify 8 }

		
		-- 1.3.6.1.4.1.2011.6.139.6.9.1.9
		hwStaAuthEncryptModeNotMatchNotify NOTIFICATION-TYPE
			OBJECTS { hwApIndex, hwApMac, hwRadioID, hwStaAssocBssid, hwWlanServiceEssSsid, 
				hwWlanServiceStaMac, hwWlanStaAuthEncryptMode, hwWlanVapAuthEncryptMode }
			STATUS current
			DESCRIPTION 
				"Description."
			::= { hwWsecNotify 9 }
--  1.3.6.1.4.1.2011.6.139.6.9.2
		-- 1.3.6.1.4.1.2011.6.139.6.9.2
		hwWsecNotifyObjects OBJECT IDENTIFIER ::= { hwWsecNotifications 2 }

		
--  1.3.6.1.4.1.2011.6.139.6.9.2.1
		-- 1.3.6.1.4.1.2011.6.139.6.9.2.1
		hwStaAuthenticationMode OBJECT-TYPE
			SYNTAX Integer32
			MAX-ACCESS read-only
			STATUS current
			DESCRIPTION
				"Description."
			::= { hwWsecNotifyObjects 1 }

		
--  1.3.6.1.4.1.2011.6.139.6.9.2.2
		-- 1.3.6.1.4.1.2011.6.139.6.9.2.2
		hwStaAuthenticationFailCause OBJECT-TYPE
			SYNTAX Integer32
			MAX-ACCESS read-only
			STATUS current
			DESCRIPTION
				"Description."
			::= { hwWsecNotifyObjects 2 }

		
--  1.3.6.1.4.1.2011.6.139.6.9.2.3
		-- 1.3.6.1.4.1.2011.6.139.6.9.2.3
		hwStaAssociationFailCause OBJECT-TYPE
			SYNTAX Integer32
			MAX-ACCESS read-only
			STATUS current
			DESCRIPTION
				"Description."
			::= { hwWsecNotifyObjects 3 }

		
--  1.3.6.1.4.1.2011.6.139.6.9.2.4
		-- 1.3.6.1.4.1.2011.6.139.6.9.2.4
		hwStaAssocBssid OBJECT-TYPE
			SYNTAX MacAddress
			MAX-ACCESS read-only
			STATUS current
			DESCRIPTION
				"Description."
			::= { hwWsecNotifyObjects 4 }

		
		-- 1.3.6.1.4.1.2011.6.139.6.9.2.5
		hwStaFailCodeType OBJECT-TYPE
			SYNTAX INTEGER
				{
				reasonCode(1),
				statusCode(2)
				}
			MAX-ACCESS read-only
			STATUS current
			DESCRIPTION
				"Description."
			::= { hwWsecNotifyObjects 5 }

		
		-- 1.3.6.1.4.1.2011.6.139.6.9.2.6
		hwWepIDConflictTrapAPMAC OBJECT-TYPE
			SYNTAX MacAddress
			MAX-ACCESS read-only
			STATUS current
			DESCRIPTION
				"Description."
			::= { hwWsecNotifyObjects 6 }

		
		-- 1.3.6.1.4.1.2011.6.139.6.9.2.7
		hwWepIDConflictTrapAPID OBJECT-TYPE
			SYNTAX Integer32
			MAX-ACCESS read-only
			STATUS current
			DESCRIPTION
				"Description."
			::= { hwWsecNotifyObjects 7 }

		
		-- 1.3.6.1.4.1.2011.6.139.6.9.2.8
		hwWepIDConflictTrapRadioId OBJECT-TYPE
			SYNTAX Integer32
			MAX-ACCESS read-only
			STATUS current
			DESCRIPTION
				"Description."
			::= { hwWsecNotifyObjects 8 }

		
		-- 1.3.6.1.4.1.2011.6.139.6.9.2.9
		hwWepIDConflictTrapPreSSID OBJECT-TYPE
			SYNTAX OCTET STRING (SIZE (0..32))
			MAX-ACCESS read-only
			STATUS current
			DESCRIPTION
				"Description."
			::= { hwWsecNotifyObjects 9 }

		
		-- 1.3.6.1.4.1.2011.6.139.6.9.2.10
		hwWepIDConflictTrapCurrSSID OBJECT-TYPE
			SYNTAX OCTET STRING (SIZE (0..32))
			MAX-ACCESS read-only
			STATUS current
			DESCRIPTION
				"Description."
			::= { hwWsecNotifyObjects 10 }

		
		-- 1.3.6.1.4.1.2011.6.139.6.9.2.11
		hwWepIDConflictTrapCipherIdx OBJECT-TYPE
			SYNTAX Integer32
			MAX-ACCESS read-only
			STATUS current
			DESCRIPTION
				"Description."
			::= { hwWsecNotifyObjects 11 }

		
		-- 1.3.6.1.4.1.2011.6.139.6.9.2.12
		hwWlanStaAuthEncryptMode OBJECT-TYPE
			SYNTAX Integer32
			MAX-ACCESS read-only
			STATUS current
			DESCRIPTION
				"Description."
			::= { hwWsecNotifyObjects 12 }

		
		-- 1.3.6.1.4.1.2011.6.139.6.9.2.13
		hwWlanVapAuthEncryptMode OBJECT-TYPE
			SYNTAX Integer32
			MAX-ACCESS read-only
			STATUS current
			DESCRIPTION
				"Description."
			::= { hwWsecNotifyObjects 13 }
		-- 1.3.6.1.4.1.2011.6.139.6.9.2.14
		hwStaAuthenticationFailCauseStr OBJECT-TYPE
			SYNTAX OCTET STRING
			MAX-ACCESS read-only
			STATUS current
			DESCRIPTION
				"Description."
			::= { hwWsecNotifyObjects 14 }

		
		-- 1.3.6.1.4.1.2011.6.139.6.9.2.15
		hwStaAssociationFailCauseStr OBJECT-TYPE
			SYNTAX OCTET STRING
			MAX-ACCESS read-only
			STATUS current
			DESCRIPTION
				"Description."
			::= { hwWsecNotifyObjects 15 }
		
		hwWlanSecurityObject OBJECT IDENTIFIER ::= { hwWlanSecurity 10 }
		
		hwWlanSecurityConformance OBJECT IDENTIFIER ::= { hwWlanSecurity 11 }
		
		hwWlanSecurityCompliances OBJECT IDENTIFIER ::= { hwWlanSecurityConformance 1 }
		
		hwWlanSecurityCompliance MODULE-COMPLIANCE
			STATUS current
			DESCRIPTION 
				"Description."
			MODULE -- this module
				MANDATORY-GROUPS { hwWsecProfileGroup, hwWsecWEPDefaultKeysGroup, hwWsecWEPKeyMappingsGroup, hwWsecAuthSuitesGroup, hwWsecStatsGroup, 
					hwWsecBatchProfileInfoGroup, hwWsecNotifyGroup, hwWsecNotifyObjectsGroup }
			::= { hwWlanSecurityCompliances 1 }
		
		hwWlanSecurityObjectGroups OBJECT IDENTIFIER ::= { hwWlanSecurityConformance 2 }
		
		hwWsecProfileGroup OBJECT-GROUP
			OBJECTS { hwWsecProfileName, hwWsecProfileWEPDataEncrypt, hwWsecProfileWEPDefaultKeyID, hwWsecProfileWEPKeyMappingLength, hwWsecProfileAsuIpAddr, hwWsecProfileCaCertFileName, 
				hwWsecProfileAsuCertFileName, hwWsecProfileAcCertFileName, hwWsecProfileAcPrvKeyFileName, hwWsecProfileRsnaVersion, hwWsecProfileWapiVersion, 
				hwWsecProfileRowStatus, hwWsecProfileCaPfxPassword, hwWsecProfileCaCertState, hwWsecProfileAsuPfxPassword, hwWsecProfileAsuCertState, 
				hwWsecProfileAcPfxPassword, hwWsecProfileAcCertState, hwWsecProfileKeyPfxPassword, hwWsecProfileAsuType, hwWsecProfileWpaPtkRekeySwitch,
				hwWsecProfileWpa2PtkRekeySwitch,hwWsecProfileWpaWpa2PtkRekeySwitch,hwWsecProfileWpaPtkRekeyInterval,hwWsecProfileWpa2PtkRekeyInterval, hwWsecProfileWpaWpa2PtkRekeyInterval }
			STATUS current
			DESCRIPTION
				"Description."
			::= { hwWlanSecurityObjectGroups 1 }
		
		hwWsecWEPDefaultKeysGroup OBJECT-GROUP
			OBJECTS { hwWsecWEPDefaultKeyValue, hwWsecWEPPassPhrase }
			STATUS current
			DESCRIPTION
				"Description."
			::= { hwWlanSecurityObjectGroups 2 }
		
		hwWsecWEPKeyMappingsGroup OBJECT-GROUP
			OBJECTS { hwWsecWEPKeyMappingAddress, hwWsecWEPKeyMappingWEPOn, hwWsecWEPKeyMappingValue, hwWsecWEPKeyMappingStatus }
			STATUS current
			DESCRIPTION
				"Description."
			::= { hwWlanSecurityObjectGroups 3 }
		
		hwWsecAuthSuitesGroup OBJECT-GROUP
			OBJECTS { hwWsecAuthSuite, hwWsecAuthSuiteEnabled, hwWsecAuthPreauthenticationImplemented, hwWsecAuthPreauthenticationEnabled, hwWsecAuthUnicastKeysSupported, 
				hwWsecAuthPairwiseCipher, hwWsecAuthPairwiseCipherSize, hwWsecAuthUnicastRekeyMethod, hwWsecAuthUnicastRekeyTime, hwWsecAuthUnicastRekeyPackets, 
				hwWsecAuthMulticastCipher, hwWsecAuthMulticastCipherSize, hwWsecAuthMulticastRekeyMethod, hwWsecAuthMulticastRekeyTime, hwWsecAuthMulticastRekeyPackets, 
				hwWsecAuthMulticastRekeyStrict, hwWsecAuthPSKValue, hwWsecAuthPSKPassPhrase, hwWsecAuthCertificateUpdateCount, hwWsecAuthMulticastUpdateCount, 
				hwWsecAuthUnicastUpdateCount, hwWsecAuthBKLifetime, hwWsecAuthBKReauthThreshold, hwWsecAuthSATimeout, hwWsecAuthExcludeUnencrypted, 
				hwWsecAuthDot1XMethod, hwWsecAuthControlledAuthControl, hwWsecAuthControlledPortControl, hwWsecAuthOptionalImplemented }
			STATUS current
			DESCRIPTION
				"Description."
			::= { hwWlanSecurityObjectGroups 4 }
		
		hwWsecStatsGroup OBJECT-GROUP
			OBJECTS { hwWsecStatsSTAAddress, hwWsecStatsVersion, hwWsecStatsBKIDUsed, hwWsecStatsAuthenticationSuiteSelected, hwWsecStatsUnicastCipherSelected, hwWsecStatsMulticastCipherSelected, 
				hwWsecStatsAuthenticationSuiteRequested, hwWsecStatsUnicastCipherRequested, hwWsecStatsMulticastCipherRequested, hwWsecStatsWEPICVErrorCount, hwWsecStatsWEPExcludedCount, 
				hwWsecStatsWEPUndecryptableCount, hwWsecStatsTKIPICVErrors, hwWsecStatsTKIPLocalMICFailures, hwWsecStatsTKIPRemoteMICFailures, hwWsecStatsTKIPReplays, 
				hwWsecStatsCCMPReplays, hwWsecStatsCCMPDecryptErrors, hwWsecStatsWAISignatureErrors, hwWsecStatsWAIHMACErrors, hwWsecStatsWAIAuthenticationResultFailures, 
				hwWsecStatsWAIDiscardCounters, hwWsecStatsWAITimeoutCounters, hwWsecStatsWAIFormatErrors, hwWsecStatsWAICertificateHandshakeFailures, hwWsecStatsWAIUnicastHandshakeFailures, 
				hwWsecStatsWAIMulticastHandshakeFailures, hwWsecStatsWPIReplayCounter, hwWsecStatsWPIDecryptableErrors, hwWsecStatsWPIMICErrors, hwWsecStatsControlledPortStatus, 
				hwWsecStatsNumberOfPTKSAReplayCounters, hwWsecStatsNumberOfGTKSAReplayCounters, hwWsecStatsTKIPCounterMeasuresInvoked, hwWsecStatsWpa4WayHandshakeFailures }
			STATUS current
			DESCRIPTION
				"Description."
			::= { hwWlanSecurityObjectGroups 5 }
		
		hwWsecBatchProfileInfoGroup OBJECT-GROUP
			OBJECTS { hwWsecBatchProfileStartNumber, hwWsecBatchProfileWantNumber, hwWsecBatchProfileReturnNumber, hwWsecBatchProfileName }
			STATUS current
			DESCRIPTION
				"Description."
			::= { hwWlanSecurityObjectGroups 6 }
		
		hwWsecNotifyGroup NOTIFICATION-GROUP
			NOTIFICATIONS { hwStaAuthErrorNotify, hwStaAssociationFailNotify, hwUserWithInvalidCerficationInbreakNetworkNotify, hwStationRepititiveAttackNotify, hwTamperAttackNotify, 
				hwLowSafeLevelAttackNotify, hwAddressRedirectionAttackNotify, hwWepIDConflictNotify, hwStaAuthEncryptModeNotMatchNotify }
			STATUS current
			DESCRIPTION
				"Description."
			::= { hwWlanSecurityObjectGroups 7 }
		
		hwWsecNotifyObjectsGroup OBJECT-GROUP
			OBJECTS { hwStaAuthenticationMode, hwStaAuthenticationFailCause, hwStaAssociationFailCause, hwStaAssocBssid, hwStaFailCodeType, 
				hwWepIDConflictTrapAPMAC, hwWepIDConflictTrapAPID, hwWepIDConflictTrapRadioId, hwWepIDConflictTrapPreSSID, hwWepIDConflictTrapCurrSSID, 
				hwWepIDConflictTrapCipherIdx, hwWlanStaAuthEncryptMode, hwWlanVapAuthEncryptMode, hwStaAuthenticationFailCauseStr, hwStaAssociationFailCauseStr
				 }
			STATUS current
			DESCRIPTION
				"Description."
			::= { hwWlanSecurityObjectGroups 8 }
		
	
	END

--
-- HUAWEI-WLAN-SECURITY-MIB.mib
--
