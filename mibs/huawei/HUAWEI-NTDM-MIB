-- =====================================================================================
-- Copyright (C) 2015 by  HUAWEI TECHNOLOGIES. All rights reserved.               
-- Description:  The mib is used for defining huawei's native TDM management MIB objects.
-- Reference: 
-- Version: V1.24
-- =====================================================================================

  HUAWEI-NTDM-MIB DEFINITIONS ::= BEGIN       
     IMPORTS 
      huaweiMgmt    
        FROM HUAWEI-MIB 
      hwFrameIndex, hwSlotIndex,hwConfigChangeIP
        FROM HUAWEI-DEVICE-MIB        
      IpAddress, Unsigned32, Counter64,Counter32, OBJECT-TYPE, MODULE-IDENTITY, 
      NOTIFICATION-TYPE, Integer32      
        FROM SNMPv2-SMI     
      DisplayString, RowStatus, TruthValue, MacAddress, DateAndTime     
        FROM SNMPv2-TC
      InterfaceIndex, ifIndex
        FROM IF-MIB; 

     hwNTDM MODULE-IDENTITY
      LAST-UPDATED "201501310000Z"
      ORGANIZATION "Huawei Technologies Co.,Ltd."
      CONTACT-INFO                                    
        "Huawei Industrial Base            
         Bantian, Longgang                 
         Shenzhen 518129                   
         People's Republic of China        
         Website: http://www.huawei.com    
         Email: support@huawei.com         
        "                                  
      DESCRIPTION  "The mib is used for defining huawei's native TDM management MIB objects."      
      
--  Revision history
      REVISION     "201501310000Z"
      DESCRIPTION  "V1.24, modified the scope of hwNativeTDMSrcPara1 and hwNativeTDMSrcPara2."
		    
      REVISION     "201406290000Z" 
      DESCRIPTION  "V1.23, Modify the following not normative nodes to satisfy for the new OMSYS tool.
                    hwNativeTDMFrameIndex
                    hwNativeTDMSlotIndex
                    hwNativeTDMConnectID."
		    
      REVISION     "201308230900Z"        
      DESCRIPTION  "V1.22,Added leaf node hwTDMJitterBuffer in table hwNativeTDMBoardTable for setting jitterbuffer"   
                     
      REVISION     "201304250900Z"     
      DESCRIPTION  "V1.21, modified the name of hwNativeTDMFlowConnectID."

      REVISION     "201212260900Z"     
      DESCRIPTION  "V1.20, add the leaf hwNativeTDMOnuTDMVCL in hwNativeTDMFlowTable table.
                    Add the leaf hwNativeTDMConnectOnuDropPackets,hwNativeTDMConnectOnuRecvPackets,
                    hwNativeTDMConnectOnuSendPackets,hwNativeTDMConnectOnuRecvErrCesopPackets,
                    hwNativeTDMConnectOnuRecvSnErrCesopPackets,hwNativeTDMConnectOnuRecvSsrcErrCesopPackets
                    in hwNativeTDMConnectStatTable table.
                    Modified the scope of hwNativeTDMServicePortIndex,hwNativeTDMFlowConnectID,hwNativeTDMConnectID."
                    
      REVISION     "201205210900Z"     
      DESCRIPTION  "V1.19, add the leaf hwNativeTDMServicePortIndex in hwNativeTDMFlowTable table.
                    Modified the scope of hwNativeTDMBoardAttrSlotIndex, hwNativeTDMClockSourceIndex, hwNativeTDMSrcPara, and hwNativeTDMFlowID."
                    
      REVISION     "201201050900Z"     
      DESCRIPTION  "V1.18, modified the scope of hwNativeTDMSrcPara1 and hwNativeTDMSrcPara2. 
                    Modified the name of hwNativeTDMConnectId to hwNativeTDMPwId and modified the description of hwNativeTDMPwId."
      
      REVISION     "201112080000Z"     
      DESCRIPTION  "V1.17, modified the max-access of hwNativeTDMClockSourceState to read-only."

      REVISION     "201111110000Z"     
      DESCRIPTION  "V1.16, modified the syntax of leaves:
                    Added node hwNativeTDMClockSourceState in hwNativeTDMBoardClockSourceTable.
                    Modified the name of hwNativeTDMPwId to hwNativeTDMConnectId."

      REVISION     "201011090900Z"     
      DESCRIPTION  "V1.15, modified the description of MIB. "
      
      REVISION     "201009170900Z"        
      DESCRIPTION  "V1.14, modified the syntax of leaves
                    Added leaf node hwTDMCfgAccessMode in table hwNativeTDMBoardTable for setting 
                    access mode of the TDM interfaces board.
                    "    
      REVISION     "201009100900Z"        
      DESCRIPTION  "V1.13, add the following leaves in hwNativeTDMConnectStatTable table:
                    hwNativeTDMConnectUpstreamRecvEthPackets,
                    hwNativeTDMConnectDownstreamSendEthPackets,
                    hwNativeTDMConnectUpstreamRecvVC12Packets,
                    hwNativeTDMConnectDownstreamSendVC12Packets,
                    hwNativeTDMConnectFifoFullPackets,
                    hwNativeTDMConnectFifoEmptyPackets.  
                    modify the following leaves type to Counter32: 
                    hwNativeTDMConnectRecvTdmPackets,
                    hwNativeTDMConnectSendTdmPackets,
                    hwNativeTDMConnectRecvCesopPackets,
                    hwNativeTDMConnectSendCesopPackets,
                    hwNativeTDMConnectRecvUpVc12Frames,
                    hwNativeTDMConnectSendDownVc12Frames,
                    hwNativeTDMConnectDropUpstreamBufferOverflow,
                    hwNativeTDMConnectDropUpstreamBufferUnderflow,
                    hwNativeTDMConnectDropDownstreamBufferOverflow,
                    hwNativeTDMConnectDropDownstreamBufferUnderflow,
                    hwNativeTDMConnectDropDownstreamSnError.        
                    "
                    
      REVISION     "201009030900Z"        
      DESCRIPTION  "V1.12, modified the syntax of leaves
                    modified the syntax of hwNativeTDMSrcIfIndex from InterfaceIndex to Integer32.
                    modified the syntax of hwNativeTDMDstIfIndex from InterfaceIndex to Integer32.
                    "
                    
      REVISION     "201007020900Z"        
      DESCRIPTION  "V1.11, modified the description of mib
                    Added enum dsx1Impedance100(3) in hwNativeTDMIfImpedance leaf node 
                    "
                        
      REVISION     "201004220900Z"        
      DESCRIPTION  "V1.10, changes in this revision:
                    Added enum in leaf hwNativeTDMIfLoopbackConfig.
                    Added enum in leaf hwNativeTDMIfLineStatus.
                    Added enum in leaf hwNativeTDMIfLineCoding.
                    Added enum in leaf hwNativeTDMIfImpedance. 
                    "

      REVISION     "201004010900Z"        
      DESCRIPTION  "V1.09, changes in this revision:
                    Modified the syntax error.
                    "
                    
      REVISION     "201001120900Z"        
      DESCRIPTION  "V1.08, changes in this revision:
                    Added the definition of the trap node.
                    "

      REVISION     "200904070900Z"        
      DESCRIPTION  "V1.07, changes in this revision:
                    Added table hwNativeTDMBoardAttrTable for setting the attribute of the TDM board.
                    Added table hwNativeTDMConnectStatTable for obtaining the traffic statistics for converting TDM service stream to CESoP service stream.
                    Added table hwNativeTDMFlowClockModeTable for the native TDM flow clock mode.
                    Added table hwNativeTDMBoardClockSourceTable for clock source configured in native TDM board. 
                    Modified the range of the leaf node hwNativeTDMFlowID from <0, 255> to <0, 1023>.
                   "   
      
      REVISION     "200807230900Z"        
      DESCRIPTION  "V1.05, changes in this revision:
                    Added IMPORT type ifIndex.
                    Added leaf nodes hwNativeTDMSrcPara1 and hwNativeTDMSrcPara2 in table hwNativeTDMFlowTable
                    for setting the native TDM flow in XPON profile mode. 
                    Added leaf node hwNativeTDMIfLoopback in table hwNativeTDMBoardTable for setting 
                    loopback of the TDM interfaces on a board.  
                   " 
      
      REVISION     "200704100900Z"        
      DESCRIPTION  "V1.02, changes in this revision: 
                    Modified the enum value of leaf node hwNativeTDMIfLineCoding from dsx1HDB3(1) and dsx1AMI(2)
                    to dsx1AMI(1) and dsx1HDB3(2).
                    Added the index ifIndex for table hwNativeTDMIfTable.
                   "
      
      REVISION     "200612070900Z"        
      DESCRIPTION  "V1.00, initial version."  
     ::= { huaweiMgmt 105 }

    hwNTDMMibObjects OBJECT IDENTIFIER ::= { hwNTDM 1 }
   
               
    hwNativeTDMIfTable OBJECT-TYPE
     SYNTAX SEQUENCE OF HwNativeTDMIfEntry
     MAX-ACCESS not-accessible
     STATUS current
     DESCRIPTION
       "Configuration table of Native TDM interface, such as the TDM interface loopback type,
        line status and alarm status.
        The index of this table is ifIndex.
        "
     ::= { hwNTDMMibObjects 1 }

    hwNativeTDMIfEntry OBJECT-TYPE
     SYNTAX HwNativeTDMIfEntry
     MAX-ACCESS not-accessible
     STATUS current
     DESCRIPTION
       "Configuration table of Native TDM interface, such as the TDM interface loopback type,
        line status and alarm status.
        The index of this entry is ifIndex.
        "  
     INDEX { ifIndex }
     ::= { hwNativeTDMIfTable 1 }

    HwNativeTDMIfEntry ::=
     SEQUENCE 
       {   
         hwNativeTDMIfLoopbackConfig       INTEGER,
         hwNativeTDMIfLineStatus           INTEGER,
         hwNativeTDMIfLineAlarm            BITS
       }   
         
    hwNativeTDMIfLoopbackConfig OBJECT-TYPE
     SYNTAX INTEGER
       {
         dsx1NoLoop(1),
         dsx1RemoteLoop(2),
         dsx1DigitalLoop(3),
         dsx1AnalogLoop(4),
         invalid(-1)
       }     
     MAX-ACCESS read-write
     STATUS current
     DESCRIPTION
       "Loopback type of the TDM interface.
        Options:
        1. dsx1NoLoop(1)       -NoLoop
        2. dsx1RemoteLoop(2)   -RemoteLoop
        3. dsx1DigitalLoop(3)  -DigitalLoop
        4. dsx1AnalogLoop(4)   -AnalogLoop
        5. invalid(-1)         -invalid value
        Default: dsx1NoLoop(1)
        "    
     DEFVAL { dsx1NoLoop }
     ::= { hwNativeTDMIfEntry 1 }  
     
   hwNativeTDMIfLineStatus OBJECT-TYPE
      SYNTAX INTEGER
        {    
          dsx1Normal(1),
          dsx1Fault(2),
          invalid(-1)
        }     
      MAX-ACCESS read-only
      STATUS current
      DESCRIPTION
        "Line status of the TDM interface.
         Options:
         1. dsx1Normal(1)  -Line is normal
         2. dsx1Fault(2)   -Line is fault
         3. invalid(-1)    -invalid value
         "
      ::= { hwNativeTDMIfEntry 2 }

   hwNativeTDMIfLineAlarm OBJECT-TYPE
     SYNTAX BITS
       {
         dsx1NoAlarm(0),
         dsx1LOS(1),
         dsx1AIS(2)
       }     
     MAX-ACCESS read-only
     STATUS current
     DESCRIPTION
       "Alarm status of the TDM interface.
        Options:
        1. dsx1NoAlarm(0)  -NoAlarm
        2. dsx1LOS(1)      -signal is lost
        3. dsx1AIS(2)      -alarm indicate signal value
        "  
     ::= { hwNativeTDMIfEntry 3 }

               
   hwNativeTDMBoardTable OBJECT-TYPE
     SYNTAX SEQUENCE OF HwNativeTDMBoardEntry
     MAX-ACCESS not-accessible
     STATUS current
     DESCRIPTION
       "This table is used for setting configuration of Native TDM board, such as line coding format,
        impedance and remote inner loopback.
        The indexes of this table are hwNativeTDMFrameIndex and hwNativeTDMSlotIndex.
        "
     ::= { hwNTDMMibObjects 2 }

   hwNativeTDMBoardEntry OBJECT-TYPE
     SYNTAX HwNativeTDMBoardEntry
     MAX-ACCESS not-accessible
     STATUS current
     DESCRIPTION
       "This table is used for setting configuration of Native TDM board, such as line coding format,
        impedance and remote inner loopback.
        The indexes of this entry are hwNativeTDMFrameIndex and hwNativeTDMSlotIndex.
        "
     INDEX { hwNativeTDMFrameIndex, hwNativeTDMSlotIndex  }
     ::= { hwNativeTDMBoardTable 1 }

   HwNativeTDMBoardEntry ::=
     SEQUENCE 
     {
       hwNativeTDMFrameIndex       Integer32,
       hwNativeTDMSlotIndex        Integer32,
       hwNativeTDMIfLineCoding     INTEGER,
       hwNativeTDMIfImpedance      INTEGER,
       hwNativeTDMIfLoopback       INTEGER,
       hwTDMCfgAccessMode          INTEGER,     
       hwTDMJitterBuffer           INTEGER
}

   hwNativeTDMFrameIndex OBJECT-TYPE
     SYNTAX Integer32
     MAX-ACCESS accessible-for-notify
     STATUS current
     DESCRIPTION
       "Frame ID of the TDM board."
     ::= { hwNativeTDMBoardEntry 1 }

   hwNativeTDMSlotIndex OBJECT-TYPE
     SYNTAX Integer32(0..22)   
     MAX-ACCESS accessible-for-notify
     STATUS current
     DESCRIPTION
       "Slot ID of the TDM board."
     ::= { hwNativeTDMBoardEntry 2 }
     
   hwNativeTDMIfLineCoding OBJECT-TYPE
     SYNTAX INTEGER  
       {  
         dsx1AMI(1),
         dsx1HDB3(2),
         invalid(-1)
       } 
     MAX-ACCESS read-write
     STATUS current
     DESCRIPTION
       "Line coding format of the TDM interfaces in the board.
        Options:
        1. dsx1AMI(1)   -AMI
        2. dsx1HDB3(2)  -HDB3
        3. invalid(-1)  -invalid value
        Default: dsx1HDB3(2)
        "
     DEFVAL { dsx1HDB3 }
     ::= { hwNativeTDMBoardEntry 3 }

   hwNativeTDMIfImpedance OBJECT-TYPE
     SYNTAX INTEGER
       {  
         dsx1Impedance75(1),       
         dsx1Impedance120(2),
         dsx1Impedance100(3),
         invalid(-1)       
       }
     MAX-ACCESS read-write
     STATUS current
     DESCRIPTION
       "Impedance of the TDM interfaces in the board.
        Options:
        1. dsx1Impedance75(1)    -75
        2. dsx1Impedance120(2)   -120
        3. dsx1Impedance100(3)   -100
        4. invalid(-1)           -invalid value
        Default: dsx1Impedance75(1)
        "
     DEFVAL { dsx1Impedance75 }
     ::= { hwNativeTDMBoardEntry 4 }   
                                      
   hwNativeTDMIfLoopback OBJECT-TYPE
     SYNTAX INTEGER
       {  
         dsx1NoLoop(1),       
         dsx1RemoteInner(2)       
       }
     MAX-ACCESS read-write
     STATUS current
     DESCRIPTION
       "Loopback of the TDM interfaces in the board.
        Options:
        1. dsx1NoLoop(1)        -no loopback
        2. dsx1RemoteInner(2)   -remote inner loopback
        Default: dsx1NoLoop(1)
        "
     DEFVAL { dsx1NoLoop }
     ::= { hwNativeTDMBoardEntry 5 } 
 
    hwTDMCfgAccessMode OBJECT-TYPE
     SYNTAX INTEGER
       {         
         e1(1),       
         t1(2),
         invalid(-1)       
       }
     MAX-ACCESS read-write
     STATUS current
     DESCRIPTION
       "Access mode of the TDM interfaces board.
        Options:
        1. e1(1)        -e1 access mode
        2. t1(2)        -t1 access mode
        3. invalid(-1)  -invalid value
        " 
        DEFVAL { e1 }
     ::= { hwNativeTDMBoardEntry 6 }
      
    hwTDMJitterBuffer OBJECT-TYPE
     SYNTAX INTEGER
       {  
         jitterbuffer375(1),         
         jitterbuffer500(2),         
         jitterbuffer625(3),         
         jitterbuffer750(4),         
         jitterbuffer875(5),         
         jitterbuffer1000(6),        
         jitterbuffer1125(7),        
         jitterbuffer1250(8),        
         jitterbuffer1375(9),        
         jitterbuffer1500(10),       
         jitterbuffer1625(11),       
         jitterbuffer1750(12),       
         jitterbuffer1875(13), 
         jitterbuffer2000(14),           
         jitterbuffer4000(15),  
         jitterbuffer8000(16),
         invalid(-1)    
        }
     MAX-ACCESS read-write
     STATUS current
     DESCRIPTION
       "Set jitterbuffer of the TDM interfaces board.This operation will reboot the board. 
        Setting jitterbuffer has great impact on the service,Increasing the value of jitterbuffer can reduce the probability of 
        underflow,but will increase the delay and the probability of overflow;decreasing the value of jitterbuffer can reduce delay, 
        lower probability of overflow, but will increase the probability of underflow.Therefore, we should  set jitterbuffer carefully 
        according to the specific situation of the network jitter.For O2CE subboard, jitterbuffer defaults to 625us,for NH1A subboard, 
        jitterbuffer defaults to 1125us.The default jitterbuffer of the subboard is recommended values based on actual experience, 
        under normal circumstances without adjustment.According to the network jitter, if the default jitterbuffer does not 
        meet the requirements, jitterbuffer should also be set near the default value.
        Options:
        1.  jitterbuffer375(1),        -375     
        2.  jitterbuffer500(2),        -500     
        3.  jitterbuffer625(3),        -625     
        4.  jitterbuffer750(4),        -750    
        5.  jitterbuffer875(5),        -875    
        6.  jitterbuffer1000(6),       -1000   
        7.  jitterbuffer1125(7),       -1125   
        8.  jitterbuffer1250(8),       -1250   
        9.  jitterbuffer1375(9),       -1375  
        10. jitterbuffer1500(10),      -1500    
        11. jitterbuffer1625(11),      -1625    
        12. jitterbuffer1750(12),      -1750   
        13. jitterbuffer1875(13),      -1875   
        14. jitterbuffer2000(14),      -2000    
        15. jitterbuffer4000(15),      -4000         
        16. jitterbuffer8000(16),      -8000   
        17. invalid(-1)                -invalid value
        MA5600T TOPA BOARD:
        EH1A SUBBOARD support the enum value 375 500 625 750 875 1000 1125 1250 1375 1500 1625 1750 1875.
        NH1A/O2CE SUBBOARD support the enum value 500 1000 2000 4000 8000. " 
     ::= { hwNativeTDMBoardEntry 7 } 
        
   hwNativeTDMFlowTable OBJECT-TYPE
     SYNTAX SEQUENCE OF HwNativeTDMFlowEntry
     MAX-ACCESS not-accessible
     STATUS current
     DESCRIPTION
       "This table is used for setting configuration of the Native TDM flow, such as
        source interface index, source parameter.
        The index of this table is hwNativeTDMFlowID.
        "
     ::= { hwNTDMMibObjects 3 }

   hwNativeTDMFlowEntry OBJECT-TYPE
     SYNTAX HwNativeTDMFlowEntry
     MAX-ACCESS not-accessible
     STATUS current
     DESCRIPTION
       "This table is used for setting configuration of the Native TDM flow, such as
        source interface index, source parameter.
        The index of this entry is hwNativeTDMFlowID.
        "
     INDEX { hwNativeTDMFlowID }
     ::= { hwNativeTDMFlowTable 1 }

   HwNativeTDMFlowEntry ::=
     SEQUENCE 
     {   
       hwNativeTDMFlowID               Integer32, 
       hwNativeTDMSrcIfIndex           Integer32,
       hwNativeTDMSrcPara              Integer32,
       hwNativeTDMDstIfIndex           Integer32,
       hwNativeTDMDstPara              Integer32,
       hwNativeTDMAdminStatus          Integer32,
       hwNativeTDMOperStatus           Integer32,
       hwNativeTDMRowStatus            RowStatus,      
       hwNativeTDMSrcPara1             Integer32,
       hwNativeTDMSrcPara2             Integer32,
       hwNativeTDMServicePortIndex     Integer32,
       hwNativeTDMOnuTDMVCL            Integer32  
     }   
      
   hwNativeTDMFlowID OBJECT-TYPE
     SYNTAX Integer32(-1 | 0..2047)
     MAX-ACCESS read-create
     STATUS current
     DESCRIPTION
       "Unique identifier of the Native TDM flow in the system."
     ::= { hwNativeTDMFlowEntry 1 }


   hwNativeTDMSrcIfIndex OBJECT-TYPE
     SYNTAX Integer32
     MAX-ACCESS read-create
     STATUS current
     DESCRIPTION
       "Source interface index, in current application the source interface index is the index 
        of the GPON interface.
        "
     ::= { hwNativeTDMFlowEntry 2 }

   hwNativeTDMSrcPara OBJECT-TYPE
     SYNTAX Integer32(-1 | 128..3999)    
     MAX-ACCESS read-create
     STATUS current
     DESCRIPTION
       "Source parameter, in current application the source parameter is the corresponding 
        GEM Port-ID of the Native TDM service.
        "
     ::= { hwNativeTDMFlowEntry 3 }

   hwNativeTDMDstIfIndex OBJECT-TYPE
     SYNTAX Integer32
     MAX-ACCESS read-create
     STATUS current
     DESCRIPTION
       "Destination interface index, in current application the destination interface index 
        is the index of the E1 port. 
        In the case of the connection of pwe3-uplink, ifIndex are generated by frame/slot/0xff.
        "
     ::= { hwNativeTDMFlowEntry 4 }
     
   hwNativeTDMDstPara OBJECT-TYPE
     SYNTAX Integer32
     MAX-ACCESS read-create
     STATUS current
     DESCRIPTION
       "Destination parameter, used for future expansibility."
     ::= { hwNativeTDMFlowEntry 5 }  

   hwNativeTDMAdminStatus OBJECT-TYPE
     SYNTAX Integer32
     MAX-ACCESS read-write
     STATUS current
     DESCRIPTION
       "Administration status, used for future expansibility."
     ::= { hwNativeTDMFlowEntry 6 }    
     
   hwNativeTDMOperStatus OBJECT-TYPE
     SYNTAX Integer32
     MAX-ACCESS read-only
     STATUS current
     DESCRIPTION
       "Operation status, used for future expansibility."
     ::= { hwNativeTDMFlowEntry 7 }
     
   hwNativeTDMRowStatus OBJECT-TYPE
     SYNTAX RowStatus
     MAX-ACCESS read-create
     STATUS current
     DESCRIPTION
       "The present operation status of the row.
        Options:
        1. createAndGo(4)   -The present operation status is createAndGo
        2. destroy(6)       -The present operation status is destroy 
        "
     ::= { hwNativeTDMFlowEntry 8 }
     
   hwNativeTDMSrcPara1 OBJECT-TYPE
     SYNTAX Integer32(-1 | 0..127)   
     MAX-ACCESS read-create
     STATUS current
     DESCRIPTION
       "Source parameter, in current application the source parameter is the corresponding 
        ONT-ID of the Native TDM service.
        "
     ::= { hwNativeTDMFlowEntry 9 }
     
   hwNativeTDMSrcPara2 OBJECT-TYPE
     SYNTAX Integer32(-1 | 0..1023)   
     MAX-ACCESS read-create
     STATUS current
     DESCRIPTION
       "Source parameter, in current application the source parameter is the corresponding 
        Gemport-Index of the Native TDM service.
        "
     ::= { hwNativeTDMFlowEntry 10 }
     
   hwNativeTDMServicePortIndex OBJECT-TYPE
     SYNTAX Integer32(-1 | 1..131072)   
     MAX-ACCESS read-create
     STATUS current
     DESCRIPTION
       "A unique identifier of the service virtual port.
       The invalid value is -1. "
     ::= { hwNativeTDMFlowEntry 11 }
     
   hwNativeTDMOnuTDMVCL OBJECT-TYPE
     SYNTAX Integer32(-1 | 0..31)   
     MAX-ACCESS read-create
     STATUS current
     DESCRIPTION
       "Onu TDM VCL ID. 
       The invalid value is -1. "
     ::= { hwNativeTDMFlowEntry 12 }                             
                    
   hwNativeTDMBoardClockSourceTable OBJECT-TYPE
     SYNTAX SEQUENCE OF HwNativeTDMBoardClockSourceEntry
     MAX-ACCESS not-accessible
     STATUS current
     DESCRIPTION
       "Configuration table of clock source configured in Native TDM board.
        The indexes of this table are hwNativeTDMFrameId, hwNativeTDMSlotId and hwNativeTDMClockSourceId.
        "
     ::= { hwNTDMMibObjects 4 }

   hwNativeTDMBoardClockSourceEntry OBJECT-TYPE
     SYNTAX HwNativeTDMBoardClockSourceEntry
     MAX-ACCESS not-accessible
     STATUS current
     DESCRIPTION
       "Configuration table of clock source configured in Native TDM board.
        The indexes of this entry are hwNativeTDMFrameId, hwNativeTDMSlotId and hwNativeTDMClockSourceId.
        "
     INDEX { hwNativeTDMFrameId, hwNativeTDMSlotId, hwNativeTDMClockSourceId }
     ::= { hwNativeTDMBoardClockSourceTable 1 }

   HwNativeTDMBoardClockSourceEntry ::=
     SEQUENCE 
     {          
       hwNativeTDMFrameId             Integer32,
       hwNativeTDMSlotId              Integer32,
       hwNativeTDMClockSourceId       Integer32,
       hwNativeTDMPwId                Unsigned32,
       hwNativeTDMRowStat             RowStatus,
       hwNativeTDMClockSourceState    INTEGER
     }

   hwNativeTDMFrameId OBJECT-TYPE
     SYNTAX Integer32
     MAX-ACCESS not-accessible
     STATUS current
     DESCRIPTION
       "Frame ID of the TDM board."
     ::= { hwNativeTDMBoardClockSourceEntry 1 }

   hwNativeTDMSlotId OBJECT-TYPE
     SYNTAX Integer32(0..22)   
     MAX-ACCESS not-accessible
     STATUS current
     DESCRIPTION
       "Slot ID of the TDM board."
     ::= { hwNativeTDMBoardClockSourceEntry 2 }
     
   hwNativeTDMClockSourceId OBJECT-TYPE
     SYNTAX Integer32  
     MAX-ACCESS read-write
     STATUS current
     DESCRIPTION
       "Clock Source ID of the TDM board."
     ::= { hwNativeTDMBoardClockSourceEntry 3 }

   hwNativeTDMPwId OBJECT-TYPE
     SYNTAX Unsigned32(0..4294967294)
     MAX-ACCESS read-write
     STATUS current
     DESCRIPTION
       "PW or CESoP connectID of Clock Source on the TDM board."
     ::= { hwNativeTDMBoardClockSourceEntry 4 }    
         
   hwNativeTDMRowStat OBJECT-TYPE
     SYNTAX RowStatus    
     MAX-ACCESS read-create
     STATUS current
     DESCRIPTION
       "The present operation status of the row.
        Options:
        1. createAndGo(4) -The present operation status of the row is createAndgo
        2. destroy(6)     -The present operation status of the row is destroy
        "
     ::= { hwNativeTDMBoardClockSourceEntry 5 }   

   hwNativeTDMClockSourceState OBJECT-TYPE
     SYNTAX INTEGER    
     {
         normal(1),
         failed(2),
         invalid(-1)
     }
     MAX-ACCESS  read-only
     STATUS      current
     DESCRIPTION
       "Type of clock mode.
        Options:
        1. normal(1)    -the clock source state is normal 
        2. fail(2)      -the clock source state is failed
        3. invalid(-1)  -invalid value                             
        "
     ::= { hwNativeTDMBoardClockSourceEntry 6 }   
           
   hwNativeTDMFlowClockModeTable OBJECT-TYPE
     SYNTAX SEQUENCE OF HwNativeTDMFlowClockModeEntry
     MAX-ACCESS not-accessible
     STATUS current
     DESCRIPTION
       "Configuration table of the Native TDM flow clock mode.
        The index of this table is hwNativeTDMFlowConnectID.
        "
     ::= { hwNTDMMibObjects 5 }

   hwNativeTDMFlowClockModeEntry OBJECT-TYPE
     SYNTAX HwNativeTDMFlowClockModeEntry
     MAX-ACCESS not-accessible
     STATUS current
     DESCRIPTION
       "Configuration table of the Native TDM flow clock mode.
        The index of this entry is hwNativeTDMFlowConnectID.
        "
     INDEX {hwNativeTDMFlowConnectID }
     ::= { hwNativeTDMFlowClockModeTable 1 }

   HwNativeTDMFlowClockModeEntry ::=
     SEQUENCE 
     { 
       hwNativeTDMFlowConnectID            Integer32, 
       hwNativeTDMClockMode                INTEGER,
       hwNativeTDMClockSourceMode          INTEGER,
       hwNativeTDMClockSourceIndex         Integer32 
     }
        
     hwNativeTDMFlowConnectID OBJECT-TYPE
     SYNTAX Integer32(0..2047)
     MAX-ACCESS not-accessible
     STATUS current
     DESCRIPTION
       "Unique identifier of the Native TDM flow in the system.
       "
     ::= { hwNativeTDMFlowClockModeEntry 1 }
       
   hwNativeTDMClockMode  OBJECT-TYPE 
     SYNTAX       INTEGER
     {
     master(1),
     slave(2),
     invalid(-1)
     }
     MAX-ACCESS  read-write
     STATUS      current
     DESCRIPTION
       "Type of clock mode.
        Options:
        1. master(1)    -master mode 
        2. slave(2)     -slave mode
        3. invalid(-1)  -invalid value                             
        "
      ::= { hwNativeTDMFlowClockModeEntry 2}            
                    
   hwNativeTDMClockSourceMode  OBJECT-TYPE 
     SYNTAX       INTEGER
     {
     retiming(1),
     adapt(2) ,
     invalid(-1)
     }
     MAX-ACCESS  read-write
     STATUS      current
     DESCRIPTION
       "Type of clock source mode.
        Options:
        1. retiming(1)    -retiming mode
        2. adapt(2)       -adapt mode   
        3. invalid(-1)    -invalid value                            
        "
      ::= { hwNativeTDMFlowClockModeEntry 3}
      
   hwNativeTDMClockSourceIndex OBJECT-TYPE 
     SYNTAX Integer32(-1 | 0)
     MAX-ACCESS  read-write
     STATUS      current
     DESCRIPTION
          "Type of recovery clock source index:
           In current application the source index is 0.
           The invalid value is -1.                            
          "
      ::= { hwNativeTDMFlowClockModeEntry 4}      
            
   hwNativeTDMConnectStatTable OBJECT-TYPE
     SYNTAX SEQUENCE OF HwNativeTDMConnectStatEntry
     MAX-ACCESS not-accessible
     STATUS current
     DESCRIPTION
       "Native TDM connect statistics table, such as received upstream Native TDM packets.
        The index of this table is hwNativeTDMConnectID.
       "
     ::= { hwNTDMMibObjects 6 }

   hwNativeTDMConnectStatEntry OBJECT-TYPE
     SYNTAX HwNativeTDMConnectStatEntry
     MAX-ACCESS not-accessible
     STATUS current
     DESCRIPTION
       "Native TDM connect statistics table, such as received upstream Native TDM packets.
        The index of this entry is hwNativeTDMConnectID.
       "
     INDEX { hwNativeTDMConnectID }
     ::= { hwNativeTDMConnectStatTable 1 }

   HwNativeTDMConnectStatEntry ::=
     SEQUENCE {
       hwNativeTDMConnectID
                Integer32,
       hwNativeTDMConnectRecvTdmPackets
                Counter32,
       hwNativeTDMConnectSendTdmPackets
                Counter32,
       hwNativeTDMConnectRecvCesopPackets
                Counter32,
       hwNativeTDMConnectSendCesopPackets
                Counter32,
       hwNativeTDMConnectRecvUpVc12Frames
                Counter32,
       hwNativeTDMConnectSendDownVc12Frames
                Counter32,
       hwNativeTDMConnectDropUpstreamBufferOverflow
                Counter32,
       hwNativeTDMConnectDropUpstreamBufferUnderflow
                Counter32,
       hwNativeTDMConnectDropDownstreamBufferOverflow
                Counter32,
       hwNativeTDMConnectDropDownstreamBufferUnderflow
                Counter32,
       hwNativeTDMConnectDropDownstreamSnError
                Counter32,
       hwNativeTDMConnectStatClear
                INTEGER,
       hwNativeTDMConnectUpstreamRecvEthPackets
                Counter32,
       hwNativeTDMConnectDownstreamSendEthPackets
                Counter32,
       hwNativeTDMConnectUpstreamRecvVC12Packets
                Counter32,
       hwNativeTDMConnectDownstreamSendVC12Packets
                Counter32,
       hwNativeTDMConnectFifoFullPackets
                Counter32,
       hwNativeTDMConnectFifoEmptyPackets
                Counter32,
       hwNativeTDMConnectOnuDropPackets
                Counter64,
       hwNativeTDMConnectOnuRecvPackets
                Counter64,
       hwNativeTDMConnectOnuSendPackets
                Counter64,
       hwNativeTDMConnectOnuRecvErrCesopPackets
                Counter64,
       hwNativeTDMConnectOnuRecvSnErrCesopPackets
                Counter64,
       hwNativeTDMConnectOnuRecvSsrcErrCesopPackets
                Counter64 
      }

   hwNativeTDMConnectID OBJECT-TYPE
     SYNTAX Integer32(0..2047)
     MAX-ACCESS accessible-for-notify
     STATUS current
     DESCRIPTION
       "Native TDM connect ID.
       "
     ::= { hwNativeTDMConnectStatEntry 1 }
         
   hwNativeTDMConnectRecvTdmPackets OBJECT-TYPE
     SYNTAX Counter32
     MAX-ACCESS read-only
     STATUS current
     DESCRIPTION
       "Received upstream Native TDM packets.
       "
     ::= { hwNativeTDMConnectStatEntry 2 }
          
   hwNativeTDMConnectSendTdmPackets OBJECT-TYPE
     SYNTAX Counter32
     MAX-ACCESS read-only
     STATUS current
     DESCRIPTION
       "Transmitted downstream Native TDM packets.
       "
     ::= { hwNativeTDMConnectStatEntry 3 }
          
   hwNativeTDMConnectRecvCesopPackets OBJECT-TYPE
     SYNTAX Counter32
     MAX-ACCESS read-only
     STATUS current
     DESCRIPTION
       "Received downstream CESoP packets.
       "
     ::= { hwNativeTDMConnectStatEntry 4 }
         
   hwNativeTDMConnectSendCesopPackets OBJECT-TYPE
     SYNTAX Counter32
     MAX-ACCESS read-only
     STATUS current
     DESCRIPTION
       "Transmitted upstream CESoP packets.
       "
     ::= { hwNativeTDMConnectStatEntry 5 }
        
   hwNativeTDMConnectRecvUpVc12Frames OBJECT-TYPE
     SYNTAX Counter32
     MAX-ACCESS read-only
     STATUS current
     DESCRIPTION
       "Received upstream VC12 frames.
       "
     ::= { hwNativeTDMConnectStatEntry 6 }
        
   hwNativeTDMConnectSendDownVc12Frames OBJECT-TYPE
     SYNTAX Counter32
     MAX-ACCESS read-only
     STATUS current
     DESCRIPTION
       "Transmitted downstream VC12 frames.
       "
     ::= { hwNativeTDMConnectStatEntry 7 }
        
   hwNativeTDMConnectDropUpstreamBufferOverflow OBJECT-TYPE
     SYNTAX Counter32
     MAX-ACCESS read-only
     STATUS current
     DESCRIPTION
       "Discarded upstream Native TDM packets due to buffer overflow.
       "
     ::= { hwNativeTDMConnectStatEntry 8 }
      
   hwNativeTDMConnectDropUpstreamBufferUnderflow OBJECT-TYPE
     SYNTAX Counter32
     MAX-ACCESS read-only
     STATUS current
     DESCRIPTION
       "Discarded upstream Native TDM packets due to buffer underflow.
       "
     ::= { hwNativeTDMConnectStatEntry 9 }
          
   hwNativeTDMConnectDropDownstreamBufferOverflow OBJECT-TYPE
     SYNTAX Counter32
     MAX-ACCESS read-only
     STATUS current
     DESCRIPTION
       "Discarded downstream CESoP packets due to buffer overflow.
       "
     ::= { hwNativeTDMConnectStatEntry 10 }
          
   hwNativeTDMConnectDropDownstreamBufferUnderflow OBJECT-TYPE
     SYNTAX Counter32
     MAX-ACCESS read-only
     STATUS current
     DESCRIPTION
       "Discarded downstream CESoP packets due to buffer underflow.
       "
     ::= { hwNativeTDMConnectStatEntry 11 }
       
   hwNativeTDMConnectDropDownstreamSnError OBJECT-TYPE
     SYNTAX Counter32
     MAX-ACCESS read-only
     STATUS current
     DESCRIPTION
       "Discarded downstream CESoP packets due to SN error.
       "
     ::= { hwNativeTDMConnectStatEntry 12 }
                
   hwNativeTDMConnectStatClear OBJECT-TYPE  
     SYNTAX     INTEGER   
      {  
        clearExecute(1),
        invalid(-1)
      }
                 
     MAX-ACCESS   read-write
     STATUS      current   
     DESCRIPTION 
       "Clear the native TDM connect statistics.
        Options:
        1. clearExecute(1)   -clear the native TDM connect statistics
        2. invalid(-1)       -invalid value
        Default: clearExecute(1)
        "  
     DEFVAL { clearExecute }
     ::= { hwNativeTDMConnectStatEntry 50}  
      
   hwNativeTDMConnectUpstreamRecvEthPackets OBJECT-TYPE
     SYNTAX Counter32
     MAX-ACCESS read-only
     STATUS current
     DESCRIPTION
       "Statistics of the Rx upstream Ethernet packets.
       "
     ::= { hwNativeTDMConnectStatEntry 51 }
     
   hwNativeTDMConnectDownstreamSendEthPackets OBJECT-TYPE
     SYNTAX Counter32
     MAX-ACCESS read-only
     STATUS current
     DESCRIPTION
       "Statistics of the Tx downstream Ethernet packets.
       "
     ::= { hwNativeTDMConnectStatEntry 52 }
     
   hwNativeTDMConnectUpstreamRecvVC12Packets OBJECT-TYPE
     SYNTAX Counter32
     MAX-ACCESS read-only
     STATUS current
     DESCRIPTION
       "Statistics of the Rx upstream VC12 frames.
       "
     ::= { hwNativeTDMConnectStatEntry 53 }
     
   hwNativeTDMConnectDownstreamSendVC12Packets OBJECT-TYPE
     SYNTAX Counter32
     MAX-ACCESS read-only
     STATUS current
     DESCRIPTION
       "Statistics of the Tx downstream VC12 frames.
       "
     ::= { hwNativeTDMConnectStatEntry 54 }
     
   hwNativeTDMConnectFifoFullPackets OBJECT-TYPE
     SYNTAX Counter32
     MAX-ACCESS read-only
     STATUS current
     DESCRIPTION
       "FIFO full statistics in the de-jitter buffer.
       "
     ::= { hwNativeTDMConnectStatEntry 55 }    
     
   hwNativeTDMConnectFifoEmptyPackets OBJECT-TYPE
     SYNTAX Counter32
     MAX-ACCESS read-only
     STATUS current
     DESCRIPTION
       "FIFO empty statistics in the de-jitter buffer.
       "
     ::= { hwNativeTDMConnectStatEntry 56 }
     
   hwNativeTDMConnectOnuDropPackets OBJECT-TYPE
    SYNTAX Counter64
    MAX-ACCESS read-only
    STATUS current
    DESCRIPTION
      "Discarded packets on onu side.
      "
    ::= { hwNativeTDMConnectStatEntry 57 }
   
   hwNativeTDMConnectOnuRecvPackets OBJECT-TYPE
    SYNTAX Counter64
    MAX-ACCESS read-only
    STATUS current
    DESCRIPTION
      "Received packets on onu side.
      "
    ::= { hwNativeTDMConnectStatEntry 58 }
   
   hwNativeTDMConnectOnuSendPackets OBJECT-TYPE
    SYNTAX Counter64
    MAX-ACCESS read-only
    STATUS current
    DESCRIPTION
      "Transmitted packets on onu side.
      "
    ::= { hwNativeTDMConnectStatEntry 59 }
   
   hwNativeTDMConnectOnuRecvErrCesopPackets OBJECT-TYPE
    SYNTAX Counter64
    MAX-ACCESS read-only
    STATUS current
    DESCRIPTION
      "Received abnormal CESoP packets on onu side.
      "
    ::= { hwNativeTDMConnectStatEntry 60 }
   
   hwNativeTDMConnectOnuRecvSnErrCesopPackets OBJECT-TYPE
    SYNTAX Counter64
    MAX-ACCESS read-only
    STATUS current
    DESCRIPTION
      "Received SN-error CESoP packets on onu side.
      "
    ::= { hwNativeTDMConnectStatEntry 61 }
   
   hwNativeTDMConnectOnuRecvSsrcErrCesopPackets OBJECT-TYPE
    SYNTAX Counter64
    MAX-ACCESS read-only
    STATUS current
    DESCRIPTION
      "Received SSRC-error CESoP packets on onu side.
      "
    ::= { hwNativeTDMConnectStatEntry 62 }     
               
   hwNativeTDMBoardAttrTable OBJECT-TYPE
     SYNTAX SEQUENCE OF HwNativeTDMBoardAttrEntry
     MAX-ACCESS not-accessible
     STATUS current
     DESCRIPTION
       "Configuration table of Native TDM to CESoP board attribute, such as loopback type.
        The indexes of this table are hwNativeTDMBoardAttrFrameIndex and hwNativeTDMBoardAttrSlotIndex.
        "
     ::= { hwNTDMMibObjects 7 }

   hwNativeTDMBoardAttrEntry OBJECT-TYPE
     SYNTAX HwNativeTDMBoardAttrEntry
     MAX-ACCESS not-accessible
     STATUS current
     DESCRIPTION
       "Configuration table of Native TDM to CESoP board attribute, such as loopback type.
        The indexes of this entry are hwNativeTDMBoardAttrFrameIndex and hwNativeTDMBoardAttrSlotIndex.
        "
     INDEX { hwNativeTDMBoardAttrFrameIndex, hwNativeTDMBoardAttrSlotIndex  }
     ::= { hwNativeTDMBoardAttrTable 1 }

   HwNativeTDMBoardAttrEntry ::=
     SEQUENCE 
     {
       hwNativeTDMBoardAttrFrameIndex      Integer32,
       hwNativeTDMBoardAttrSlotIndex       Integer32,
       hwNativeTDMBoardLoopback            INTEGER
     }

   hwNativeTDMBoardAttrFrameIndex OBJECT-TYPE
     SYNTAX Integer32
     MAX-ACCESS not-accessible
     STATUS current
     DESCRIPTION
       "Frame ID of the TDM board."
     ::= { hwNativeTDMBoardAttrEntry 1 }

   hwNativeTDMBoardAttrSlotIndex OBJECT-TYPE
     SYNTAX Integer32(-1 | 0..22)    
     MAX-ACCESS not-accessible
     STATUS current
     DESCRIPTION
       "Slot ID of the TDM board."
     ::= { hwNativeTDMBoardAttrEntry 2 }
     
   hwNativeTDMBoardLoopback OBJECT-TYPE
     SYNTAX INTEGER
      {  
        noloop(1),
        cesopinloop(2),
        cesopoutloop(3),
        nativeoutloop(4),
        nativeinloop(5) 
      }
     MAX-ACCESS read-write
     STATUS current
     DESCRIPTION
       "Loopback type of the TDM board.
        Options:
        1. noloop(1)         -no loopback
        2. cesopinloop(2)    -cesop in loopback
        3. cesopoutloop(3)   -cesop out loopback
        4. nativeoutloop(4)  -native out loopback
        5. nativeinloop(5)   -native in loopback
        Default: noloop(1)
        "
     DEFVAL { noloop }
     ::= { hwNativeTDMBoardAttrEntry 3 }  
     
   hwNTDMTraps       OBJECT IDENTIFIER ::= { hwNTDM 2 }
   hwNTDMTrapsVbOids OBJECT IDENTIFIER ::= { hwNTDM 3 }
              
   hwNTDMCommonTraps OBJECT IDENTIFIER ::= { hwNTDMTraps 1 }   
   hwNTDMCommonTrapsPrefix  OBJECT IDENTIFIER ::= { hwNTDMCommonTraps 0 }    
   
   hwTDMAccessModeChangeTrap NOTIFICATION-TYPE
     OBJECTS {
              hwConfigChangeIP,
              hwNativeTDMFrameIndex,
              hwNativeTDMSlotIndex,
              hwTDMCfgAccessMode
             } 
     STATUS current
     DESCRIPTION
            "This trap will send when switch access mode."
     ::= { hwNTDMCommonTraps 0 1 }

   hwNTDMAlarmTraps  OBJECT IDENTIFIER ::= { hwNTDMTraps 2 }               
   hwNTDMAlarmTrapsPrefix  OBJECT IDENTIFIER ::= { hwNTDMAlarmTraps 0 }
   
   hwNTDMConnectFaultPeerEndAlarmTrap NOTIFICATION-TYPE
     OBJECTS {
             hwFrameIndex,
             hwSlotIndex,
             hwNativeTDMConnectID
             } 
     STATUS current
     DESCRIPTION
            "This trap will send when the TDM connection fault occurs between the peer end and its connected equipment."
     ::= { hwNTDMAlarmTraps 0 1 }
     
   hwNTDMConnectFaultLocalAlarmTrap NOTIFICATION-TYPE
     OBJECTS {
             hwFrameIndex,
             hwSlotIndex,
             hwNativeTDMConnectID
             } 
     STATUS current
     DESCRIPTION
            "This trap will send when the TDM connection fault occurs between the local device and the peer end."
     ::= { hwNTDMAlarmTraps 0 2 }
     
   hwNTDMConnectAISRecoverAlarmTrap NOTIFICATION-TYPE
     OBJECTS {
             hwFrameIndex,
             hwSlotIndex,
             hwNativeTDMConnectID
             } 
     STATUS current
     DESCRIPTION
            "This trap will send when the TDM connection AIS recovers from the abnormal state."
     ::= { hwNTDMAlarmTraps 0 3 }
     
   hwNTDMConnectRDIRecoverAlarmTrap NOTIFICATION-TYPE
     OBJECTS {
             hwFrameIndex,
             hwSlotIndex,
             hwNativeTDMConnectID
             } 
     STATUS current
     DESCRIPTION
            "This trap will send when the TDM connection RDI recovers from the abnormal state."
     ::= { hwNTDMAlarmTraps 0 4 }
  END
