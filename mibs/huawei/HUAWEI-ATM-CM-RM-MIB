-- ============================================================================
-- Copyright (C) 2010 by  HUAWEI TECHNOLOGIES. All rights reserved.
-- Description:   The MIB is used for defining huawei's ATM CM RM MIB objects.
-- Reference:  
-- Version: V1.10
-- ============================================================================

  HUAWEI-ATM-CM-RM-MIB DEFINITIONS ::= BEGIN
 
    IMPORTS
      atmVclVpi, atmVclVci      
        FROM ATM-MIB      
      hwFrameIndex, hwSlotIndex, hwFrameIndex, hwSlotIndex, hwConfigChangeIP      
        FROM HUAWEI-DEVICE-MIB
      hwIpdslamConnectIndex
        FROM HUAWEI-ETHERLIKE-EXT-MIB             
      huaweiMgmt
        FROM HUAWEI-MIB     
      ifIndex     
        FROM IF-MIB     
      IpAddress, Integer32, OBJECT-TYPE, MODULE-IDENTITY, NOTIFICATION-TYPE     
        FROM SNMPv2-SMI     
      MacAddress      
        FROM SNMPv2-TC
      atmVcCrossConnectIndex, atmVcCrossConnectLowIfIndex, atmVcCrossConnectLowVpi, atmVcCrossConnectLowVci, 
      atmVcCrossConnectHighIfIndex, atmVcCrossConnectHighVpi, atmVcCrossConnectHighVci, atmVclReceiveTrafficDescrIndex,
      atmVclTransmitTrafficDescrIndex, atmVclCastType, atmVclConnKind
        FROM ATM-MIB
      hwAtmVclUpcNpcFlagCfg, hwAtmVclUpcNpcFlag
        FROM HUAWEI-ATM-EXT-MIB;


    hwAtmCmRm MODULE-IDENTITY 
      LAST-UPDATED "201011090000Z"
      ORGANIZATION 
         "Huawei Technologies Co.,Ltd."
      CONTACT-INFO 
         "Huawei Industrial Base
          Bantian, Longgang
          Shenzhen 518129
          People's Republic of China
          Website: http://www.huawei.com
          Email: support@huawei.com
         "
      DESCRIPTION 
        "The MIB is used for defining huawei's ATM CM RM MIB objects."
  
--  Revision history 
      REVISION "201011090000Z"     
      DESCRIPTION  "V1.10, modified the description of MIB. "
      
      REVISION "201010100000Z"     
      DESCRIPTION
        "V1.09, modified the description of hwVclGatewayMac.
        " 
        
      REVISION "201008130000Z"     
      DESCRIPTION
        "V1.08, modified parameter hwAtmAutosensePvcVpiVciTrap.
        Added the following leaves into hwAtmCmRmVbTrapsOids: 
           hwatmVcCrossConnectIndex, 
           hwatmVcCrossConnectLowIfIndex,
           hwatmVcCrossConnectLowVpi, 
           hwatmVcCrossConnectLowVci, 
           hwatmVcCrossConnectHighIfIndex,
           hwatmVcCrossConnectHighVpi, 
           hwatmVcCrossConnectHighVci, 
           hwatmVclReceiveTrafficDescrLowIndex,
           hwatmVclTransmitTrafficDescrLowIndex, 
           hwatmVclCastTypeLow,   
           hwatmVclConnKindLow,   
           hwAtmVclUpcNpcFlagLowCfg, 
           hwatmVclReceiveTrafficDescrHighIndex, 
           hwatmVclTransmitTrafficDescrHighIndex,
           hwatmVclCastTypeHigh, 
           hwatmVclConnKindHigh, 
           hwAtmVclUpcNpcFlagHighCfg.    
        " 

      REVISION "201007280000Z"     
      DESCRIPTION
        "V1.07, modified the description of MIB.
         Modified parameter hwAtmVclUpcNpcFlag to hwAtmVclUpcNpcFlagCfg 
         in trap hwAtmCmRmVcCxcChangeTrap and hwAtmAutosensePvcVpiVciTrap.
        "     
      
      REVISION "201006300000Z"                 
      DESCRIPTION                  
        "
        V1.06, added the definition of leaf hwAtmAutosensePvcVpiVciTrap.
        Modified the definition of leaf hwAtmCmRmVcCxcChangeTrap.
        Changed leaf hwVclEncapTypeChangeSerialNo to hwConfigChangeIP and changed its type from Integer32 to IpAddress.
        Deleted the definition for hwVclEncapTypeChangeSerialNo.
        "    
      
      REVISION "201003160000Z"     
      DESCRIPTION                  
        "
        V1.05, added the enumerated value that causes the hwVclUserSrcIpMode to be invalid.
        Modified the description of hwVclAttrTable.
        " 
        
      REVISION "201002080000Z"     
      DESCRIPTION                  
        "V1.04, added the definition of the trap node." 

      REVISION "201002020000Z"     
      DESCRIPTION                  
        "
        V1.03, added the definition for the common leaf hwVclEncapTypeChangeTrap that is used 
        for encapsulation type change.
        Added the definition of the alarm leaf hwVclPvcProtocolNoFreeSrcMacTrap that is used 
        when the PPPoA or IPoA user fails to apply for a source MAC address.
        Added the definitions of hwVclEncapTypeChangeSerialNo and hwVclEncapTypeChangeOperType 
        that are bound to the common leaf hwVclEncapTypeChangeTrap used for encapsulation type change.
        Added the definition of hwVclPvcProtocolUsedMacNum that is bound to the alarm trap leaf 
        hwVclPvcProtocolNoFreeSrcMacTrap used when the PPPoA or IPoA user fails to apply for a source 
        MAC address.
        "
                     
      REVISION "200712170000Z"     
      DESCRIPTION                  
        "V1.01, added hwVclAttrTable for management VCL."
                             
      REVISION "200611240000Z"     
      DESCRIPTION                  
        "V1.00, initial version."
                                   
                                   
      ::= { huaweiMgmt 10 }        
                                                                              
    hwAtmPortBandWidthTable OBJECT-TYPE
      SYNTAX SEQUENCE OF HwAtmPortBandWidthEntry
      MAX-ACCESS not-accessible
      STATUS current
      DESCRIPTION
        "BandWidth table of ATM port, such as the bandwidth value of the ATM port.
         The index of this table is ifIndex.
        "
      ::= { hwAtmCmRm 1 }
    
    hwAtmPortBandWidthEntry OBJECT-TYPE
      SYNTAX HwAtmPortBandWidthEntry
      MAX-ACCESS not-accessible
      STATUS current
      DESCRIPTION
        "BandWidth table of ATM port, such as the bandwidth value of the ATM port.
         The index of this entry is ifIndex.
        "
      INDEX { ifIndex }
      ::= { hwAtmPortBandWidthTable 1 }
    
    HwAtmPortBandWidthEntry ::=
      SEQUENCE { 
        hwAtmPortBandWidthValue
          Integer32
               }

    hwAtmPortBandWidthValue OBJECT-TYPE
      SYNTAX Integer32
      MAX-ACCESS read-write
      STATUS current
      DESCRIPTION
        "The bandwidth value of the ATM port."
      DEFVAL { 0 }
      ::= { hwAtmPortBandWidthEntry 1 }
    
    hwApmBandWidthTable OBJECT-TYPE
      SYNTAX SEQUENCE OF HwApmBandWidthEntry
      MAX-ACCESS not-accessible
      STATUS current
      DESCRIPTION
        "BandWidth resource table of apm, such as the type and the bandwidth of apm.
         The indexes of this table are hwFrameIndex, hwSlotIndex and hwApmBandWidthType.
         "
      ::= { hwAtmCmRm 2 }
    
    hwApmBandWidthEntry OBJECT-TYPE
      SYNTAX HwApmBandWidthEntry
      MAX-ACCESS not-accessible
      STATUS current
      DESCRIPTION
        "BandWidth resource table of apm, such as the type and the bandwidth of apm.
         The indexes of this entry are hwFrameIndex, hwSlotIndex and hwApmBandWidthType.
         "
      INDEX { hwFrameIndex, hwSlotIndex, hwApmBandWidthType }
      ::= { hwApmBandWidthTable 1 }
    
    HwApmBandWidthEntry ::=
      SEQUENCE { 
        hwApmBandWidthType
          INTEGER,
        hwApmBandWidthValue
          Integer32
               }

    hwApmBandWidthType OBJECT-TYPE
      SYNTAX INTEGER
        {
        vpring(1),
        relay(2),
        inner(3)
        }
      MAX-ACCESS not-accessible
      STATUS current
      DESCRIPTION
        "BandWidth type of apm.
         Options:
         1. vpring(1)  -BandWidth type of apm is vpring
         2. relay(2)   -BandWidth type of apm is relay
         3. inner(3)   -BandWidth type of apm is inner
         "
      ::= { hwApmBandWidthEntry 1 }
    
    hwApmBandWidthValue OBJECT-TYPE
      SYNTAX Integer32
      MAX-ACCESS read-write
      STATUS current
      DESCRIPTION
        "The bandwidth value of the apm."
      DEFVAL { 0 }
      ::= { hwApmBandWidthEntry 2 }
    
    
    hwVclAttrTable OBJECT-TYPE
      SYNTAX SEQUENCE OF HwVclAttrEntry
      MAX-ACCESS not-accessible
      STATUS current
      DESCRIPTION
        "VCL attribute table, this table is used for setting and querying the VCL attributes.
         Currently, parameters such as the encapsulation type and xPoA2E can be set and queried.
         It is created automatically when traffic streams are created.
         The indexes of this table are ifIndex, atmVclVpi and atmVclVci.
        "
      ::= { hwAtmCmRm 3 }
    
    hwVclAttrEntry OBJECT-TYPE
      SYNTAX HwVclAttrEntry
      MAX-ACCESS not-accessible
      STATUS current
      DESCRIPTION
        "VCL attribute table, this table is used for setting and querying the VCL attributes.
         Currently, parameters such as the encapsulation type and xPoA2E can be set and queried.
         It is created automatically when traffic streams are created.
         The indexes of this entry are ifIndex, atmVclVpi and atmVclVci.
        "
      INDEX { ifIndex, atmVclVpi, atmVclVci }
      ::= { hwVclAttrTable 1 }
    
    HwVclAttrEntry ::=
      SEQUENCE { 
        hwVclEncapType
          INTEGER,
        hwVclUserSrcMac
          MacAddress,
        hwVclGatewayMac
          MacAddress,
        hwVclUserSrcIP
          IpAddress,
        hwVclGatewayIP
          IpAddress,          
        hwVclUserSrcIpMode
          INTEGER,
        hwVclUserSessionId
          Integer32,
        hwVclUserActualType
          INTEGER
              }

    hwVclEncapType OBJECT-TYPE
      SYNTAX INTEGER
        {
        auto(1),
        llcBridge(2),
        llcPPP(3),
        llcIP(4),
        vcmuxBridge(5),
        vcmuxPPP(6),
        vcmuxIP(7)
        }
      MAX-ACCESS read-create
      STATUS current
      DESCRIPTION
        "PVC encapsulation type.
         Options:
         1. auto(1)        -PVC encapsulation type is auto    
         2. llcBridge(2)   -PVC encapsulation type is llcBridge
         3. llcPPP(3)      -PVC encapsulation type is llcPPP
         4. llcIP(4)       -PVC encapsulation type is llcIP
         5. vcmuxBridge(5) -PVC encapsulation type is vcmuxBridge
         6. vcmuxPPP(6)    -PVC encapsulation type is vcmuxPPP
         7. vcmuxIP(7)     -PVC encapsulation type is vcmuxIP
         Default: llcBridge(2)
        "
      DEFVAL { llcBridge }
      ::= { hwVclAttrEntry 1 }
    
    hwVclUserSrcMac OBJECT-TYPE
      SYNTAX MacAddress
      MAX-ACCESS read-only
      STATUS current
      DESCRIPTION
        "SrcMac of the PVC forwarding entry.
        "
      ::= { hwVclAttrEntry 2 }
    
    hwVclGatewayMac OBJECT-TYPE
      SYNTAX MacAddress
      MAX-ACCESS read-only
      STATUS current
      DESCRIPTION
        "DstMac of the VCL gateway.
        "
      ::= { hwVclAttrEntry 3 }
    
    hwVclUserSrcIP OBJECT-TYPE
      SYNTAX IpAddress
      MAX-ACCESS read-write
      STATUS current
      DESCRIPTION
        "Set or query the IP address of the static IPoA user configured on the RTU, 
         or query the IP address of the dynamic IPoA user configured on the RTU.
         It is valid when the encapsulation type is IPoA.
        "
      ::= { hwVclAttrEntry 4 }

    hwVclGatewayIP OBJECT-TYPE
      SYNTAX IpAddress
      MAX-ACCESS read-write
      STATUS current
      DESCRIPTION
        "Set or query the destination gateway IP address of the IPoA user. 
         In the case of auto encapsulation type, the destination IP address must be specified during 
         configuration if the IPoA default gateway of the system is not configured.
         It is valid when the encapsulation type is IPoA or auto.
        "
      ::= { hwVclAttrEntry 5 }
    
    hwVclUserSrcIpMode OBJECT-TYPE
      SYNTAX INTEGER
        {
        dynamicIP(1),
        staticIP(2),
        invalid(255)
        }
      MAX-ACCESS read-only
      STATUS current
      DESCRIPTION
        "User corresponding to the PVC.
         Options:
         1. dynamicIP(1) -The user corresponding to the PVC is a dynamic user or auto user
         2. staticIP(2)  -The user corresponding to the PVC is a static user
         3. invalid(255) -Invalid value
         It is valid when the encapsulation type is IPoA.
        "
      ::= { hwVclAttrEntry 6 }
    
    hwVclUserSessionId OBJECT-TYPE
      SYNTAX Integer32 (0..65535)
      MAX-ACCESS read-only
      STATUS current
      DESCRIPTION
        "Query the session ID of the PPPoA to PPPoE converted user.
         It is valid when the actual encapsulation mode is PPPoA.
        "
      ::= { hwVclAttrEntry 7 }
    
    hwVclUserActualType OBJECT-TYPE
      SYNTAX INTEGER
        {
        bridge(1),
        llcPPP(2),
        llcIP(3),
        vcPPP(4),
        llcBridge(5),
        vcmuxBridge(6),
        vcmuxIP(7)
        }
      MAX-ACCESS read-only
      STATUS current
      DESCRIPTION
        "Actual PVC encapsulation type.
         Options:
         1. bridge(1)     -Actual PVC encapsulation type is bridge
         2. llcPPP(2)     -Actual PVC encapsulation type is llcPPP
         3. llcIP(3)      -Actual PVC encapsulation type is llcIP
         4. vcPPP(4)      -Actual PVC encapsulation type is vcPPP
         5. llcBridge(5)  -Actual PVC encapsulation type is llcBridge
         6. vcmuxBridge(6)-Actual PVC encapsulation type is vcmuxBridge
         7. vcmuxIP(7)    -Actual PVC encapsulation type is vcmuxIP
        "
      ::= { hwVclAttrEntry 8 }
      
      
    hwAtmCmRmVbTrapsOids OBJECT IDENTIFIER ::= { hwAtmCmRm 10 } 
                
    hwAtmCmRmOperType OBJECT-TYPE
      SYNTAX   INTEGER 
        {
        add(1),
        modify(2),
        delete(3)
        } 
      MAX-ACCESS   accessible-for-notify
      STATUS       current
      DESCRIPTION
        "Operation type.
         Options:
         1. add(1)    -Operation type is add
         2. modify(2) -Operation type is modify
         3. delete(3) -Operation type is delete
        "
      ::= { hwAtmCmRmVbTrapsOids 1 } 
            
    hwVclEncapTypeChangeOperType OBJECT-TYPE
      SYNTAX Integer32   
      MAX-ACCESS  accessible-for-notify
      STATUS current
      DESCRIPTION
        "The operation type is used when the PVC encapsulation is changed. 
         Value 1 indicates that the encapsulation type is changed.
        "
      ::= { hwAtmCmRmVbTrapsOids 2 }        
            
    hwVclPvcConnectIndex OBJECT-TYPE
        SYNTAX Integer32 (-1|1..2147483647)
        MAX-ACCESS  accessible-for-notify
        STATUS current
        DESCRIPTION
          "
          The index used for reporting the trap information when the PVC encapsulation is changed.
          For the four-step service flow in the xDSL/AIUG ATM access mode creation, atmVcCrossConnectIndex is the index of hwVclPvcConnectIndex.
          For the one-step service flow in the xDSL/AIUG ATM access mode creation, the hwVclPvcConnectIndex is set to -1.
          "
        ::= { hwAtmCmRmVbTrapsOids 3 }
        
    hwVclPvcProtocolUsedMacNum OBJECT-TYPE
        SYNTAX Integer32   
        MAX-ACCESS  accessible-for-notify
        STATUS current
        DESCRIPTION
          "Indicate the total number of source MAC addresses used by the current 
           IPoA and PPPoA users.
          "
        ::= { hwAtmCmRmVbTrapsOids 4 } 
    
    hwatmVcCrossConnectIndex OBJECT-TYPE
        SYNTAX Integer32   
        MAX-ACCESS  accessible-for-notify
        STATUS current
        DESCRIPTION
          "
          A unique value to identify this VC cross-connect.
          For each VCL associated with this cross-connect,
          the agent reports this cross-connect index value.
          "
        ::= { hwAtmCmRmVbTrapsOids 5 } 
        
    hwatmVcCrossConnectLowIfIndex OBJECT-TYPE
        SYNTAX Integer32   
        MAX-ACCESS  accessible-for-notify
        STATUS current
        DESCRIPTION
          "
          The ifIndex value of the ATM interface for this
          VC cross-connect. The term low implies
          that this ATM interface has the numerically lower
          ifIndex value.
          "                                  
        ::= { hwAtmCmRmVbTrapsOids 6 }         
                                               
    hwatmVcCrossConnectLowVpi OBJECT-TYPE
        SYNTAX Integer32   
        MAX-ACCESS  accessible-for-notify
        STATUS current
        DESCRIPTION
          "
          The VPI value at the ATM interface
          associated with the VC cross-connect.
          "
        ::= { hwAtmCmRmVbTrapsOids 7 } 
        
    hwatmVcCrossConnectLowVci OBJECT-TYPE
        SYNTAX Integer32   
        MAX-ACCESS  accessible-for-notify
        STATUS current
        DESCRIPTION
          "
          The VCI value at the ATM interface
          associated with this VC cross-connect.
          "
        ::= { hwAtmCmRmVbTrapsOids 8 } 
        
    hwatmVcCrossConnectHighIfIndex OBJECT-TYPE
        SYNTAX Integer32   
        MAX-ACCESS  accessible-for-notify
        STATUS current
        DESCRIPTION
          "
          The ifIndex value for the ATM interface for
          this VC cross-connect. The term high implies
            that this ATM interface has the numerically higher
          ifIndex value.
          "
        ::= { hwAtmCmRmVbTrapsOids 9 }
         
    hwatmVcCrossConnectHighVpi OBJECT-TYPE
        SYNTAX Integer32   
        MAX-ACCESS  accessible-for-notify
        STATUS current
        DESCRIPTION
          "
          The VPI value at the ATM interface
          associated with the VC cross-connect.
          "
        ::= { hwAtmCmRmVbTrapsOids 10 } 
        
    hwatmVcCrossConnectHighVci OBJECT-TYPE
        SYNTAX Integer32   
        MAX-ACCESS  accessible-for-notify
        STATUS current
        DESCRIPTION
          "
          The VCI value at the ATM interface
          associated with the VC cross-connect.
          "
        ::= { hwAtmCmRmVbTrapsOids 11 } 
          
    hwatmVclReceiveTrafficDescrHighIndex OBJECT-TYPE
        SYNTAX Integer32   
        MAX-ACCESS  accessible-for-notify
        STATUS current
        DESCRIPTION
          "
          The value of this object identifies the row
          in the ATM Traffic Descriptor Table which
          applies to the receive direction of this VCL.
          "
        ::= { hwAtmCmRmVbTrapsOids 12 } 
          
    hwatmVclTransmitTrafficDescrHighIndex OBJECT-TYPE
        SYNTAX Integer32   
        MAX-ACCESS  accessible-for-notify
        STATUS current
        DESCRIPTION
          "
          The value of this object identifies the row
          of the ATM Traffic Descriptor Table which applies
          to the transmit direction of this VCL.
          "
        ::= { hwAtmCmRmVbTrapsOids 13 } 
          
    hwatmVclCastTypeHigh OBJECT-TYPE
        SYNTAX Integer32   
        MAX-ACCESS  accessible-for-notify
        STATUS current
        DESCRIPTION
          "
          The connection topology type.
          "
        ::= { hwAtmCmRmVbTrapsOids 14 }  
          
    hwatmVclConnKindHigh OBJECT-TYPE
        SYNTAX Integer32   
        MAX-ACCESS  accessible-for-notify
        STATUS current
        DESCRIPTION
          "
          The use of call control.
          "
        ::= { hwAtmCmRmVbTrapsOids 15 } 
           
    hwAtmVclUpcNpcFlagHighCfg OBJECT-TYPE
        SYNTAX Integer32   
        MAX-ACCESS  accessible-for-notify
        STATUS current
        DESCRIPTION
          "
          VCL UPC  identifiers expanded from atmVclTable of ATM-MIB.
          "
        ::= { hwAtmCmRmVbTrapsOids 16 } 
        
    hwatmVclReceiveTrafficDescrLowIndex OBJECT-TYPE
        SYNTAX Integer32   
        MAX-ACCESS  accessible-for-notify
        STATUS current
        DESCRIPTION
          "
          The value of this object identifies the row
          in the ATM Traffic Descriptor Table which
          applies to the receive direction of this VCL.
          "
        ::= { hwAtmCmRmVbTrapsOids 17 } 
          
    hwatmVclTransmitTrafficDescrLowIndex OBJECT-TYPE
        SYNTAX Integer32   
        MAX-ACCESS  accessible-for-notify
        STATUS current
        DESCRIPTION
          "
          The value of this object identifies the row
          of the ATM Traffic Descriptor Table which applies
          to the transmit direction of this VCL.
          "
        ::= { hwAtmCmRmVbTrapsOids 18 } 
          
    hwatmVclCastTypeLow OBJECT-TYPE
        SYNTAX Integer32   
        MAX-ACCESS  accessible-for-notify
        STATUS current
        DESCRIPTION
          "
          The connection topology type.
          "
        ::= { hwAtmCmRmVbTrapsOids 19 }  
            
    hwatmVclConnKindLow OBJECT-TYPE
        SYNTAX Integer32   
        MAX-ACCESS  accessible-for-notify
        STATUS current
        DESCRIPTION
          "
          The use of call control.
          "
        ::= { hwAtmCmRmVbTrapsOids 20 } 
           
    hwAtmVclUpcNpcFlagLowCfg OBJECT-TYPE
        SYNTAX Integer32   
        MAX-ACCESS  accessible-for-notify
        STATUS current
        DESCRIPTION
          "
          VCL UPC  identifiers expanded from atmVclTable of ATM-MIB.
          "
        ::= { hwAtmCmRmVbTrapsOids 21 }
          
    hwAtmCmRmTraps OBJECT IDENTIFIER ::= { hwAtmCmRm 11 }
    hwAtmCmRmCommonTraps OBJECT IDENTIFIER ::= { hwAtmCmRmTraps 1 }
    hwAtmCmRmCommonTrapsPrefix OBJECT IDENTIFIER ::= { hwAtmCmRmCommonTraps 0 }
    hwAtmCmRmAlarmTraps OBJECT IDENTIFIER ::= { hwAtmCmRmTraps 2 }
    hwAtmCmRmAlarmTrapsPrefix OBJECT IDENTIFIER ::= { hwAtmCmRmAlarmTraps 0 }
          
-- Common traps
    hwAtmCmRmVcCxcChangeTrap NOTIFICATION-TYPE
        OBJECTS {
                hwConfigChangeIP,
                hwAtmCmRmOperType,
                atmVcCrossConnectIndex,
                atmVcCrossConnectLowIfIndex,
                atmVcCrossConnectLowVpi,
                atmVcCrossConnectLowVci,
                atmVcCrossConnectHighIfIndex,
                atmVcCrossConnectHighVpi,
                atmVcCrossConnectHighVci,
                atmVclReceiveTrafficDescrIndex,
                atmVclTransmitTrafficDescrIndex,
                atmVclCastType,   
                atmVclConnKind,   
                hwAtmVclUpcNpcFlagCfg,
                atmVclReceiveTrafficDescrIndex,
                atmVclTransmitTrafficDescrIndex,
                atmVclCastType,   
                atmVclConnKind,   
                hwAtmVclUpcNpcFlagCfg
                } 
        STATUS current
        DESCRIPTION
          "This trap is sent when the CM VC CXC change.
           The value -1 that is reported through the trap indicates that the parameter is invalid. 
          "
        ::= { hwAtmCmRmCommonTraps 0 1 }
        
    hwVclEncapTypeChangeTrap NOTIFICATION-TYPE
        OBJECTS { 
                hwConfigChangeIP,
                hwVclEncapTypeChangeOperType,     
                hwVclPvcConnectIndex,  
                hwVclEncapType,
                hwVclUserSrcIP,
                hwVclGatewayIP,
                ifIndex,
                atmVclVpi,
                atmVclVci
                }  
        STATUS  current
        DESCRIPTION
          "This trap is sent when the PVC encapsulation is changed."  
        ::= { hwAtmCmRmCommonTraps 0 2 }
            
    hwAtmAutosensePvcVpiVciTrap NOTIFICATION-TYPE
        OBJECTS {
                 hwConfigChangeIP,
                 hwAtmCmRmOperType,
                 hwatmVcCrossConnectIndex,
                 hwatmVcCrossConnectLowIfIndex,
                 hwatmVcCrossConnectLowVpi,
                 hwatmVcCrossConnectLowVci,
                 hwatmVcCrossConnectHighIfIndex,
                 hwatmVcCrossConnectHighVpi,
                 hwatmVcCrossConnectHighVci,
                 hwatmVclReceiveTrafficDescrLowIndex,
                 hwatmVclTransmitTrafficDescrLowIndex,
                 hwatmVclCastTypeLow,   
                 hwatmVclConnKindLow,   
                 hwAtmVclUpcNpcFlagLowCfg,
                 hwatmVclReceiveTrafficDescrHighIndex,
                 hwatmVclTransmitTrafficDescrHighIndex,
                 hwatmVclCastTypeHigh,   
                 hwatmVclConnKindHigh,   
                 hwAtmVclUpcNpcFlagHighCfg                             
               } 
        STATUS current
        DESCRIPTION
          "This trap is sent when the VPI VCI auto sense.
           The value -1 that is reported through the trap indicates that the parameter is invalid. 
          "
        ::= { hwAtmCmRmCommonTraps 0 3 }          
        
    hwVclPvcProtocolNoFreeSrcMacTrap NOTIFICATION-TYPE
        OBJECTS { 
                hwVclPvcProtocolUsedMacNum
                }  
        STATUS  current
        DESCRIPTION
          "This trap is sent when MAC addresses in the MAC address pool are exhausted and 
           the PPPoA or IPoA user fails to apply for a source MAC address.
          "  
        ::= { hwAtmCmRmAlarmTraps 0 1 }                    
        
  END
