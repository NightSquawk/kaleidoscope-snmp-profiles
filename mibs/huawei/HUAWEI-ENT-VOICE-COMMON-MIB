-- ============================================================================
-- Copyright (C) 2016 by  HUAWEI TECHNOLOGIES. All rights reserved.
-- Description:  This MIB module defines MIB objects which provides VOIP global parameters management.
-- Reference:  
-- Version: V1.00
-- ============================================================================

HUAWEI-ENT-VOICE-COMMON-MIB DEFINITIONS ::= BEGIN
    IMPORTS
        MODULE-IDENTITY, OBJECT-TYPE, NOTIFICATION-TYPE, private, Integer32, Unsigned32
            FROM SNMPv2-SMI
        MODULE-COMPLIANCE, OBJECT-GROUP, NOTIFICATION-GROUP
            FROM SNMPv2-CONF
        TEXTUAL-CONVENTION
            FROM SNMPv2-TC
        IpAddress, TimeTicks, Counter32
            FROM SNMPv2-SMI
        RowStatus, DisplayString
            FROM SNMPv2-TC
        hwDatacomm
            FROM HUAWEI-MIB;

hwEntVoiceCommonMIB MODULE-IDENTITY
    LAST-UPDATED "201606130000Z"
    ORGANIZATION 
              "Huawei Technologies Co.,Ltd."
    CONTACT-INFO 
              "Huawei Industrial Base                
              Bantian, Longgang                     
              Shenzhen 518129                       
              People's Republic of China            
              Website: http://www.huawei.com        
              Email: support@huawei.com             
              "  
    DESCRIPTION
        "This MIB module defines MIB objects which provides VOIP global parameters management."
                	
-- Revision history

    REVISION     "201606130000Z"        
    DESCRIPTION  "V1.0, create this file."

::= { hwDatacomm 253 }
               
--==

  hwEntServiceModeTable OBJECT IDENTIFIER ::= {  hwEntVoiceCommonMIB 1  }
     
  hwEntServiceModeConfig OBJECT-TYPE
    SYNTAX      INTEGER{h248Ag(1), sipAg(2), pbxSip(3)}
    MAX-ACCESS  read-write
    STATUS      current
    DESCRIPTION
        " 
        Indicates the configuration of voice feature that will be supported by the system after resets. 
        Options:
        h248Ag(1) 
 	    sipAg(2) 
 	    pbxSip(3)    
        "
    ::= { hwEntServiceModeTable 1 }   
    
  hwEntServiceModeActive OBJECT-TYPE
    SYNTAX      INTEGER{h248Ag(1), sipAg(2), pbxSip(3)}
    MAX-ACCESS  read-only
    STATUS      current
    DESCRIPTION
        " 
        Indicates the configuration voice feature that is currently used.
        Options:
        h248Ag(1) 
 	    sipAg(2) 
 	    pbxSip(3)     
      "
    ::= { hwEntServiceModeTable 2 }   

--==

    hwEntUserDefineRingTypeTable     OBJECT-TYPE
        SYNTAX         SEQUENCE OF HwEntUserDefineRingTypeEntry
        MAX-ACCESS     not-accessible
        STATUS         current
        DESCRIPTION
            "
            This table is used to set the user-defined ring type.
            The index of this table is hwEntUserDefineRingType.
           "
    ::= { hwEntVoiceCommonMIB 2 }

    hwEntUserDefineRingTypeEntry         OBJECT-TYPE
        SYNTAX         HwEntUserDefineRingTypeEntry
        MAX-ACCESS     not-accessible
        STATUS         current
        DESCRIPTION
            "
            This table is used to set the user-defined ring type.
            The index of this table is hwEntUserDefineRingType.
            "
            INDEX   { 
                      hwEntUserDefineRingType
                    }
    ::= { hwEntUserDefineRingTypeTable  1 }

     HwEntUserDefineRingTypeEntry ::= SEQUENCE 
     {
        hwEntUserDefineRingType                Integer32,
        hwEntUserDefineRingFirstRing           Integer32,
        hwEntUserDefineRingFirstInterval       Integer32,
        hwEntUserDefineRingSecondRing          Integer32,
        hwEntUserDefineRingSecondInterval      Integer32,
        hwEntUserDefineRingThirdRing           Integer32,
        hwEntUserDefineRingThirdInterval       Integer32                
     }                                         

    hwEntUserDefineRingType         OBJECT-TYPE
        SYNTAX      Integer32(0..15) 
        MAX-ACCESS  not-accessible
        STATUS      current
        DESCRIPTION
            "
            Indicates the index of user-define ring type.
            "
    ::= { hwEntUserDefineRingTypeEntry 1 }

    hwEntUserDefineRingFirstRing         OBJECT-TYPE
        SYNTAX      Integer32(0|200..12750) 
        MAX-ACCESS  read-write
        STATUS      current
        DESCRIPTION
            "
            Indicates the first ring time length. 
            0 means to cancel parameter value.
            Unit: ms
            "
    ::= { hwEntUserDefineRingTypeEntry 2 }


    hwEntUserDefineRingFirstInterval         OBJECT-TYPE
        SYNTAX      Integer32(0|200..12750) 
        MAX-ACCESS  read-write
        STATUS      current
        DESCRIPTION
            "
            Indicates the first silent time length.
            0 means to cancel parameter value.
            Unit: ms
         "
    ::= { hwEntUserDefineRingTypeEntry 3 }

    hwEntUserDefineRingSecondRing         OBJECT-TYPE
        SYNTAX      Integer32(0|200..12750) 
        MAX-ACCESS  read-write
        STATUS      current
        DESCRIPTION
            "
            Indicates the second ring time length.
            0 means to cancel parameter value.
            Unit: ms
            "
    ::= { hwEntUserDefineRingTypeEntry 4 }

    hwEntUserDefineRingSecondInterval         OBJECT-TYPE
        SYNTAX      Integer32(0|200..12750) 
        MAX-ACCESS  read-write
        STATUS      current
        DESCRIPTION
            "
            Indicates the second silent time length.
            0 means to cancel parameter value.
            Unit: ms
         "
    ::= { hwEntUserDefineRingTypeEntry 5 }

    hwEntUserDefineRingThirdRing         OBJECT-TYPE
        SYNTAX      Integer32(0|200..12750) 
        MAX-ACCESS  read-write
        STATUS      current
        DESCRIPTION
            "
            Indicates the third ring time length.
            0 means to cancel parameter value.
            Unit: ms
            "
    ::= { hwEntUserDefineRingTypeEntry 6 }

    hwEntUserDefineRingThirdInterval         OBJECT-TYPE
        SYNTAX      Integer32(0|200..12750) 
        MAX-ACCESS  read-write
        STATUS      current
        DESCRIPTION
            "
            Indicates the third silent time length.
            0 means to cancel parameter value.
            Unit: ms
         "
    ::= { hwEntUserDefineRingTypeEntry 7 } 
    
--==

   hwEntRingModeTable OBJECT-TYPE
     SYNTAX      SEQUENCE OF HwEntRingModeEntry
     MAX-ACCESS  not-accessible
     STATUS      current
     DESCRIPTION
         "
         This table is used to set the ring mode.
         The indexes of this table are hwEntRingModeMgId, hwEntRingModeIndex.
         "
     ::= { hwEntVoiceCommonMIB 3 }
    
   hwEntRingModeEntry OBJECT-TYPE
     SYNTAX      HwEntRingModeEntry
     MAX-ACCESS  not-accessible
     STATUS      current
     DESCRIPTION
         "
         This table is used to set the ring mode.
         The indexes of this entry are hwEntRingModeMgId, hwEntRingModeIndex.
       "
     INDEX    {  
               hwEntRingModeMgId,
               hwEntRingModeIndex
              }
     ::= { hwEntRingModeTable 1 }
 
   HwEntRingModeEntry ::=
     SEQUENCE
     {
       hwEntRingModeMgId	             Integer32,
       hwEntRingModeIndex                Integer32,
       hwEntRingModeName                 DisplayString,
       hwEntRingModeCascadeRingType	     Integer32,
       hwEntRingModeInitRingType	     Integer32,
       hwEntRingModeRowStatus	         RowStatus
       
     }
 
   hwEntRingModeMgId OBJECT-TYPE
     SYNTAX      Integer32(0..33554431)
     MAX-ACCESS  not-accessible
     STATUS      current
     DESCRIPTION
         "
         Indicates the MG ID.
         The range of ID from 0 to 16777215 is for AG system, value of 33554431 is only for PBX system and the value input from 16777215 to 33554431 is invalid.
         "
     ::= { hwEntRingModeEntry 1 }
 
   hwEntRingModeIndex OBJECT-TYPE
     SYNTAX      Integer32(0..15)
     MAX-ACCESS  not-accessible
     STATUS      current
     DESCRIPTION
         "
         Indicates the ring mode index.
         "
     ::= { hwEntRingModeEntry 2 }
     
   hwEntRingModeName OBJECT-TYPE
     SYNTAX      DisplayString(SIZE (0..32))
     MAX-ACCESS  read-create
     STATUS      current
     DESCRIPTION
         "
         Indicates the ring mode name.
         "
     ::= { hwEntRingModeEntry 3 }
 
   hwEntRingModeCascadeRingType OBJECT-TYPE
     SYNTAX      Integer32(0..3|6|8..15|128..143|255)
     MAX-ACCESS  read-create
     STATUS      current
     DESCRIPTION
         "
         Indicates the cadence ringing type.
          0: Normal ring 1:4
          1: Special ring 1:2
          2: Special ring 0.4:0.2:0.4:4
          3: Long ring
          6: Special ring 1.2:2
          8: HK ring 1:3
          9: HK CNTRX 0.4:0.2:0.4:0.2:0.4:3.0
         10: HK DN-A 0.4:0.2:0.4:3.0
         11: HK ACB 0.4:0.2
         12: HK reminder ring (one tone every 0.4 second; one tone)
         13: HK DN-B 1.2:3 
         14: CNTRX-IN 0.4:0.2:0.4:0.2:0.4:2.6
         15: Egypt long-distance ring 2:1
         128-143: user defined ring mode 0-15
         255: Null
         "
     ::= { hwEntRingModeEntry 4 }
 
   hwEntRingModeInitRingType OBJECT-TYPE
     SYNTAX      Integer32(4|17..18|22|24..26|29..31|144..159|255)
     MAX-ACCESS  read-create
     STATUS      current
     DESCRIPTION
         "
         Indicates the initial ringing type.
          4: Normal ring (FSK) 1:4
         17: Special ring (FSK) 1:2 
         18: Special ring (FSK) 0.4:0.2:0.4:4 
         22: Special ring (FSK) 1.2:2 
         24: HK ring (FSK) 1:3 
         25: HK CNTRX (FSK) 0.4:0.2:0.4:0.2:0.4:3.0 
         26: HK DN-A (FSK) 0.4:0.2:0.4:3.0 
         29: HK DN-B (FSK) 1.2:3 
         30: CNTRX-IN (FSK) 0.4:0.2:0.4:0.2:0.4:2.6 
         31: Egypt long-distance ring (FSK) 2:1 
         144-159: user defined FSK ring mode 0-15
         255: Null
         "
     ::= { hwEntRingModeEntry 5 }
 
   hwEntRingModeRowStatus OBJECT-TYPE
     SYNTAX      RowStatus
     MAX-ACCESS  read-create
     STATUS      current
     DESCRIPTION
         "
         Indicates the row status (the SIP supports only 4 and 6).
         Options:
         active(1)
     	 notInService(2)
         notReady(3)
         createAndGo(4)
         createAndWait(5)
         destroy(6)
         "
     ::= { hwEntRingModeEntry 6 }
     
--==

  hwEntSipStackParametersTable OBJECT IDENTIFIER ::= {  hwEntVoiceCommonMIB 4  }

  hwEntSipStackParaServer OBJECT-TYPE
    SYNTAX      OCTET STRING(SIZE (0..64))
    MAX-ACCESS  read-write
    STATUS      current
    DESCRIPTION
        "
        The head-field of Server.
        "
    ::= { hwEntSipStackParametersTable 1 }

  hwEntSipStackParaOrganization  OBJECT-TYPE
    SYNTAX      OCTET STRING(SIZE (0..64))
    MAX-ACCESS  read-write
    STATUS      current
    DESCRIPTION
        "
        The head-field of Organization.
        "
    ::= { hwEntSipStackParametersTable 2 }

  hwEntSipStackParaUserAgent  OBJECT-TYPE
    SYNTAX      OCTET STRING(SIZE (0..64))
    MAX-ACCESS  read-write
    STATUS      current
    DESCRIPTION
        "
        The head-field of UserAgent.
        "
    ::= { hwEntSipStackParametersTable 3 }

  hwEntSipStackParaMaxForwards   OBJECT-TYPE
    SYNTAX      Integer32(0..255)
    MAX-ACCESS  read-write
    STATUS      current
    DESCRIPTION
        "
        The MaxForwards parameter of SipStack.
        Default: 70
        "
    ::= { hwEntSipStackParametersTable 4 }

  hwEntSipStackParaT1   OBJECT-TYPE
    SYNTAX      Integer32(200..10000)
    MAX-ACCESS  read-write
    STATUS      current
    DESCRIPTION
        "
        The T1 timer(Round-Trip timer) of SipStack.
        Default: 500
        Unit: ms
        "
    ::= { hwEntSipStackParametersTable 5 }

  hwEntSipStackParaT2   OBJECT-TYPE
    SYNTAX      Integer32(200..10000)
    MAX-ACCESS  read-write
    STATUS      current
    DESCRIPTION
        "
        The T2 timer of SipStack(The maximum length of retransmission for non-invite request or invite response).
        Default: 4000
        Unit: ms
        "
    ::= { hwEntSipStackParametersTable 6 }

  hwEntSipStackParaT4   OBJECT-TYPE
    SYNTAX      Integer32(200..10000)
    MAX-ACCESS  read-write
    STATUS      current
    DESCRIPTION
        "
        The T4 timer of SipStack(The maximum length of message transmission in the network).
        Default: 5000
        Unit: ms
        "
    ::= { hwEntSipStackParametersTable 7 }

  hwEntSipStackParaTD   OBJECT-TYPE
    SYNTAX      Integer32(0..300000)
    MAX-ACCESS  read-write
    STATUS      current
    DESCRIPTION
        "
        The D timer of SipStack(The maximum length of message retransmission for getting a response).
        Default: 32000
        Unit: ms
        "
    ::= { hwEntSipStackParametersTable 8 }

  hwEntSipStackParaMinSE   OBJECT-TYPE
    SYNTAX      Integer32(90..65535)
    MAX-ACCESS  read-write
    STATUS      current
    DESCRIPTION
        "
        The timer for Minimum of Session-Expires.
        Default: 90
        Unit: second
        "
    ::= { hwEntSipStackParametersTable 9 }

  hwEntSipStackParaSessionProgress   OBJECT-TYPE
    SYNTAX      Integer32(0..65535)
    MAX-ACCESS  read-write
    STATUS      current
    DESCRIPTION
        "
        The length of retransmission for SessionProgress.
        Default: 180
        Unit: second
        "
    ::= { hwEntSipStackParametersTable 10 }

  hwEntSipStackParaSessionRelProgress   OBJECT-TYPE
    SYNTAX      Integer32(0..65535)
    MAX-ACCESS  read-write
    STATUS      current
    DESCRIPTION
        "
        The length of retransmission for SessionRelProgress.
        Default: 60
        Unit: second
        "
    ::= { hwEntSipStackParametersTable 11 }

  hwEntSipStackParaEntityBasedSessionsTimerFlag   OBJECT-TYPE
    SYNTAX      INTEGER{enable(1), disable(2)}
    MAX-ACCESS  read-write
    STATUS      current
    DESCRIPTION
        "
        This flag indicates that whether the Sessions Timer based on UA-Entity.
        Options:
        enable(1)   -Sessions Timer based on UA-Entity
        disable(2)  -Sessions Timer not based on UA-Entity
        Default: disable(2)
        "
    ::= { hwEntSipStackParametersTable 12 }

  hwEntSipStackParaHeaderFoldFlag   OBJECT-TYPE
    SYNTAX      INTEGER{enable(1), disable(2)}
    MAX-ACCESS  read-write
    STATUS      current
    DESCRIPTION
        "
        Indicates that whether the authentication header field is folded.
        Options:
        enable(1)
        disable(2)
        Default: disable(2)
        "
    ::= { hwEntSipStackParametersTable 13 }

  hwEntSipStackParaToHeaderCheckFlag    OBJECT-TYPE
    SYNTAX      INTEGER{enable(1), disable(2)}
    MAX-ACCESS  read-write
    STATUS      current
    DESCRIPTION
        "
        Indicates that whether to check to header.
        Options:
        enable(1)
        disable(2)
        Default: disable(2)
        "
    ::= { hwEntSipStackParametersTable 14 }

--==

  hwEntDspAttributeTable OBJECT IDENTIFIER ::= {  hwEntVoiceCommonMIB 5  }
  
  hwEntDspFaxMaxTrainRate OBJECT-TYPE
    SYNTAX      INTEGER{v17(1), v29(2), v27(3)}            
    MAX-ACCESS  read-write
    STATUS      current
    DESCRIPTION
      " 
      Indicates the maximum fax training rate.
      Options:
      v17(1)
      v29(2)
      v27(3)
      Default: v17(1)
      "
    ::= { hwEntDspAttributeTable 1 }
 
  hwEntDspFaxTrainMode OBJECT-TYPE
    SYNTAX      INTEGER{e2e(1), local(2)}
    MAX-ACCESS  read-write
    STATUS      current
    DESCRIPTION
      " 
      Indicates the fax training mode.
      Options:
      e2e(1)
      local(2)
      Default: e2e(1)
      "
    ::= { hwEntDspAttributeTable 2 }  
       
  hwEntDspCodeType OBJECT-TYPE
    SYNTAX      INTEGER{g711a(1),
                        g711u(2),
                        g723(3),
                        g729(4),
                        g726by16k(5),
                        g726by24k(6),
                        g726by32k(7),
                        g726by40k(8)
                        }
    MAX-ACCESS  read-write
    STATUS      current
    DESCRIPTION
      " 
      Indicates the default coding type of DSP channel.
      Options:
      g711A(1)
      g711u(2)
      g723(3)
      g729(4)
      g726by16k(5)
      g726by24k(6)
      g726by32k(7)
      g726by40k(8)
      Default: g711A(1)
      "
    ::= { hwEntDspAttributeTable 3 }  
      
  hwEntDspRtcpPackageSendInterval OBJECT-TYPE
    SYNTAX      Integer32(0..65535)
    MAX-ACCESS  read-write
    STATUS      current
    DESCRIPTION
      " 
      Indicates the RTCP packet sending interval of DSP channel. 
      The valid value must be no less than 500, 0 indicates that the parameter is disabled.
      Default: 5000
      Unit: ms
      "
    ::= { hwEntDspAttributeTable 4 }  
     
  hwEntDspRtpPacketInterval OBJECT-TYPE
    SYNTAX      INTEGER{pt5ms(1), pt10ms(2), pt20ms(3), pt30ms(4)}
    MAX-ACCESS  read-write
    STATUS      current
    DESCRIPTION
      " 
      Indicates the default RTP packet time of DSP channel.
      Options:
      1. pt5ms(1)  
      2. pt10ms(2)
      3. pt20ms(3)
      4. pt30ms(4)
      Default: pt20ms(3) 
      "
    ::= { hwEntDspAttributeTable 5 }   
    
  hwEntDspEchoCheck OBJECT-TYPE
    SYNTAX      INTEGER{enable(1), disable(2)}
    MAX-ACCESS  read-write
    STATUS      current
    DESCRIPTION
      " 
      Indicates whether to enable echo check of DSP channel.
      Options:
      enable(1)
      disable(2)
      Default: enable(1)
      "
    ::= { hwEntDspAttributeTable 6 }     
    
  hwEntDspSilenceReduce OBJECT-TYPE
    SYNTAX      INTEGER{enable(1), disable(2)}
    MAX-ACCESS  read-write
    STATUS      current
    DESCRIPTION
      " 
      Indicates whether to enable silence compression of DSP channel.
      Options:
      enable(1)
      disable(2)
      Default: disable(2)
      "
    ::= { hwEntDspAttributeTable 7 }  
    
    
  hwEntDspClearmodePayload OBJECT-TYPE
    SYNTAX      Integer32(96..127)
    MAX-ACCESS  read-write
    STATUS      current
    DESCRIPTION
      " 
      Indicates the default payload type of the DSP channel clearmode (it must not conflict with the payload used).
      Default: 100
      "
    ::= { hwEntDspAttributeTable 8 }  
     
  hwEntDspSevereDegradethreshold  OBJECT-TYPE
    SYNTAX      Integer32(1..65535)
    MAX-ACCESS  read-write
    STATUS      current
    DESCRIPTION
      " 
      Indicates the default threshold of severely packet loss seconds.
      Default: 400 
      "
    ::= { hwEntDspAttributeTable 9 }    
      
  hwEntDspBvqm         OBJECT-TYPE
    SYNTAX      INTEGER{enable(1),disable(2)}
    MAX-ACCESS  read-write
    STATUS      current
    DESCRIPTION
      " 
      Indicates the VQM switch. 
      Options:
      enable(1)
      disable(2)
      Default: disable(2)
      "
    ::= { hwEntDspAttributeTable 10 } 
    
  hwEntDspPlc OBJECT-TYPE
    SYNTAX      INTEGER{enable(1), disable(2)}
    MAX-ACCESS  read-write
    STATUS      current
    DESCRIPTION
      " 
      Indicates the DSP packet loss compensation algorithm.
      Options:
      enable(1)
      disable(2)
      Default: disable(2)
      "
    ::= { hwEntDspAttributeTable 11 }       
    
    hwEntDspMinAdaptJitterBuffer OBJECT-TYPE
    SYNTAX      Integer32(0..150)            
    MAX-ACCESS  read-write
    STATUS      current
    DESCRIPTION
      " 
      Minimum adapt jitterbuffer of DSP. MinAdaptJitterBuffer<=InitAdaptJitterBuffer<=MaxAdaptJitterBuffer and the MinAdaptJitterBuffer<ThresholdJitterBuffer.
      Default: 2
      Unit: ms
      "
    ::= { hwEntDspAttributeTable 12 }
 
  hwEntDspMaxAdaptJitterBuffer OBJECT-TYPE
    SYNTAX      Integer32(0..150)            
    MAX-ACCESS  read-write
    STATUS      current
    DESCRIPTION
      " 
      Maximum adapt jitterbuffer of DSP. MinAdaptJitterBuffer<=InitAdaptJitterBuffer<=MaxAdaptJitterBuffer and the MinAdaptJitterBuffer<ThresholdJitterBuffer.
      Default: 135
      Unit: ms
      "
    ::= { hwEntDspAttributeTable 13 }
  
  hwEntDspInitAdaptJitterBuffer OBJECT-TYPE
    SYNTAX      Integer32(0..150)          
    MAX-ACCESS  read-write
    STATUS      current
    DESCRIPTION
      " 
      Initial adapt jitterbuffer of DSP. MinAdaptJitterBuffer<=InitAdaptJitterBuffer<=MaxAdaptJitterBuffer and the MinAdaptJitterBuffer<ThresholdJitterBuffer.
      Default: 2
      Unit: ms
      "
    ::= { hwEntDspAttributeTable 14 }
  
  hwEntDspMinFixedJitterBuffer OBJECT-TYPE
    SYNTAX      Integer32(0..150)            
    MAX-ACCESS  read-write
    STATUS      current
    DESCRIPTION
      " 
      Minimum fixed jitterbuffer of DSP. MinFixedJitterBuffer<=NormalFixedJitterBuffer<=MaxFixedJitterBuffer.
      Default: 2
      Unit: ms
      "
    ::= { hwEntDspAttributeTable 15 }
    
  hwEntDspMaxFixedJitterBuffer OBJECT-TYPE
    SYNTAX      Integer32(0..150)            
    MAX-ACCESS  read-write
    STATUS      current
    DESCRIPTION
      " 
      Maximum fixed jitterbuffer of DSP. MinFixedJitterBuffer<=NormalFixedJitterBuffer<=MaxFixedJitterBuffer.
      Default: 135
      Unit: ms
      "
    ::= { hwEntDspAttributeTable 16 }
    
  hwEntDspNormalFixedJitterBuffer OBJECT-TYPE
    SYNTAX      Integer32(0..150)            
    MAX-ACCESS  read-write
    STATUS      current
    DESCRIPTION
      " 
      Initial fixed jitterbuffer of DSP. MinFixedJitterBuffer<=NormalFixedJitterBuffer<=MaxFixedJitterBuffer.
      Default: 60
      Unit: ms
      "
    ::= { hwEntDspAttributeTable 17 }
    
  hwEntDspRedundancyPayload OBJECT-TYPE
    SYNTAX      Integer32(96..127)
    MAX-ACCESS  read-write
    STATUS      current
    DESCRIPTION
      " 
      Indicates the payload type value of redundancy (it must not conflict with the payload used).
      Default: 96
      "
    ::= { hwEntDspAttributeTable 18 }
      
  hwEntDspRedundancyT30 OBJECT-TYPE
    SYNTAX      Integer32(0..7)
    MAX-ACCESS  read-write
    STATUS      current
    DESCRIPTION
      " 
      Indicates the T30 redundancy parameter of T38 Fax.
      Default: 3
      "
    ::= { hwEntDspAttributeTable 19 } 
    
  hwEntDspRedundancyT4 OBJECT-TYPE
    SYNTAX      Integer32(0..3)
    MAX-ACCESS  read-write
    STATUS      current
    DESCRIPTION
      " 
      Indicates the T4 redundancy parameter of T38 Fax.
      Default: 3
      "
    ::= { hwEntDspAttributeTable 20 } 
    
  hwEntDspFaxV8Negotiate OBJECT-TYPE
    SYNTAX      INTEGER{enable(1), disable(2)}
    MAX-ACCESS  read-write
    STATUS      current
    DESCRIPTION
        "
        Indicates the switch of the V8 negotiation of FAX.
        Options:
        enable(1)
        disable(2)
        Default: disable(2)
        "
    ::= { hwEntDspAttributeTable 21 }
    
  hwEntDspRTCPXR OBJECT-TYPE
    SYNTAX      INTEGER{enable(1), disable(2)}            
    MAX-ACCESS  read-write
    STATUS      current
    DESCRIPTION
      " 
      The switch of RTCP XR.
      Options:
      enable(1)   -enable RTCP XR
      disable(2)  -disable RTCP XR
      Default: enable(1)
      "
    ::= { hwEntDspAttributeTable 22 }        
     
  hwEntDspVbdPayload OBJECT-TYPE
    SYNTAX      Integer32(96..127)
    MAX-ACCESS  read-write
    STATUS      current
    DESCRIPTION
      " 
      Indicates the payload type value of VBD (it must not conflict with the payload used). 
      Default: 102
      "
    ::= { hwEntDspAttributeTable 23 }      
    
  hwEntDspRfcNtePayload OBJECT-TYPE
    SYNTAX      Integer32(96..127)
    MAX-ACCESS  read-write
    STATUS      current
    DESCRIPTION
      " 
      Indicates the payload type value of nte (it must not conflict with the payload used). 
      Default: 97
      "
    ::= { hwEntDspAttributeTable 24 }
    
  hwEntDspG726R16kPayload OBJECT-TYPE
    SYNTAX      Integer32(96..127)
    MAX-ACCESS  read-write
    STATUS      current
    DESCRIPTION
      " 
      Indicates the payload type value of G.726-16k (it must not conflict with the payload used).
      Default: 103
      "
    ::= { hwEntDspAttributeTable 25 } 
    
  hwEntDspG726R24kPayload OBJECT-TYPE
    SYNTAX      Integer32(96..127)
    MAX-ACCESS  read-write
    STATUS      current
    DESCRIPTION
      " 
      Indicates the payload type value of G.726-24k (it must not conflict with the payload used).
      Default: 104
      "
    ::= { hwEntDspAttributeTable 26 } 
            
  hwEntDspG726R32kPayload OBJECT-TYPE
    SYNTAX      Integer32(96..127)
    MAX-ACCESS  read-write
    STATUS      current
    DESCRIPTION
      " 
      Indicates the payload type value of G.726-32k (it must not conflict with the payload used).
      Default: 101
      "
    ::= { hwEntDspAttributeTable 27 }    
    
  hwEntDspG726R40kPayload OBJECT-TYPE
    SYNTAX      Integer32(96..127)
    MAX-ACCESS  read-write
    STATUS      current
    DESCRIPTION
      " 
      Indicates the payload type value of G.726-40k (it must not conflict with the payload used).
      Default: 105
      "
    ::= { hwEntDspAttributeTable 28 } 

 hwEntDspAutoVBDSwitchMode OBJECT-TYPE
    SYNTAX      INTEGER{hostControl(1), autoSwitch(2)}
    MAX-ACCESS  read-write
    STATUS      current
    DESCRIPTION
      " 
      VBD switch mode.
      Options:
      1. hostControl(1)  -host control
      2. autoSwitch(2)   -auto switch
      Default: hostControl(1)
      "
    ::= { hwEntDspAttributeTable 29 } 
    
 hwEntDspAlarmAdaptJitterBuffer OBJECT-TYPE
    SYNTAX      Integer32(0..150) 
    MAX-ACCESS  read-write
    STATUS      current
    DESCRIPTION
      " 
      Adapt jitterbuffer of DSP alarm threshold.
      Default: 150
      Unit: ms
      "
    ::= { hwEntDspAttributeTable 30 }     
    
--==
 
    hwEntDspTemplateTable OBJECT-TYPE
     SYNTAX      SEQUENCE OF HwEntDspTemplateEntry
     MAX-ACCESS  not-accessible
     STATUS      current
     DESCRIPTION
       "
       This table is used to config the dsp parameters template.
       The index of this table is hwEntDspTemplateName.
       "
     ::= { hwEntVoiceCommonMIB 6 }
 
   hwEntDspTemplateEntry OBJECT-TYPE
     SYNTAX      HwEntDspTemplateEntry
     MAX-ACCESS  not-accessible
     STATUS      current
     DESCRIPTION
       "
       This table is used to config the dsp parameters template.
       The index of this entry is hwEntDspTemplateName.
       "
     INDEX    {  
               hwEntDspTemplateName
              }
     ::= { hwEntDspTemplateTable 1 }
 
   HwEntDspTemplateEntry ::=
     SEQUENCE
     {
       hwEntDspTemplateName  	        DisplayString,
       hwEntDspEc                       INTEGER,
       hwEntDspJbMode                   INTEGER,
       hwEntDspNlp                      INTEGER,
       hwEntDspWorkMode                 INTEGER,
       hwEntDspSc                       INTEGER, 
       hwEntDspInputGain                Integer32, 
       hwEntDspOutputGain               Integer32,
       hwEntDspDtmfPara                 INTEGER,
       hwEntDspNteForDataevent          INTEGER,
       hwEntDspSpecialFlow              Integer32,
       hwEntDspRedundancyForVbd         INTEGER,
       hwEntDspTemplateRowStatus        RowStatus
     }
 
   hwEntDspTemplateName OBJECT-TYPE
     SYNTAX      DisplayString(SIZE(1..31))
     MAX-ACCESS  not-accessible
     STATUS      current
     DESCRIPTION
         "
         Indicates the dsp parameters template name.
         "
     ::= { hwEntDspTemplateEntry 1 }
  
  hwEntDspEc OBJECT-TYPE
     SYNTAX      INTEGER{enable(1), disable(2), globalConfig(255)}
     MAX-ACCESS  read-create
     STATUS      current
     DESCRIPTION
         "
         Indicates the echo cotrol. 
         Options:
         enable(1)         -open 
         disable(2)        -close 
         globalConfig(255) -using global config
         Default: globalConfig(255)
         "
     ::= { hwEntDspTemplateEntry 2 } 
    
  hwEntDspJbMode OBJECT-TYPE
     SYNTAX      INTEGER{dynamic(1), static(2), globalConfig(255)}
     MAX-ACCESS  read-create
     STATUS      current
     DESCRIPTION
         "
         Indicates the jitterbuffer mode. 
         Options:
         dynamic(1)         -dynamic mode 
         static(2)           -static mode 
         globalConfig(255)  -use global config
         Default: globalConfig(255)
         "
     ::= { hwEntDspTemplateEntry 3 } 

  hwEntDspNlp OBJECT-TYPE
     SYNTAX      INTEGER{close(1), normal(2), enhanced(3), globalConfig(255)}
     MAX-ACCESS  read-create
     STATUS      current
     DESCRIPTION
         "
         Indicates the NLP mode. 
         Options:
         close(1)           -close 
         normal(2)          -normal mode 
         enhanced(3)        -enhanced mode 
         globalConfig(255)  -use global config
         Default: globalConfig(255)
         "
     ::= { hwEntDspTemplateEntry 4 } 
     
  hwEntDspWorkMode OBJECT-TYPE
     SYNTAX      INTEGER{voice(1), fax(2), modem(3), globalConfig(255)}
     MAX-ACCESS  read-create
     STATUS      current
     DESCRIPTION
         "
         Indicates the dsp workmode. 
         Options:
         voice(1)           -voice mode 
         fax(2)             -fax mode 
         modem(3)           -modem mode 
         globalConfig(255)  -use global config
         Default: globalConfig(255)
         "
     ::= { hwEntDspTemplateEntry 5 } 

  hwEntDspSc OBJECT-TYPE
     SYNTAX      INTEGER{enable(1), disable(2),globalConfig(255)}
     MAX-ACCESS  read-create
     STATUS      current
     DESCRIPTION
         "
         Indicates the silence cotrol. 
         Options:
         enable(1)          -open 
         disable(2)         -close 
         globalConfig(255)  -use global config
         Default: globalConfig(255)
         "
     ::= { hwEntDspTemplateEntry 6 } 
         
  hwEntDspInputGain OBJECT-TYPE
     SYNTAX      Integer32(0..15|255)
     MAX-ACCESS  read-create
     STATUS      current
     DESCRIPTION
         " 
         Indicates the input gain of DSP chip:  
         0-15  -correspond to -10 dB to +5 dB
         255   -use global config
         Default: 255
         "
     ::= { hwEntDspTemplateEntry 7 }
     
  hwEntDspOutputGain OBJECT-TYPE
     SYNTAX      Integer32(0..20|255)
     MAX-ACCESS  read-create
     STATUS      current
     DESCRIPTION
         " 
         Indicates the output gain of DSP chip:
         0-20  -correspond to -10 dB to +10 dB;
         255   -use global config
         Default: 255.
         "
    ::= { hwEntDspTemplateEntry 8 }    
     
  hwEntDspDtmfPara OBJECT-TYPE
    SYNTAX      INTEGER{globalConfig(1), nte(2), erase(3), nteWithRedundancy(4)}           
    MAX-ACCESS  read-create
    STATUS      current
    DESCRIPTION
      "
      Indicates the transmission mode of DTMF. 
      Options:
      globalConfig(1)       -use global config
      nte(2)                -nte transmission
      erase(3)              -erase DTMF
      nteWithRedundancy(4)  -nte with redundancy
      Default: globalConfig(1)
      "
    ::= { hwEntDspTemplateEntry 9 }  
    
  hwEntDspNteForDataevent OBJECT-TYPE
    SYNTAX      INTEGER{enable(1), globalConfig(2)}           
    MAX-ACCESS  read-create
    STATUS      current
    DESCRIPTION
      "
      Indicates the mode of sending fax/modem event.
      Options:
      enable(1)        -enable NTE for Dataevent
      globalConfig(2)  -use global config
      Default: globalConfig(2)
      "
    ::= { hwEntDspTemplateEntry 10 }  
    
  hwEntDspSpecialFlow OBJECT-TYPE
    SYNTAX      Integer32(0..255)         
    MAX-ACCESS  read-create
    STATUS      current
    DESCRIPTION
      "
      Indicates the dsp special flow.
      0: intelligent telephone special flow: filter RTP messages and only processs nte messages
      1: intelligent telephone special flow: only processs DTMF events in nte messages
      2-254: reserved values
      255: no dsp special flow
      Default: 255
      "
    ::= { hwEntDspTemplateEntry 11 }  
    
  hwEntDspRedundancyForVbd OBJECT-TYPE
    SYNTAX      INTEGER{globalConfig(1), enable(2)}          
    MAX-ACCESS  read-create
    STATUS      current
    DESCRIPTION
      "
      Flag of locally starting the redundancy VBD function.
      Options:
      globalConfig(1)  -use global config
      enable(2)        -enable redundancy for vbd      
      Default: globalConfig(1)
      "
    ::= { hwEntDspTemplateEntry 12 }   
    
 hwEntDspTemplateRowStatus OBJECT-TYPE
   SYNTAX      RowStatus
   MAX-ACCESS  read-create
   STATUS      current
   DESCRIPTION
       "
       Indicates the row status.
       Options:
       active(1)
   	   notInService(2)
       notReady(3)
       createAndGo(4)
       createAndWait(5)
       destroy(6)
       "
   ::= { hwEntDspTemplateEntry 13 }
    
--==
    
   hwEntServiceNumTable OBJECT-TYPE
     SYNTAX      SEQUENCE OF HwEntServiceNumEntry
     MAX-ACCESS  not-accessible
     STATUS      current
     DESCRIPTION
       "
       This table is used to config the binding between service number and DSP parameters template.
       The index of this table is hwEntServiceNumMap.
       "
     ::= { hwEntVoiceCommonMIB 7 }
 
   hwEntServiceNumEntry OBJECT-TYPE
     SYNTAX      HwEntServiceNumEntry
     MAX-ACCESS  not-accessible
     STATUS      current
     DESCRIPTION
       "
       This table is used to config the binding between service number and DSP parameters template.
       The index of this entry is hwEntServiceNumMap.
       "
     INDEX    {  
               hwEntServiceNumMap
              }
     ::= { hwEntServiceNumTable 1 }
 
   HwEntServiceNumEntry ::=
     SEQUENCE
     {
       hwEntServiceNumMap  	               DisplayString,
       hwEntServiceNumDspTemplate  	       DisplayString,
       hwEntServiceNumRowStatus            RowStatus
     }
 
   hwEntServiceNumMap OBJECT-TYPE
     SYNTAX      DisplayString(SIZE(1..64))
     MAX-ACCESS  not-accessible
     STATUS      current
     DESCRIPTION
         "
         Indicates the service number digital map.
         "
     ::= { hwEntServiceNumEntry 1 }
 
   hwEntServiceNumDspTemplate OBJECT-TYPE
     SYNTAX      DisplayString(SIZE(1..31))
     MAX-ACCESS  read-create
     STATUS      current
     DESCRIPTION
         "
         Indicates the dsp parameters template name
         "
     ::= { hwEntServiceNumEntry 2 }
  
  hwEntServiceNumRowStatus OBJECT-TYPE
     SYNTAX      RowStatus
     MAX-ACCESS  read-create
     STATUS      current
     DESCRIPTION
         "
         Indicates the row status.
         Options:
         active(1)
     	 notInService(2)
         notReady(3)
         createAndGo(4)
         createAndWait(5)
         destroy(6)
         "
     ::= { hwEntServiceNumEntry 3 } 

--==   
  
   hwEntDspOperTable OBJECT-TYPE
     SYNTAX      SEQUENCE OF HwEntDspOperEntry
     MAX-ACCESS  not-accessible
     STATUS      current
     DESCRIPTION
         "
         This table is used to config the operation of DSP channel.
         The index of this table are hwEntDspDimmIndex, hwEntDspChannelIndex.
         "
     ::= { hwEntVoiceCommonMIB 8 }
 
   hwEntDspOperEntry OBJECT-TYPE
     SYNTAX      HwEntDspOperEntry
     MAX-ACCESS  not-accessible
     STATUS      current
     DESCRIPTION
         "
         This table is used to config the operation of DSP channel.
         The index of this entry are hwEntDspDimmIndex, hwEntDspChannelIndex.
         "
     INDEX    {  
               hwEntDspDimmIndex,
               hwEntDspChannelIndex
              }
     ::= { hwEntDspOperTable 1 }
 
   HwEntDspOperEntry ::=
     SEQUENCE
     {
       hwEntDspDimmIndex	            Integer32,
       hwEntDspChannelIndex	            Integer32,
       hwEntDspOperChannelState	        INTEGER,
       hwEntDspOperAdminStatus          INTEGER,
       hwEntDspOperCodec 	            INTEGER,
       hwEntDspOperPacketInterval       Integer32,
       hwEntDspOperJitterBufferMode     INTEGER,
       hwEntDspOperMinJitterBuffer      Integer32,
       hwEntDspOperMaxJitterBuffer      Integer32,
       hwEntDspOperInitJitterBuffer     Integer32,
       hwEntDspOperVAD                  INTEGER,
       hwEntDspOperEC                   INTEGER,
       hwEntDspOperGainOut              Integer32,
       hwEntDspOperGainIn               Integer32,
       hwEntDspOprJBInPercent           Integer32,
       hwEntDspOprIpSideMix             INTEGER,
       hwEntDspOprPcmSideMix            INTEGER
     }
 
   hwEntDspDimmIndex OBJECT-TYPE
     SYNTAX      Integer32
     MAX-ACCESS  not-accessible
     STATUS      current
     DESCRIPTION
         "
         Indicates the  slotid/dsp index.  
         bits 16-31 (16 bits): reserved      
         bits  8-15  (8 bits): slotid index
         bits   0-7  (8 bits): dsp index
         "
     ::= { hwEntDspOperEntry 1 }
     
  hwEntDspChannelIndex OBJECT-TYPE
     SYNTAX      Integer32
     MAX-ACCESS  not-accessible
     STATUS      current
     DESCRIPTION
         "
         Indicates the DSP channel index.
         bits 8-31 (24 bits): reserved
         bits  0-7  (8 bits): channel index
         "
     ::= { hwEntDspOperEntry 2 }
          
   hwEntDspOperChannelState OBJECT-TYPE
     SYNTAX      INTEGER{idle(1), busy(2), wastage(3), fault(4), prohibit(5), pcmLoopback(6), ipLoopback(7)}
     MAX-ACCESS  read-only
     STATUS      current
     DESCRIPTION
         "
         Indicates the channel state. 
         Options:
         idle(1)
         busy(2)
         wastage(3)
         fault(4)
         prohibit(5)
         pcmLoopback(6)
         ipLoopback(7)
         "
     ::= { hwEntDspOperEntry 3 }
   
   hwEntDspOperAdminStatus OBJECT-TYPE
     SYNTAX      INTEGER{prohibit(1), unprohibit(2), pcmLoopback(3), ipLoopback(4), noLoopback(5)}
     MAX-ACCESS  read-write
     STATUS      current
     DESCRIPTION
         "
         Indicates the operation type. 
         Options:
         prohibit(1)     -prohibit
         unprohibit(2)   -unprohibit
         pcmLoopback(3)  -PCM loopback
         ipLoopback(4)   -IP loopback
         noLoopback(5)   -cancel loopback
         "
     ::= { hwEntDspOperEntry 4 }
     
   hwEntDspOperCodec OBJECT-TYPE
     SYNTAX      INTEGER{g711a(1),  
                         g711u(2),
                         g723(3),
                         g729(4),
                         g726by16k(5),
                         g726by24k(6), 
                         g726by32k(7),
                         g726by40k(8),
                         g722(9),
                         null(255)
                         }
     MAX-ACCESS  read-only
     STATUS      current
     DESCRIPTION
         "
         Indicates the codec of DSP.
         Options:
         g711a(1) 
 	     g711u(2) 
 	     g723(3) 
 	     g729(4)
 	     g726by16k(5)
 	     g726by24k(6)
 	     g726by32k(7)
 	     g726by40k(8)
 	     g722(9)
 	     null(255)
         "
     ::= { hwEntDspOperEntry 5 }   
     
   hwEntDspOperPacketInterval OBJECT-TYPE
     SYNTAX      Integer32
     MAX-ACCESS  read-only
     STATUS      current
     DESCRIPTION
         "
         Indicates the packet interval of DSP.
         "
     ::= { hwEntDspOperEntry 6 } 
     
   hwEntDspOperJitterBufferMode OBJECT-TYPE
     SYNTAX      INTEGER{dynamic(1), static(2), null(255)}
     MAX-ACCESS  read-only
     STATUS      current
     DESCRIPTION
         "
         Indicates the jitter buffer mode of DSP.
         Options:
         dynamic(1)
         static(2)
         null(255)
         "
     ::= { hwEntDspOperEntry 7 } 
     
   hwEntDspOperMinJitterBuffer OBJECT-TYPE
     SYNTAX      Integer32
     MAX-ACCESS  read-only
     STATUS      current
     DESCRIPTION
         "
         Indicates the minimum jitterbuffer of DSP.
         "
     ::= { hwEntDspOperEntry 8 }  
     
   hwEntDspOperMaxJitterBuffer OBJECT-TYPE
     SYNTAX      Integer32
     MAX-ACCESS  read-only
     STATUS      current
     DESCRIPTION
         "
         Indicates the maximum jitterbuffer of DSP.
         "
     ::= { hwEntDspOperEntry 9 }  
     
   hwEntDspOperInitJitterBuffer OBJECT-TYPE
     SYNTAX      Integer32
     MAX-ACCESS  read-only
     STATUS      current
     DESCRIPTION
         "
         Indicates the initial jitterbuffer of DSP.
         "
     ::= { hwEntDspOperEntry 10 }  
     
   hwEntDspOperVAD OBJECT-TYPE
     SYNTAX      INTEGER{enable(1), disable(2), null(255)}
     MAX-ACCESS  read-only
     STATUS      current
     DESCRIPTION
         "
         Indicates the switch state of VAD.
         Options:
         enable(1)
         disable(2)
         null(255)
         "
     ::= { hwEntDspOperEntry 11 }  
     
   hwEntDspOperEC OBJECT-TYPE
     SYNTAX      INTEGER{enable(1), disable(2), null(255)}
     MAX-ACCESS  read-only
     STATUS      current
     DESCRIPTION
         "
         Indicates the switch state of echo cancellation.
         Options:
         enable(1)
         disable(2)
         null(255)
         "
     ::= { hwEntDspOperEntry 12 }  
     
   hwEntDspOperGainOut OBJECT-TYPE
     SYNTAX      Integer32
     MAX-ACCESS  read-only
     STATUS      current
     DESCRIPTION
         "
         Indicates the output gain of DSP.
         "
     ::= { hwEntDspOperEntry 13 } 
     
   hwEntDspOperGainIn OBJECT-TYPE
     SYNTAX      Integer32
     MAX-ACCESS  read-only
     STATUS      current
     DESCRIPTION
         "
         Indicates the input gain of DSP.
         "
     ::= { hwEntDspOperEntry 14 }
     
   hwEntDspOprJBInPercent  OBJECT-TYPE
     SYNTAX      Integer32
     MAX-ACCESS  read-only
     STATUS      current
     DESCRIPTION
         "
         Indicates the current fill level of the jitterbuffer in percent.
         "
     ::= { hwEntDspOperEntry 15 } 
     
   hwEntDspOprIpSideMix OBJECT-TYPE
     SYNTAX      INTEGER{noState(1),yesState(2)}
     MAX-ACCESS  read-only
     STATUS      current
     DESCRIPTION
         "
         Indicates the IP side mix state of DSP.
         Options:
         noState(1)
         yesState(2)
         "
     ::= { hwEntDspOperEntry 16 }   
     
   hwEntDspOprPcmSideMix OBJECT-TYPE
     SYNTAX      INTEGER{noState(1),yesState(2)}
     MAX-ACCESS  read-only
     STATUS      current
     DESCRIPTION
         "
         Indicates the PCM side mix state of DSP.
         Options:
         noState(1)
         yesState(2)
         "
     ::= { hwEntDspOperEntry 17 } 
      
--==     

hwEntDspStatisticsTable OBJECT-TYPE
     SYNTAX      SEQUENCE OF HwEntDspStatisticsEntry
     MAX-ACCESS  not-accessible
     STATUS      current
     DESCRIPTION
       "
       This table is used to query the DSP channel statistics.
       The index of this table is hwEntDspDimmIndex.
       "
     ::= { hwEntVoiceCommonMIB 9 }
 
   hwEntDspStatisticsEntry OBJECT-TYPE
     SYNTAX      HwEntDspStatisticsEntry
     MAX-ACCESS  not-accessible
     STATUS      current
     DESCRIPTION
       "
       This table is used to query the DSP channel statistics.
       The index of this entry is hwEntDspDimmIndex.
       "
     INDEX    {  
               hwEntDspDimmIndex
              }
     ::= { hwEntDspStatisticsTable 1 }
 
   HwEntDspStatisticsEntry ::=
     SEQUENCE
     {
       hwEntDspStatisticsTotalNum	    Integer32,
       hwEntDspStatisticsFreeNum	    Integer32,
       hwEntDspStatisticsG711Num	    Integer32,
       hwEntDspStatisticsAllNum         Integer32,
       hwEntDspStatisticsWastageNum	    Integer32,
       hwEntDspStatisticsFaultNum       Integer32,
       hwEntDspStatisticsLoopNum	    Integer32,
       hwEntDspStatisticsForbiddenNum	Integer32          
     }
 
   hwEntDspStatisticsTotalNum OBJECT-TYPE
     SYNTAX      Integer32
     MAX-ACCESS  read-only
     STATUS      current
     DESCRIPTION
         "
         Indicates the total number of DSP channels.
         "
     ::= { hwEntDspStatisticsEntry 1 }
     
   hwEntDspStatisticsFreeNum OBJECT-TYPE
     SYNTAX      Integer32
     MAX-ACCESS  read-only
     STATUS      current
     DESCRIPTION
         "
         Indicates the number of idle channels.
         "
     ::= { hwEntDspStatisticsEntry 2 }
 
   hwEntDspStatisticsG711Num OBJECT-TYPE
     SYNTAX      Integer32
     MAX-ACCESS  read-only
     STATUS      current
     DESCRIPTION
         "
         Indicates the number of occupied DSP channels of the G.711.
         "
     ::= { hwEntDspStatisticsEntry 3 }
 
   hwEntDspStatisticsAllNum OBJECT-TYPE
     SYNTAX      Integer32
     MAX-ACCESS  read-only
     STATUS      current
     DESCRIPTION
         "
         Indicates the number of occupied DSP channels of the full rate.
         "
     ::= { hwEntDspStatisticsEntry 4 }
 
   hwEntDspStatisticsWastageNum OBJECT-TYPE
     SYNTAX      Integer32
     MAX-ACCESS  read-only
     STATUS      current
     DESCRIPTION
         "
         Indicates the number of DSP channels of the wastage.
         "
     ::= { hwEntDspStatisticsEntry 5 }
 
   hwEntDspStatisticsFaultNum OBJECT-TYPE
     SYNTAX      Integer32
     MAX-ACCESS  read-only
     STATUS      current
     DESCRIPTION
         "
         Indicates the number of faulty DSP channels.
         "
     ::= { hwEntDspStatisticsEntry 6 }
 
   hwEntDspStatisticsLoopNum OBJECT-TYPE
     SYNTAX      Integer32
     MAX-ACCESS  read-only
     STATUS      current
     DESCRIPTION
         "
         Indicates the number of DSP channels in the loopback.
         "
     ::= { hwEntDspStatisticsEntry 7 }
 
   hwEntDspStatisticsForbiddenNum OBJECT-TYPE
     SYNTAX      Integer32
     MAX-ACCESS  read-only
     STATUS      current
     DESCRIPTION
         "
         Indicates the number of prohibited DSP channels.
         "
     ::= { hwEntDspStatisticsEntry 8 }                     
   
--==

 hwEntDspOverloadResourceTable OBJECT IDENTIFIER ::= {  hwEntVoiceCommonMIB 10  }

  hwEntDspResourceWorkMode OBJECT-TYPE
    SYNTAX      INTEGER{normal(1), priority(2)}           
    MAX-ACCESS  read-write
    STATUS      current
    DESCRIPTION
      "
      Indicates whether to restrict calls in case of insufficient DSP resource, when many calls raised. 
      Options:
      normal(1)
      priority(2)
      Default: normal(1)
      "
         ::= { hwEntDspOverloadResourceTable 1 }
  
  hwEntDspResourcethreshold1 OBJECT-TYPE
    SYNTAX      Integer32(0..100)           
    MAX-ACCESS  read-write
    STATUS      current
    DESCRIPTION
      "
      Indicates the normal call will use the max threshold of the whole DSP resource. 
      The value of hwEntDspResourcethreshold1 must be smaller than or equal to the hwEntDspResourcethreshold2.
      Default: 100
      Unit: 1/100
      "
         ::= { hwEntDspOverloadResourceTable 2 }  
    
  hwEntDspResourcethreshold2 OBJECT-TYPE
    SYNTAX      Integer32(0..100)           
    MAX-ACCESS  read-write
    STATUS      current
    DESCRIPTION
      "
      Indicates the max threshold of the whole DSP resource which used for the prior user. 
      The value of hwEntDspResourcethreshold2 must be smaller than or equal to the hwEntDspResourcethreshold3.
      Default: 100
      Unit: 1/100
      "
         ::= { hwEntDspOverloadResourceTable 3 }  
         
  hwEntDspResourcethreshold3 OBJECT-TYPE
    SYNTAX      Integer32(0..100)           
    MAX-ACCESS  read-write
    STATUS      current
    DESCRIPTION
      "
      Indicates the max threshold of the whole DSP resource which used for the high prior user. 
      Unit: 1/100
      Default: 100
      "
         ::= { hwEntDspOverloadResourceTable 4 }  
     
--==
     
 hwEntBandwidthParaTable OBJECT IDENTIFIER ::= {  hwEntVoiceCommonMIB 11  }
           
  hwEntBandwidthSupport OBJECT-TYPE
    SYNTAX      INTEGER{enable(1),disable (2)}           
    MAX-ACCESS  read-write
    STATUS      current
    DESCRIPTION
      "
      Indicates whether to restrict calls in case of insufficient bandwidth.
      Options:
      1. enable(1)   -support
      2. disable(2)  -not support
      Default: disable(2)
      "
         ::= { hwEntBandwidthParaTable 1 }
  
  hwEntBandwidthMax OBJECT-TYPE
    SYNTAX      Integer32(2..1000)           
    MAX-ACCESS  read-write
    STATUS      current
    DESCRIPTION
      "
      Indicates the value of the maximum upstream bandwidth.
      Default: 1000
      Unit: 100 kbit/s
      "
         ::= { hwEntBandwidthParaTable 2 }  
    
  hwEntBandwidthReserved OBJECT-TYPE
    SYNTAX      Integer32(1..999)           
    MAX-ACCESS  read-write
    STATUS      current
    DESCRIPTION
      "
      Indicates the value of the bandwidth reserved for emergency calls. 
      Default: 10
      Unit: 100 kbit/s
      "
    ::= { hwEntBandwidthParaTable 3 }    
     
--==

  hwEntClipParaTable OBJECT IDENTIFIER ::= {  hwEntVoiceCommonMIB 12  }

  hwEntClipOnHookDualToneAlertLevel OBJECT-TYPE
    SYNTAX      Integer32(0..15)
    MAX-ACCESS  read-write
    STATUS      current
    DESCRIPTION
        "
        Indicates the power of dual tone alert in onhook state.
        Support 16 electric:
         0: -5.5dBm0
         1: -6.5dBm0
         2: -7.5dBm0
         3: -8.5dBm0
         4: -9.5dBm0
         5: -10.5dBm0
         6: -11.5dBm0
         7: -12.5dBm0
         8: -13.5dBm0
         9: -14.5dBm0
        10: -15.5dBm0
        11: -16.5dBm0
        12: -17.5dBm0
        13: -18.5dBm0
        14: -19.5dBm0
        15: -20.5dBm0
        Default: 3
        "
    ::= { hwEntClipParaTable 1 }

  hwEntClipOnHookFskLevel OBJECT-TYPE
    SYNTAX      Integer32(0..15)
    MAX-ACCESS  read-write
    STATUS      current
    DESCRIPTION
        "
        Indicates the power of FSK level in onhook state.
        Support 16 electric:
         0: -5.5dBm0
         1: -6.5dBm0
         2: -7.5dBm0
         3: -8.5dBm0
         4: -9.5dBm0
         5: -10.5dBm0
         6: -11.5dBm0
         7: -12.5dBm0
         8: -13.5dBm0
         9: -14.5dBm0
        10: -15.5dBm0
        11: -16.5dBm0
        12: -17.5dBm0
        13: -18.5dBm0
        14: -19.5dBm0
        15: -20.5dBm0
        Default: 3
        "
    ::= { hwEntClipParaTable 2 }

  hwEntClipOffHookDualToneAlertLevel OBJECT-TYPE
    SYNTAX      Integer32(0..15)
    MAX-ACCESS  read-write
    STATUS      current
    DESCRIPTION
        "
        Indicates the power of dual tone alert in offhook state.
        Support 16 electric:
         0: -5.5dBm0
         1: -6.5dBm0
         2: -7.5dBm0
         3: -8.5dBm0
         4: -9.5dBm0
         5: -10.5dBm0
         6: -11.5dBm0
         7: -12.5dBm0
         8: -13.5dBm0
         9: -14.5dBm0
        10: -15.5dBm0
        11: -16.5dBm0
        12: -17.5dBm0
        13: -18.5dBm0
        14: -19.5dBm0
        15: -20.5dBm0
        Default: 10
        "
    ::= { hwEntClipParaTable 3 }

  hwEntClipOffHookFskLevel OBJECT-TYPE
    SYNTAX      Integer32(0..15)
    MAX-ACCESS  read-write
    STATUS      current
    DESCRIPTION
        "
        Indicates the power of FSK level in offhook state.
        Support 16 electric:
         0: -5.5dBm0
         1: -6.5dBm0
         2: -7.5dBm0
         3: -8.5dBm0
         4: -9.5dBm0
         5: -10.5dBm0
         6: -11.5dBm0
         7: -12.5dBm0
         8: -13.5dBm0
         9: -14.5dBm0
        10: -15.5dBm0
        11: -16.5dBm0
        12: -17.5dBm0
        13: -18.5dBm0
        14: -19.5dBm0
        15: -20.5dBm0
        Default: 3
        " 
    ::= { hwEntClipParaTable 4 }

  hwEntClipOnHookChnSeizure OBJECT-TYPE
    SYNTAX      Integer32(0..1000)
    MAX-ACCESS  read-write
    STATUS      current
    DESCRIPTION
        "
        Indicates the channel seize bits for onhook FSK.
        Default: 300
        "
    ::= { hwEntClipParaTable 5 }

  hwEntClipOnHookMarkSignal OBJECT-TYPE
    SYNTAX      Integer32(0..1000)
    MAX-ACCESS  read-write
    STATUS      current
    DESCRIPTION
        "
        Mark signal for onhook FSK.      
        Default: 180
        "
    ::= { hwEntClipParaTable 6 }    
    
  hwEntClipOnHookSendFskInterval OBJECT-TYPE
    SYNTAX      Integer32(0..1000)
    MAX-ACCESS  read-write
    STATUS      current
    DESCRIPTION
        "
        Indicates the interval between DT-AS and FSK when onhook. 
        Default: 250
        Unit: ms
        "
    ::= { hwEntClipParaTable 7 }   

  hwEntClipOnHookDtAsDur OBJECT-TYPE
    SYNTAX      Integer32(0..1000)
    MAX-ACCESS  read-write
    STATUS      current
    DESCRIPTION
        "
        Indicates the duration for DT-AS when onhook. 
        Default: 100
        Unit: ms
        "
    ::= { hwEntClipParaTable 8 }       

  hwEntClipOffHookMarkSignal OBJECT-TYPE
    SYNTAX      Integer32(0..1000)
    MAX-ACCESS  read-write
    STATUS      current
    DESCRIPTION
        "
        Mark signal for offhook FSK. 
        Default: 80   
        "
    ::= { hwEntClipParaTable 9 }     

  hwEntClipOffHookDetectTeAckInterval OBJECT-TYPE
    SYNTAX      Integer32(0..1000)
    MAX-ACCESS  read-write
    STATUS      current
    DESCRIPTION
        "
        Indicates the interval between DT-AS and detecting terminal ack when offhook. 
        Default: 160     
        "
    ::= { hwEntClipParaTable 10 }     

  hwEntClipOffHookSendFskInterval OBJECT-TYPE
    SYNTAX      Integer32(0..1000)
    MAX-ACCESS  read-write
    STATUS      current
    DESCRIPTION
        "
        Indicates the interval between detecting terminal ack and sending FSK when offhook. 
        Default: 50
        Unit: ms
        "
    ::= { hwEntClipParaTable 11 }     

  hwEntClipOffHookDtAsDur OBJECT-TYPE
    SYNTAX      Integer32(0..1000)
    MAX-ACCESS  read-write
    STATUS      current
    DESCRIPTION
        "
        Indicates the duration for DT-AS when offhook.
        Default: 80
        Unit: ms
        "
    ::= { hwEntClipParaTable 12 } 

   
    --  ============== conformance information ==============
        hwEntVoiceCommonConformance OBJECT IDENTIFIER ::= { hwEntVoiceCommonMIB 40 }
        
        
        hwEntVoiceCommonCompliances OBJECT IDENTIFIER ::= { hwEntVoiceCommonConformance 1 }
        hwEntVoiceCommonCompliance MODULE-COMPLIANCE
               STATUS      current
               DESCRIPTION
                   "The compliance statement for systems supporting 
                the this module."

               MODULE      -- this module
               MANDATORY-GROUPS    {hwEntServiceModeGroup, hwEntUserDefineRingTypeGroup, hwEntRingModeGroup, hwEntSipStackParametersGroup,
                                    hwEntDspAttributeGroup, hwEntDspTemplateGroup, hwEntServiceNumGroup, hwEntDspOperGroup, hwEntDspStatisticsGroup,
                                    hwEntDspOverloadResourceGroup, hwEntBandwidthParaGroup, hwEntClipParaGroup}  
                                               
              ::= { hwEntVoiceCommonCompliances 1 }  
              
          
        --  ============== groups ==============  
        hwEntVoiceCommonGroups OBJECT IDENTIFIER ::= { hwEntVoiceCommonConformance 2 } 
        
          hwEntServiceModeGroup OBJECT-GROUP
            OBJECTS 
            {
            hwEntServiceModeConfig,   
            hwEntServiceModeActive
            }
            STATUS current
            DESCRIPTION 
                "The hwEntServiceModeGroup group."
            ::= { hwEntVoiceCommonGroups 1 }

          hwEntUserDefineRingTypeGroup  OBJECT-GROUP
            OBJECTS 
            {
            hwEntUserDefineRingFirstRing,
            hwEntUserDefineRingFirstInterval,
            hwEntUserDefineRingSecondRing,
            hwEntUserDefineRingSecondInterval,
            hwEntUserDefineRingThirdRing,
            hwEntUserDefineRingThirdInterval                
            }                                         
            STATUS current
            DESCRIPTION 
                "The HwEntUserDefineRingTypeGroup group."
            ::= { hwEntVoiceCommonGroups 2 }
            
          hwEntRingModeGroup OBJECT-GROUP
            OBJECTS 
            {
            hwEntRingModeName,
            hwEntRingModeCascadeRingType,
            hwEntRingModeInitRingType,
            hwEntRingModeRowStatus     
            }
             STATUS current
            DESCRIPTION 
                "The HwEntRingModeGroup group."
            ::= { hwEntVoiceCommonGroups 3 }
            
          hwEntSipStackParametersGroup  OBJECT-GROUP
            OBJECTS 
            {
            hwEntSipStackParaServer,
            hwEntSipStackParaOrganization,
            hwEntSipStackParaUserAgent,
            hwEntSipStackParaMaxForwards,
            hwEntSipStackParaT1,
            hwEntSipStackParaT2,
            hwEntSipStackParaT4,
            hwEntSipStackParaTD,
            hwEntSipStackParaMinSE,
            hwEntSipStackParaSessionProgress,
            hwEntSipStackParaSessionRelProgress,
            hwEntSipStackParaEntityBasedSessionsTimerFlag,
            hwEntSipStackParaHeaderFoldFlag,
            hwEntSipStackParaToHeaderCheckFlag
            }
            STATUS current
            DESCRIPTION 
                "The hwEntSipStackParametersGroup group."
            ::= { hwEntVoiceCommonGroups 4 }


          hwEntDspAttributeGroup OBJECT-GROUP
            OBJECTS 
            {
            hwEntDspFaxMaxTrainRate,
            hwEntDspFaxTrainMode,
            hwEntDspCodeType,
            hwEntDspRtcpPackageSendInterval,
            hwEntDspRtpPacketInterval,
            hwEntDspEchoCheck,
            hwEntDspSilenceReduce,
            hwEntDspClearmodePayload,
            hwEntDspSevereDegradethreshold,
            hwEntDspBvqm,
            hwEntDspPlc,
            hwEntDspMinAdaptJitterBuffer,
            hwEntDspMaxAdaptJitterBuffer,
            hwEntDspInitAdaptJitterBuffer,
            hwEntDspMinFixedJitterBuffer,
            hwEntDspMaxFixedJitterBuffer,
            hwEntDspNormalFixedJitterBuffer,
            hwEntDspRedundancyPayload,
            hwEntDspRedundancyT30,
            hwEntDspRedundancyT4,
            hwEntDspFaxV8Negotiate,
            hwEntDspRTCPXR,
            hwEntDspVbdPayload,
            hwEntDspRfcNtePayload,
            hwEntDspG726R16kPayload,
            hwEntDspG726R24kPayload,
            hwEntDspG726R32kPayload,
            hwEntDspG726R40kPayload,
            hwEntDspAutoVBDSwitchMode,
            hwEntDspAlarmAdaptJitterBuffer
            }
             STATUS current
            DESCRIPTION 
                "The hwEntDspAttributeGroup group."
            ::= { hwEntVoiceCommonGroups 5 }
            
  
          hwEntDspTemplateGroup OBJECT-GROUP
            OBJECTS 
            {
                 hwEntDspEc,
                 hwEntDspJbMode,
                 hwEntDspNlp,
                 hwEntDspWorkMode,
                 hwEntDspSc, 
                 hwEntDspInputGain, 
                 hwEntDspOutputGain,
                 hwEntDspDtmfPara,
                 hwEntDspNteForDataevent,
                 hwEntDspSpecialFlow,
                 hwEntDspRedundancyForVbd,
                 hwEntDspTemplateRowStatus
            }
            STATUS current
            DESCRIPTION 
                "The HwEntDspTemplateGroup group."
            ::= { hwEntVoiceCommonGroups 6 }
            

          hwEntServiceNumGroup OBJECT-GROUP
            OBJECTS 
            {
                 hwEntServiceNumDspTemplate,
                 hwEntServiceNumRowStatus
            }
            STATUS current
            DESCRIPTION 
                "The HwEntServiceNumGroup group."
            ::= { hwEntVoiceCommonGroups 7 }
 

 
          hwEntDspOperGroup OBJECT-GROUP
            OBJECTS 
            {
                 hwEntDspOperChannelState,
                 hwEntDspOperAdminStatus,
                 hwEntDspOperCodec,
                 hwEntDspOperPacketInterval,
                 hwEntDspOperJitterBufferMode,
                 hwEntDspOperMinJitterBuffer,
                 hwEntDspOperMaxJitterBuffer,
                 hwEntDspOperInitJitterBuffer,
                 hwEntDspOperVAD,
                 hwEntDspOperEC,
                 hwEntDspOperGainOut,
                 hwEntDspOperGainIn,
                 hwEntDspOprJBInPercent,
                 hwEntDspOprIpSideMix,
                 hwEntDspOprPcmSideMix
            }
            STATUS current
            DESCRIPTION 
                "The HwEntDspOperGroup group."
            ::= { hwEntVoiceCommonGroups 8 }

          hwEntDspStatisticsGroup OBJECT-GROUP
            OBJECTS 
            {
                 hwEntDspStatisticsTotalNum,
                 hwEntDspStatisticsFreeNum,
                 hwEntDspStatisticsG711Num,
                 hwEntDspStatisticsAllNum,
                 hwEntDspStatisticsWastageNum,
                 hwEntDspStatisticsFaultNum,
                 hwEntDspStatisticsLoopNum,
                 hwEntDspStatisticsForbiddenNum         
            }
            STATUS current
            DESCRIPTION 
                "The HwEntDspStatisticsGroup group."
            ::= { hwEntVoiceCommonGroups 9 }

          hwEntDspOverloadResourceGroup  OBJECT-GROUP
            OBJECTS 
            {
            hwEntDspResourceWorkMode,
            hwEntDspResourcethreshold1,
            hwEntDspResourcethreshold2,
            hwEntDspResourcethreshold3
            }
            STATUS current
            DESCRIPTION 
                "The hwEntServiceModeGroup group."
            ::= { hwEntVoiceCommonGroups 10 }
            
            
          hwEntBandwidthParaGroup   OBJECT-GROUP
            OBJECTS 
            {
            hwEntBandwidthSupport,
            hwEntBandwidthMax,
            hwEntBandwidthReserved
            }
            STATUS current
            DESCRIPTION 
                "The hwEntBandwidthParaGroup group."
            ::= { hwEntVoiceCommonGroups 11 }
            

          hwEntClipParaGroup OBJECT-GROUP
            OBJECTS 
            {
            hwEntClipOnHookDualToneAlertLevel,
            hwEntClipOnHookFskLevel,
            hwEntClipOffHookDualToneAlertLevel,
            hwEntClipOffHookFskLevel,
            hwEntClipOnHookChnSeizure,
            hwEntClipOnHookMarkSignal,
            hwEntClipOnHookSendFskInterval,
            hwEntClipOnHookDtAsDur,
            hwEntClipOffHookMarkSignal,
            hwEntClipOffHookDetectTeAckInterval,
            hwEntClipOffHookSendFskInterval,
            hwEntClipOffHookDtAsDur
            }
            STATUS current
            DESCRIPTION 
                "The hwEntClipParaGroup group."
            ::= { hwEntVoiceCommonGroups 12 }            
                               
        --  ============== conformance information define end ==============                                

END
