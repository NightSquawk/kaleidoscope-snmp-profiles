--  =================================================================
-- Copyright (C) 2010 by HUAWEI SYMANTEC TECHNOLOGIES. All rights reserved
-- 
-- Description: SECURITY-STATEXT-MIB
-- Reference:
-- Version: V1.0
-- History:
-- fanzhen,2010-07-17,<contents>
--  =================================================================

    HUAWEI-SECURITY-STATEXT-MIB DEFINITIONS ::= BEGIN
 
        IMPORTS
	    enterprises			
		FROM RFC1155-SMI
            OBJECT-GROUP            
                FROM SNMPv2-CONF            
            Integer32, Counter64, OBJECT-TYPE, MODULE-IDENTITY            
                FROM SNMPv2-SMI            
            TruthValue            
                FROM SNMPv2-TC;
    
        -- 1.3.6.1.4.1.2011.6.122.38
        hwSecStatExtMib MODULE-IDENTITY 
            LAST-UPDATED "201007190900Z"		-- Jul 19, 2010 at 09:00 GMT
            ORGANIZATION 
                "Huawei Symantec Technologies co.,Ltd."
            CONTACT-INFO 
                "
                R&D BeiJing, Huawei Symantec Technologies co.,Ltd.
                Huawei Bld.,NO.3 Xinxi Rd.,
                Shang-Di Information Industry Base,
                Hai-Dian District Beijing P.R. China
                Zip:100085
                Http://www.huaweiSymantec.com
                E-mail:support@huaweiSymantec.com
                "
            DESCRIPTION 
                "
                V1.00
                The HUAWEI-SECURITY-STATEXT-MIB contains objects to manage the security statistics for firewall product.
                "
            ::= { hwSecurity 38 }

--
-- Node definitions
--                       
 	-- 1.3.6.1.4.1.2011
	huawei OBJECT IDENTIFIER ::= { enterprises 2011 }
        
        -- 1.3.6.1.4.1.2011.6
        huaweiUtility OBJECT IDENTIFIER ::= { huawei 6 }
        
        -- 1.3.6.1.4.1.2011.6.122
        hwSecurity OBJECT IDENTIFIER ::= { huaweiUtility 122 }                         
        
        -- 1.3.6.1.4.1.2011.6.122.38.1
        hwSecStatExtMibObjects OBJECT IDENTIFIER ::= { hwSecStatExtMib 1 } 
        
        -- 1.3.6.1.4.1.2011.6.122.38.1.1                 
        hwSecStatExtAcl OBJECT IDENTIFIER ::= { hwSecStatExtMibObjects 1 }
        
        -- 1.3.6.1.4.1.2011.6.122.38.1.1.1
        hwSecStatExtBasicAclGroupNum OBJECT-TYPE
            SYNTAX Integer32 (0..65535)
            MAX-ACCESS read-only
            STATUS current
            DESCRIPTION
                "
                The total number of Basic Acl Group.                
                "
            ::= { hwSecStatExtAcl 1 }
        
        -- 1.3.6.1.4.1.2011.6.122.38.1.1.2
        hwSecStatExtAdvanceAclGroupNum OBJECT-TYPE
            SYNTAX Integer32 (0..65535)
            MAX-ACCESS read-only
            STATUS current
            DESCRIPTION
                "
                The total number of Advance Acl Group.
                "
            ::= { hwSecStatExtAcl 2 }
        
        -- 1.3.6.1.4.1.2011.6.122.38.1.1.3
        hwSecStatExtMacAclGroupNum OBJECT-TYPE
            SYNTAX Integer32 (0..65535)
            MAX-ACCESS read-only
            STATUS current
            DESCRIPTION
                "
                The total number of mac layer Acl Group.                            
                "
            ::= { hwSecStatExtAcl 3 }
        
        -- 1.3.6.1.4.1.2011.6.122.38.1.1.4
        hwSecStatExtAcl6GroupNum OBJECT-TYPE
            SYNTAX Integer32 (0..65535)
            MAX-ACCESS read-only
            STATUS current
            DESCRIPTION
                "
                The total number of Acl6 Group.
                "
            ::= { hwSecStatExtAcl 4 }
        
        -- 1.3.6.1.4.1.2011.6.122.38.1.1.5        
        hwSecStatExtBasicAclRuleNum OBJECT-TYPE
            SYNTAX Integer32 (0..65535)
            MAX-ACCESS read-only
            STATUS current
            DESCRIPTION
                "
                The total number of Basic Acl Rule.
                "
            ::= { hwSecStatExtAcl 5 }
        
        -- 1.3.6.1.4.1.2011.6.122.38.1.1.6
        hwSecStatExtAdvanceAclRuleNum OBJECT-TYPE
            SYNTAX Integer32 (0..65535)
            MAX-ACCESS read-only
            STATUS current
            DESCRIPTION
                "
                The total number of Advance Acl Rule.
                "
            ::= { hwSecStatExtAcl 6 }
           
        -- 1.3.6.1.4.1.2011.6.122.38.1.1.7
        hwSecStatExtMacAclRuleNum OBJECT-TYPE
            SYNTAX Integer32 (0..65535)
            MAX-ACCESS read-only
            STATUS current
            DESCRIPTION
                "
                The total number of mac layer Acl Rule.
                "
            ::= { hwSecStatExtAcl 7 }
            
        -- 1.3.6.1.4.1.2011.6.122.38.1.1.8
        hwSecStatExtAcl6RuleNum OBJECT-TYPE
            SYNTAX Integer32 (0..65535)
            MAX-ACCESS read-only
            STATUS current
            DESCRIPTION
                "
                The total number of Acl6 Rule.
                "
            ::= { hwSecStatExtAcl 8 }    
            
        -- 1.3.6.1.4.1.2011.6.122.38.1.2
        hwSecStatExtRoute OBJECT IDENTIFIER ::= { hwSecStatExtMibObjects 2 }
        
        -- 1.3.6.1.4.1.2011.6.122.38.1.2.1
        hwSecStatExtStaticRouteNum OBJECT-TYPE
            SYNTAX Integer32 (0..65535)
            MAX-ACCESS read-only
            STATUS current
            DESCRIPTION
                "
                The total number of static router number.
                "
            ::= { hwSecStatExtRoute 1 }
        
        -- 1.3.6.1.4.1.2011.6.122.38.1.2.2
        hwSecStatExtOspfNum OBJECT-TYPE
            SYNTAX Integer32 (0..65535)
            MAX-ACCESS read-only
            STATUS current
            DESCRIPTION
                "
                The total number of ospf router number.
                "
            ::= { hwSecStatExtRoute 2 }
        
        -- 1.3.6.1.4.1.2011.6.122.38.1.2.3
        hwSecStatExtRipNum OBJECT-TYPE
            SYNTAX Integer32 (0..65535)
            MAX-ACCESS read-only
            STATUS current
            DESCRIPTION
                "
                The total number of rip router number.
                "
            ::= { hwSecStatExtRoute 3 }
        
        -- 1.3.6.1.4.1.2011.6.122.38.1.2.4
        hwSecStatExtIsisNum OBJECT-TYPE
            SYNTAX Integer32 (0..65535)
            MAX-ACCESS read-only
            STATUS current
            DESCRIPTION
                "
                The total number of isis router number.
                "
            ::= { hwSecStatExtRoute 4 }
        
        -- 1.3.6.1.4.1.2011.6.122.38.1.2.5
        hwSecStatExtBgpNum OBJECT-TYPE
            SYNTAX Integer32 (0..65535)
            MAX-ACCESS read-only
            STATUS current
            DESCRIPTION
                "
                The total number of bgp router number.
                "
            ::= { hwSecStatExtRoute 5 }
        
        -- 1.3.6.1.4.1.2011.6.122.38.1.2.6
        hwSecStatExtIpv6StaticRouteNum OBJECT-TYPE
            SYNTAX Integer32 (0..65535)
            MAX-ACCESS read-only
            STATUS current
            DESCRIPTION
                "
                The total number of ipv6 static router number.
                "
            ::= { hwSecStatExtRoute 6 }
        
        -- 1.3.6.1.4.1.2011.6.122.38.1.2.7
        hwSecStatExtIpv6OspfNum OBJECT-TYPE
            SYNTAX Integer32 (0..65535)
            MAX-ACCESS read-only
            STATUS current
            DESCRIPTION
                "
                The total number of ipv6 ospf router number.
                "
            ::= { hwSecStatExtRoute 7 }
            
        -- 1.3.6.1.4.1.2011.6.122.38.1.2.8
        hwSecStatExtIpv6RipNum OBJECT-TYPE
            SYNTAX Integer32 (0..65535)
            MAX-ACCESS read-only
            STATUS current
            DESCRIPTION
                "
                The total number of ipv6 rip router number.
                "
            ::= { hwSecStatExtRoute 8 }

        -- 1.3.6.1.4.1.2011.6.122.38.1.2.9
        hwSecStatExtIpv6IsisNum OBJECT-TYPE
            SYNTAX Integer32 (0..65535)
            MAX-ACCESS read-only
            STATUS current
            DESCRIPTION
                "
                The total number of ipv6 Isis router number.
                "
            ::= { hwSecStatExtRoute 9 }

        -- 1.3.6.1.4.1.2011.6.122.38.1.2.10
        hwSecStatExtIpv6BgpNum OBJECT-TYPE
            SYNTAX Integer32 (0..65535)
            MAX-ACCESS read-only
            STATUS current
            DESCRIPTION
                "
                The total number of ipv6 bgp router number.
                "
            ::= { hwSecStatExtRoute 10 }
                        
        -- 1.3.6.1.4.1.2011.6.122.38.1.3
        hwSecStatExtSession OBJECT IDENTIFIER ::= { hwSecStatExtMibObjects 3 }
                       
        -- 1.3.6.1.4.1.2011.6.122.38.1.3.1
        hwSecStatExtSessionNum OBJECT-TYPE
            SYNTAX Integer32 (0..4294967295)  
            MAX-ACCESS read-only
            STATUS current
            DESCRIPTION
                "
                The current number of session.                
                "
            ::= { hwSecStatExtSession 1 }
        
        -- 1.3.6.1.4.1.2011.6.122.38.1.3.2
        hwSecStatExtMacAddrListNum OBJECT-TYPE
            SYNTAX Integer32 (0..4294967295)
            MAX-ACCESS read-only
            STATUS current
            DESCRIPTION
                "
                The current number of mac address list.
                "
            ::= { hwSecStatExtSession 2 }
        
        -- 1.3.6.1.4.1.2011.6.122.38.1.3.3
        hwSecStatExtBlackListNum OBJECT-TYPE
            SYNTAX Integer32 (0..4294967295)
            MAX-ACCESS read-only
            STATUS current
            DESCRIPTION
                "
                The current number of blacklist.
                "
            ::= { hwSecStatExtSession 3 }
        
        -- 1.3.6.1.4.1.2011.6.122.38.1.3.4
        hwSecStatExtNatServerNum OBJECT-TYPE
            SYNTAX Integer32 (0..4294967295)
            MAX-ACCESS read-only
            STATUS current
            DESCRIPTION
                "
                The total number of nat server.
                "
            ::= { hwSecStatExtSession 4 }
        
        -- 1.3.6.1.4.1.2011.6.122.38.1.3.5
        hwSecStatExtIpMonitorListNum OBJECT-TYPE
            SYNTAX Integer32 (0..4294967295)
            MAX-ACCESS read-only
            STATUS current
            DESCRIPTION
                "
                The total number of ip monitor list.
                "
            ::= { hwSecStatExtSession 5 }
        
        -- 1.3.6.1.4.1.2011.6.122.38.1.3.6
        hwSecStatExtServerMapTotalNum OBJECT-TYPE
            SYNTAX Integer32 (0..4294967295)
            MAX-ACCESS read-only
            STATUS current
            DESCRIPTION
                "
                The total number of ServerMap list.
                "
            ::= { hwSecStatExtSession 6 }
        
        -- 1.3.6.1.4.1.2011.6.122.38.1.3.7
        hwSecStatExtServerMapDynamicNum OBJECT-TYPE
            SYNTAX Integer32 (0..4294967295)
            MAX-ACCESS read-only
            STATUS current
            DESCRIPTION
                "
                The total number of dynamic ServerMap list.
                "
            ::= { hwSecStatExtSession 7 }
        
        -- 1.3.6.1.4.1.2011.6.122.38.1.3.8
        hwSecStatExtWifiUserOnlineNum OBJECT-TYPE
            SYNTAX Integer32 (0..4294967295)
            MAX-ACCESS read-only
            STATUS current
            DESCRIPTION
                "
                The total number of wifi user online.
                "
            ::= { hwSecStatExtSession 8 }
        
        -- 1.3.6.1.4.1.2011.6.122.38.1.3.9
        hwSecStatExt802dot1xUserOnlineNum OBJECT-TYPE
            SYNTAX Integer32 (0..4294967295)
            MAX-ACCESS read-only
            STATUS current
            DESCRIPTION
                "
                The total number of 802.1x user online.
                "
            ::= { hwSecStatExtSession 9 }
            
        -- 1.3.6.1.4.1.2011.6.122.38.1.3.10
        hwSecStatExtArplistTotalNum OBJECT-TYPE
            SYNTAX Integer32 (0..4294967295)
            MAX-ACCESS read-only
            STATUS current
            DESCRIPTION
                "
                The total number of ARP list.
                "
            ::= { hwSecStatExtSession 10 }
        
        -- 1.3.6.1.4.1.2011.6.122.38.1.3.11
        hwSecStatExtFiblistTotoleNum OBJECT-TYPE
            SYNTAX Integer32 (0..4294967295)
            MAX-ACCESS read-only
            STATUS current
            DESCRIPTION
                "
                The total number of FIB list.
                "
            ::= { hwSecStatExtSession 11 }
        
        -- 1.3.6.1.4.1.2011.6.122.38.1.3.12
        hwSecStatExtIpv6SessionNum OBJECT-TYPE
            SYNTAX Integer32 (0..4294967295)
            MAX-ACCESS read-only
            STATUS current
            DESCRIPTION
                "
                The total number of ipv6 session.
                "
            ::= { hwSecStatExtSession 12 }
        
        -- 1.3.6.1.4.1.2011.6.122.38.1.3.13
        hwSecStatExtIpv6ServerMapTotalNum OBJECT-TYPE
            SYNTAX Integer32 (0..4294967295)
            MAX-ACCESS read-only
            STATUS current
            DESCRIPTION
                "
                The total number of ipv6 servermap.
                "
            ::= { hwSecStatExtSession 13 }                   
        
        -- 1.3.6.1.4.1.2011.6.122.38.1.4
        hwSecStatExtTotalNum OBJECT IDENTIFIER ::= { hwSecStatExtMibObjects 4 }
        
        -- 1.3.6.1.4.1.2011.6.122.38.1.4.1
        hwSecStatIkeNum OBJECT-TYPE
            SYNTAX Integer32 (0..4294967295)
            MAX-ACCESS read-only
            STATUS current
            DESCRIPTION
                "
                The total number of IKE currently.
                "
            ::= { hwSecStatExtTotalNum 1 }
        
        -- 1.3.6.1.4.1.2011.6.122.38.1.4.2
        hwSecStatIpsecPacketsIn OBJECT-TYPE
            SYNTAX Counter64
            MAX-ACCESS read-only
            STATUS current
            DESCRIPTION
                "
                The total packet number of ipsec receive.
                "
            ::= { hwSecStatExtTotalNum 2 }
        
        -- 1.3.6.1.4.1.2011.6.122.38.1.4.3
        hwSecStatIpsecPacketsOut OBJECT-TYPE
            SYNTAX Counter64
            MAX-ACCESS read-only
            STATUS current
            DESCRIPTION
                "
                The total packet number of ipsec send.
                "
            ::= { hwSecStatExtTotalNum 3 }
        
        -- 1.3.6.1.4.1.2011.6.122.38.1.4.4
        hwSecStatIpsecPacketsDorp OBJECT-TYPE
            SYNTAX Counter64
            MAX-ACCESS read-only
            STATUS current
            DESCRIPTION
                "
                The total packet number of ipsec drop.
                "
            ::= { hwSecStatExtTotalNum 4 }
        
        -- 1.3.6.1.4.1.2011.6.122.38.1.4.5
        hwSecStatL2tpUserTotalNum OBJECT-TYPE
            SYNTAX Integer32 (0..4294967295)
            MAX-ACCESS read-only
            STATUS current
            DESCRIPTION
                "
                The total number of l2TP user currently.
                "
            ::= { hwSecStatExtTotalNum 5 }
        
        -- 1.3.6.1.4.1.2011.6.122.38.1.4.6
        hwSecStatHrpPacketsSend OBJECT-TYPE
            SYNTAX Integer32 (0..4294967295)
            MAX-ACCESS read-only
            STATUS current
            DESCRIPTION
                "
                The total packet number of HRP send.
                "
            ::= { hwSecStatExtTotalNum 6 }
            
        
        -- 1.3.6.1.4.1.2011.6.122.38.1.5
	hwSecStatExtL2tpTable OBJECT-TYPE
	    SYNTAX SEQUENCE OF HwSecStatExtL2tpEntry
	    MAX-ACCESS not-accessible
	    STATUS current
	    DESCRIPTION
	        "
	        This table is l2tp statistic inform.
	        "
	    ::= { hwSecStatExtMibObjects 5 }
	    
    	-- 1.3.6.1.4.1.2011.6.122.38.1.5.1
    	hwSecStatExtL2tpEntry OBJECT-TYPE
       	    SYNTAX HwSecStatExtL2tpEntry
            MAX-ACCESS not-accessible
            STATUS current
            DESCRIPTION
                "
                Each entry is a statistic inform of l2tp tunnel and session.
                "
            INDEX { hwSecStatExtL2tpSlotIndex, hwSecStatExtL2tpCpuIndex }
            ::= { hwSecStatExtL2tpTable 1 }
            
        -- 1.3.6.1.4.1.2011.6.122.38.1.5.1
    	HwSecStatExtL2tpEntry ::=
            SEQUENCE { 
            	hwSecStatExtL2tpSlotIndex
               	    Integer32,
            	hwSecStatExtL2tpCpuIndex
               	    Integer32,
            	hwSecStatExtL2tpTunnelNum
               	    Integer32,
            	hwSecStatExtL2tpSessionNum
               	    Integer32                 	
                }          
                
        -- 1.3.6.1.4.1.2011.6.122.38.1.5.1.1
        hwSecStatExtL2tpSlotIndex OBJECT-TYPE
            SYNTAX Integer32 (1..4294967295)
            MAX-ACCESS not-accessible
            STATUS current
            DESCRIPTION
                "The total number of packets dropped for no session."
            ::= { hwSecStatExtL2tpEntry 1 }
        
        -- 1.3.6.1.4.1.2011.6.122.38.1.5.1.2
        hwSecStatExtL2tpCpuIndex OBJECT-TYPE
            SYNTAX Integer32 (1..4294967295)
            MAX-ACCESS not-accessible
            STATUS current
            DESCRIPTION
                "
                The total bytes of packets dropped for no session.
                "
            ::= { hwSecStatExtL2tpEntry 2 }
        
        -- 1.3.6.1.4.1.2011.6.122.38.1.5.1.3
        hwSecStatExtL2tpTunnelNum OBJECT-TYPE
            SYNTAX Integer32 (0..4294967295)
            MAX-ACCESS read-only
            STATUS current
            DESCRIPTION
                "
                The total number of l2tp tunnel.
                "
            ::= { hwSecStatExtL2tpEntry 3 }
        
        -- 1.3.6.1.4.1.2011.6.122.38.1.5.1.4
        hwSecStatExtL2tpSessionNum OBJECT-TYPE
            SYNTAX Integer32 (0..4294967295)
            MAX-ACCESS read-only
            STATUS current
            DESCRIPTION
                "
                The total number of l2tp session.
                "
            ::= { hwSecStatExtL2tpEntry 4 }
            
        -- 1.3.6.1.4.1.2011.6.122.38.1.6
	hwSecStatExtVcpuTable OBJECT-TYPE
	    SYNTAX SEQUENCE OF HwSecStatExtVcpuEntry
	    MAX-ACCESS not-accessible
	    STATUS current
	    DESCRIPTION
	        "
	        This table is vcpu useage statistic inform.
	        "
	    ::= { hwSecStatExtMibObjects 6 }
	    
    	-- 1.3.6.1.4.1.2011.6.122.38.1.6.1
    	hwSecStatExtVcpuEntry OBJECT-TYPE
       	    SYNTAX HwSecStatExtVcpuEntry
            MAX-ACCESS not-accessible
            STATUS current
            DESCRIPTION
                "
                Each entry is a statistic inform of vcpu useage.
                "
            INDEX { hwSecStatExtVcpuIndex }
            ::= { hwSecStatExtVcpuTable 1 }
            
        -- 1.3.6.1.4.1.2011.6.122.38.1.6.1
    	HwSecStatExtVcpuEntry ::=
            SEQUENCE { 
            	hwSecStatExtVcpuIndex
               	    Integer32,
               	hwSecStatExtVcpuID
               	    Integer32,
            	hwSecStatExtVcpuUseage
               	    Integer32    	
                }   
                       
        -- 1.3.6.1.4.1.2011.6.122.38.1.6.1.1
        hwSecStatExtVcpuIndex OBJECT-TYPE
            SYNTAX Integer32 (1..64)
            MAX-ACCESS not-accessible
            STATUS current
            DESCRIPTION
                "
                The index of Vcpu.
                "
            ::= { hwSecStatExtVcpuEntry 1 }
        
        -- 1.3.6.1.4.1.2011.6.122.38.1.6.1.2
        hwSecStatExtVcpuID OBJECT-TYPE
            SYNTAX Integer32 (0..64)
            MAX-ACCESS read-only
            STATUS current
            DESCRIPTION
                "
                The Id of Vcpu.
                "
            ::= { hwSecStatExtVcpuEntry 2 }
        
        
        -- 1.3.6.1.4.1.2011.6.122.38.1.6.1.3
        hwSecStatExtVcpuUseage OBJECT-TYPE
            SYNTAX Integer32 (0..4294967295)
            MAX-ACCESS read-only
            STATUS current
            DESCRIPTION
                "
                The useage of Vcpu.
                "
            ::= { hwSecStatExtVcpuEntry 3 }

        -- 1.3.6.1.4.1.2011.6.122.38.1.7
	hwSecStatExtLicenseTable OBJECT-TYPE
	    SYNTAX SEQUENCE OF HwSecStatExtLicenseEntry
	    MAX-ACCESS not-accessible
	    STATUS current
	    DESCRIPTION
	        "
	        This table show the max instance number of each module.
	        "
	    ::= { hwSecStatExtMibObjects 7 }

        -- 1.3.6.1.4.1.2011.6.122.38.1.7.1
    	hwSecStatExtLicenseEntry OBJECT-TYPE
       	    SYNTAX HwSecStatExtLicenseEntry
            MAX-ACCESS not-accessible
            STATUS current
            DESCRIPTION
                "
                Each entry is a max instance number of module.
                "
            INDEX { hwSecStatExtModuleIndex }
            ::= { hwSecStatExtLicenseTable 1 }
            
        -- 1.3.6.1.4.1.2011.6.122.38.1.7.1
    	HwSecStatExtLicenseEntry ::=
            SEQUENCE { 
            	hwSecStatExtModuleIndex
               	    Integer32,
               	hwSecStatExtModuleName
               	    OCTET STRING,
            	hwSecStatExtModuleLicenseNum
               	    Integer32    	
                }   
                       
        -- 1.3.6.1.4.1.2011.6.122.38.1.7.1.1
        hwSecStatExtModuleIndex OBJECT-TYPE
            SYNTAX Integer32 (1..256)
            MAX-ACCESS not-accessible
            STATUS current
            DESCRIPTION
                "
                The index of module in device.
                "
            ::= { hwSecStatExtLicenseEntry 1 }
        
        -- 1.3.6.1.4.1.2011.6.122.38.1.7.1.2
        hwSecStatExtModuleName OBJECT-TYPE
            SYNTAX OCTET STRING(SIZE (0..32))
	    MAX-ACCESS read-only
            STATUS current
            DESCRIPTION
                "
                The name of module.
                "
            ::= { hwSecStatExtLicenseEntry 2 }
            
        -- 1.3.6.1.4.1.2011.6.122.38.1.7.1.3
        hwSecStatExtModuleLicenseNum OBJECT-TYPE
            SYNTAX Integer32 (0..4294967295)
            MAX-ACCESS read-only
            STATUS current
            DESCRIPTION
                "
                The max instance number of module grant.
                "
            ::= { hwSecStatExtLicenseEntry 3 }
            
 -- Conformance
 
        -- 1.3.6.1.4.1.2011.6.122.38.2
        hwSecStatExtConformance OBJECT IDENTIFIER ::= { hwSecStatExtMib 2 }
        
 -- Module compliance
                               
        -- 1.3.6.1.4.1.2011.6.122.38.2.1
        hwSecStatExtCompliance OBJECT IDENTIFIER ::= { hwSecStatExtConformance 1 }
        
        -- 1.3.6.1.4.1.2011.6.122.38.2.2
        hwSecStatExtMibGroups OBJECT IDENTIFIER ::= { hwSecStatExtConformance 2 }
        
        -- 1.3.6.1.4.1.2011.6.122.38.2.2.1
        hwSecStatExtAclGroup OBJECT-GROUP
            OBJECTS { 
                hwSecStatExtBasicAclGroupNum,
                hwSecStatExtAdvanceAclGroupNum,
                hwSecStatExtMacAclGroupNum,
                hwSecStatExtAcl6GroupNum,
                hwSecStatExtBasicAclRuleNum,
                hwSecStatExtAdvanceAclRuleNum,
                hwSecStatExtMacAclRuleNum,
                hwSecStatExtAcl6RuleNum
                    }
            STATUS current
            DESCRIPTION 
                "
                Description.
                "
            ::= { hwSecStatExtMibGroups 1 }
        
        -- 1.3.6.1.4.1.2011.6.122.38.2.2.2
        hwSecStatExtRouteGroup OBJECT-GROUP
            OBJECTS { 
                hwSecStatExtStaticRouteNum,
                hwSecStatExtOspfNum,
                hwSecStatExtRipNum,
                hwSecStatExtIsisNum,
                hwSecStatExtBgpNum,
                hwSecStatExtIpv6StaticRouteNum,
                hwSecStatExtIpv6OspfNum,
                hwSecStatExtIpv6RipNum,
                hwSecStatExtIpv6IsisNum,
                hwSecStatExtIpv6BgpNum
                    }
            STATUS current
            DESCRIPTION 
                "
                Description.
                "
            ::= { hwSecStatExtMibGroups 2 }
            
        -- 1.3.6.1.4.1.2011.6.122.38.2.2.3    
        hwSecStatExtSessionGroup OBJECT-GROUP
            OBJECTS { 
                hwSecStatExtSessionNum,
                hwSecStatExtMacAddrListNum,
                hwSecStatExtBlackListNum,
                hwSecStatExtNatServerNum,
                hwSecStatExtIpMonitorListNum,
                hwSecStatExtServerMapTotalNum,
                hwSecStatExtServerMapDynamicNum,
                hwSecStatExtWifiUserOnlineNum,
                hwSecStatExt802dot1xUserOnlineNum,
                hwSecStatExtArplistTotalNum,
                hwSecStatExtIpv6SessionNum,
                hwSecStatExtIpv6ServerMapTotalNum
                    }
            STATUS current
            DESCRIPTION 
                "
                Description.
                "
            ::= { hwSecStatExtMibGroups 3 }
        
        -- 1.3.6.1.4.1.2011.6.122.38.2.2.4    
        hwSecStatExtIPsecGroup OBJECT-GROUP
            OBJECTS { 
                hwSecStatIkeNum,
                hwSecStatIpsecPacketsIn,
                hwSecStatIpsecPacketsOut,
                hwSecStatIpsecPacketsDorp,
                hwSecStatL2tpUserTotalNum,
                hwSecStatHrpPacketsSend
                    }
            STATUS current
            DESCRIPTION 
                "
                Description.
                "
            ::= { hwSecStatExtMibGroups 4 }
            
        -- 1.3.6.1.4.1.2011.6.122.38.2.2.5    
        hwSecStatExtL2tpGroup OBJECT-GROUP
            OBJECTS {                      
                hwSecStatExtL2tpTunnelNum,
                hwSecStatExtL2tpSessionNum
                    }
            STATUS current
            DESCRIPTION 
                "
                Description.
                "
            ::= { hwSecStatExtMibGroups 5 }
            
        -- 1.3.6.1.4.1.2011.6.122.38.2.2.6    
        hwSecStatExtVcpuGroup OBJECT-GROUP
            OBJECTS {                                
                hwSecStatExtVcpuID,
                hwSecStatExtVcpuUseage
                    }
            STATUS current
            DESCRIPTION 
                "
                Description.
                "
            ::= { hwSecStatExtMibGroups 6 }
        
        -- 1.3.6.1.4.1.2011.6.122.38.2.2.7    
        hwSecStatExtLicenseGroup OBJECT-GROUP
            OBJECTS {                
                hwSecStatExtModuleName,
                hwSecStatExtModuleLicenseNum
                    }
            STATUS current
            DESCRIPTION 
                "
                Description.
                "
            ::= { hwSecStatExtMibGroups 7 }     
    END
--
-- HUAWEI-SECURITY-STATEXT-MIB.mib
--
