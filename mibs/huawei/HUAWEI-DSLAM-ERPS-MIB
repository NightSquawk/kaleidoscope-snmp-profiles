-- =================================================================
-- Copyright (C) 2017 by HUAWEI TECHNOLOGIES. All rights reserved.
-- Description:  The MIB is used for defining Huawei's ERPS attribute.
-- Reference:    ITU-T G.8032/Y.1344
-- Version:      V1.03
-- =================================================================

HUAWEI-DSLAM-ERPS-MIB DEFINITIONS ::= BEGIN

        IMPORTS
            hwDatacomm
                FROM HUAWEI-MIB
            EnabledStatus
                FROM P-BRIDGE-MIB
            VlanId
                FROM Q-BRIDGE-MIB
            OBJECT-GROUP, NOTIFICATION-GROUP
                FROM SNMPv2-CONF
            InterfaceIndex
                FROM IF-MIB
            Integer32, Unsigned32, OBJECT-TYPE, MODULE-IDENTITY, OBJECT-IDENTITY, NOTIFICATION-TYPE, TimeTicks, Counter32
                FROM SNMPv2-SMI
            RowStatus,DisplayString, DateAndTime
                FROM SNMPv2-TC;

        hwErpsMIB MODULE-IDENTITY
            LAST-UPDATED "201706010000Z"
            ORGANIZATION "Huawei Technologies Co.,Ltd."
            CONTACT-INFO 
                "Huawei Industrial Base
                 Bantian, Longgang
                 Shenzhen 518129
                 People's Republic of China 
                 Website: http://www.huawei.com
                 Email: support@huawei.com
                "                                               
        DESCRIPTION                                                      
            "The MIB is used for defining Huawei's ERPS attribute.
            "

        --  Revision history
            REVISION     "201706010000Z"
            DESCRIPTION  "V1.03, added hwErpsInnerForwardingFaultTriggerSwitch and hwErpsInnerForwardingFaultTriggerTable."

            REVISION     "201406100000Z"
            DESCRIPTION  "V1.02, modified the ORGANIZATION.
                                 modified the MIB name from HUAWEI-ERPS-MIB to HUAWEI-DSLAM-ERPS-MIB.
                                 modified the MAX-ACCESS of hwConfigRingId and hwConfigPortId1."
        
            REVISION     "201308021000Z"
            DESCRIPTION  "V1.01, modified the node hwErpsRingStatusInfoGroup."
            
            REVISION     "201210230000Z"
            DESCRIPTION  "V1.00, Modified  ."

        ::= { hwDatacomm 256 }
--  Node definitions
--
    -- 1.3.6.1.4.1.2011.5.25.256.1
    hwErpsObjects OBJECT IDENTIFIER ::= { hwErpsMIB 1 }


    -- 1.3.6.1.4.1.2011.5.25.256.1.1
    hwErpsGlobalResetRapsPktCnt OBJECT-TYPE
        SYNTAX INTEGER {
                        clear(1),
                        unused(65535)
                       }
        MAX-ACCESS read-write
        STATUS current
        DESCRIPTION
            "Reset the RAPS packets counter of all running ERPS ports.
             Options:
             1. clear(1)          - It must be clear(1) when it is set.
             2. unused(65535)     - The value is unused(65535) when it is read."
        ::= { hwErpsObjects 1 }

    -- ring config table
    -- 1.3.6.1.4.1.2011.5.25.256.1.2
    hwErpsRingConfigTable OBJECT-TYPE
        SYNTAX SEQUENCE OF HwErpsRingConfigEntry
        MAX-ACCESS not-accessible
        STATUS current
        DESCRIPTION
            "The table includes the configuration of ERPS rings.
            The index of this table is hwConfigRingId."
        ::= { hwErpsObjects 2 }


    -- 1.3.6.1.4.1.2011.5.25.256.1.2.1
    hwErpsRingConfigEntry OBJECT-TYPE
        SYNTAX HwErpsRingConfigEntry
        MAX-ACCESS not-accessible
        STATUS current
        DESCRIPTION
            "The table includes the configuration of ERPS rings.
            The index of this entry is hwConfigRingId."
        INDEX { hwConfigRingId }
        ::= { hwErpsRingConfigTable 1 }


    HwErpsRingConfigEntry ::=
        SEQUENCE {
            hwConfigRingId
                Integer32,
            hwConfigRingRowStatus
                RowStatus,
            hwConfigDescription
                OCTET STRING,
            hwConfigControlVlanId
                Integer32,
            hwConfigProtectedInstanceList
                OCTET STRING,
            hwConfigWtrTimerSettingValue
                Integer32,
            hwConfigGuardTimerSettingValue
                Integer32,
            hwConfigHoldoffTimerSettingValue
                Integer32,
            hwConfigResetRapsPktCnt
                INTEGER,
           hwConfigRapsMel
                Integer32,
           hwConfigPriority
                Integer32
               }

    -- 1.3.6.1.4.1.2011.5.25.256.1.2.1.1
    hwConfigRingId OBJECT-TYPE
        SYNTAX Integer32 (1..255)
        MAX-ACCESS accessible-for-notify
        STATUS current
        DESCRIPTION
            "ERPS ring Identifier."
        ::= { hwErpsRingConfigEntry 1 }

    -- 1.3.6.1.4.1.2011.5.25.256.1.2.1.2
    hwConfigRingRowStatus OBJECT-TYPE
        SYNTAX RowStatus
        MAX-ACCESS read-create
        STATUS current
        DESCRIPTION
            "Operation of CreateAndGo can be used to create a new ERPS ring,
             and operation of Destroy be used to destroy an existent ERPS ring.
             Options:
             1. active(1)      -indicates the query operation
             2. createAndGo(4) -indicates creating an ERPS ring
             3. destroy(6)     -indicates deleting an ERPS ring"
        ::= { hwErpsRingConfigEntry 2 }

    -- 1.3.6.1.4.1.2011.5.25.256.1.2.1.3
    hwConfigDescription OBJECT-TYPE
        SYNTAX OCTET STRING (SIZE (0..80))
        MAX-ACCESS read-create
        STATUS current
        DESCRIPTION
            "A textual description of the ERPS ring.
            It is mandatory that this only contain no more than 80 characters."
        ::= { hwErpsRingConfigEntry 3 }


    -- 1.3.6.1.4.1.2011.5.25.256.1.2.1.4
    hwConfigControlVlanId OBJECT-TYPE
        SYNTAX Integer32 (0 | 2..4093)
        MAX-ACCESS read-create
        STATUS current
        DESCRIPTION
            "The control VLAN identifier of the ERPS ring.
             If the value of the object is set 0, the operation is to delete configuration."
        DEFVAL { 0 }
        ::= { hwErpsRingConfigEntry 4 }

    -- 1.3.6.1.4.1.2011.5.25.256.1.2.1.5
    hwConfigProtectedInstanceList OBJECT-TYPE
        SYNTAX OCTET STRING (SIZE (0..512))
        MAX-ACCESS read-create
        STATUS current
        DESCRIPTION
            "The protected instance list of the ERPS ring.
            Every symbol can indicates the set values of eight instances by mask.
            The first symbol indicates the instances from 0 to 7, and so on.
            All zero indicates delete all instances of current ring."
        ::= { hwErpsRingConfigEntry 5 }

    -- 1.3.6.1.4.1.2011.5.25.256.1.2.1.6
    hwConfigWtrTimerSettingValue OBJECT-TYPE
        SYNTAX Integer32 (1..12)
        UNITS "minutes"
        MAX-ACCESS read-create
        STATUS current
        DESCRIPTION
            "The setting value of  the ring's wait to restore timer."
        DEFVAL { 5 }
        ::= { hwErpsRingConfigEntry 6 }

    -- 1.3.6.1.4.1.2011.5.25.256.1.2.1.7
    hwConfigGuardTimerSettingValue OBJECT-TYPE
        SYNTAX Integer32 (1..200)
        UNITS "centiseconds"
        MAX-ACCESS read-create
        STATUS current
        DESCRIPTION
            "The setting value of the ring's guard timer."
        DEFVAL { 200 }
        ::= { hwErpsRingConfigEntry 7 }

    -- 1.3.6.1.4.1.2011.5.25.256.1.2.1.8
    hwConfigHoldoffTimerSettingValue OBJECT-TYPE
        SYNTAX Integer32 (0..100)
        UNITS "deciseconds"
        MAX-ACCESS read-create
        STATUS current
        DESCRIPTION
            "The setting value of the ring's hold-off timer."
        DEFVAL { 0 }
        ::= { hwErpsRingConfigEntry 8 }

    -- 1.3.6.1.4.1.2011.5.25.256.1.2.1.9
    hwConfigResetRapsPktCnt OBJECT-TYPE
        SYNTAX INTEGER
                {
                clear(1),
                unused(65535)
                }
            MAX-ACCESS read-create
            STATUS current
            DESCRIPTION
            "Reset the RAPS packets counter of the ERPS ring's ports.
             Options:
             1. clear(1)      - It must be clear(1) when it is set
             2. unused(65535) - The value is unused(65535) when it is read"
            ::= { hwErpsRingConfigEntry 9 }

    -- 1.3.6.1.4.1.2011.5.25.256.1.2.1.10
    hwConfigRapsMel OBJECT-TYPE
        SYNTAX Integer32 (0..7)
        MAX-ACCESS read-create
        STATUS current
        DESCRIPTION
            "The MEL is the maintenance entity group(MEG) level providing a communication channel for the ring RAPS information."
        DEFVAL { 7 }
        ::= { hwErpsRingConfigEntry 10 }

    -- 1.3.6.1.4.1.2011.5.25.256.1.2.1.11
    hwConfigPriority OBJECT-TYPE
        SYNTAX Integer32 (0..7)
        MAX-ACCESS read-create
        STATUS current
        DESCRIPTION
            "The setting value of the 802.1p of ring's R-APS.
            The index of this table is hwConfigRingId."
        DEFVAL { 7 }
        ::= { hwErpsRingConfigEntry 11 }

    --ring status table
    -- 1.3.6.1.4.1.2011.5.25.256.1.3
    hwErpsRingStatusTable OBJECT-TYPE
        SYNTAX SEQUENCE OF HwErpsRingStatusEntry
        MAX-ACCESS not-accessible
        STATUS current
        DESCRIPTION
            "The table includes the status of ERPS rings.
            The index of this table is hwConfigRingId."
        ::= { hwErpsObjects 3 }


    -- 1.3.6.1.4.1.2011.5.25.256.1.3.1
    hwErpsRingStatusEntry OBJECT-TYPE
        SYNTAX HwErpsRingStatusEntry
        MAX-ACCESS not-accessible
        STATUS current
        DESCRIPTION
            "The table includes the status of ERPS rings.
            The index of this entry is hwConfigRingId."
        INDEX { hwConfigRingId }
        ::= { hwErpsRingStatusTable 1 }


    HwErpsRingStatusEntry ::=
        SEQUENCE {
               hwStatusWtrTimerRemainingValue
                Integer32,
               hwStatusGuardTimerRemainingValue
                Integer32,
               hwStatusHoldoffTimerRemainingValue
                Integer32,
               hwStatusMachineState
                   INTEGER,
               hwStatusTopoLastChangeTime
                   TimeTicks
                   }


    -- 1.3.6.1.4.1.2011.5.25.256.1.2.1.1
    hwStatusWtrTimerRemainingValue OBJECT-TYPE
        SYNTAX Integer32 (0..720)
        UNITS "seconds"
        MAX-ACCESS read-only
        STATUS current
        DESCRIPTION
            "The remaining value of the ring's wait to restore timer."
        ::= { hwErpsRingStatusEntry 1 }

    -- 1.3.6.1.4.1.2011.5.25.256.1.2.1.2
    hwStatusGuardTimerRemainingValue OBJECT-TYPE
        SYNTAX Integer32 (0..200)
        UNITS "centiseconds"
        MAX-ACCESS read-only
        STATUS current
        DESCRIPTION
            "The remaining value of the ring's guard timer."
        ::= { hwErpsRingStatusEntry 2 }

    -- 1.3.6.1.4.1.2011.5.25.256.1.2.1.3
    hwStatusHoldoffTimerRemainingValue OBJECT-TYPE
        SYNTAX Integer32 (0..100)
        UNITS "deciseconds"
        MAX-ACCESS read-only
        STATUS current
        DESCRIPTION
            "The remaining value of the ring's hold-off timer."
        ::= { hwErpsRingStatusEntry 3 }

    -- 1.3.6.1.4.1.2011.5.25.256.1.2.1.4
    hwStatusMachineState OBJECT-TYPE
        SYNTAX INTEGER
                {
                idle(1),
                protection(2),
                manualSwitch(3),
                forcedSwitch(4),
                pending(5)
                }
            MAX-ACCESS read-only
            STATUS current
            DESCRIPTION
            "The Finite-state machine's state of the ERPS ring.
             Options:
             1. idle(1)         - idle
             2. protection(2)   - protection
             3. manualSwitch(3) - manualSwitch
             4. forcedSwitch(4) - forcedSwitch
             5. pending(5)      - pending"
            ::= { hwErpsRingStatusEntry 4 }


    -- 1.3.6.1.4.1.2011.5.25.256.1.2.1.6
    hwStatusTopoLastChangeTime OBJECT-TYPE
        SYNTAX TimeTicks
            MAX-ACCESS read-only
            STATUS current
            DESCRIPTION
            "The time since last topology change of the ring."
            ::= { hwErpsRingStatusEntry 5 }


    --port config table
    --1.3.6.1.4.1.2011.5.25.256.1.3
    hwErpsPortConfigTable OBJECT-TYPE
        SYNTAX SEQUENCE OF HwErpsPortConfigEntry
        MAX-ACCESS not-accessible
        STATUS current
        DESCRIPTION
            "The table includes the configuration of ERPS ports.
            The indexes of this table are hwConfigRingId, hwConfigPortType, hwConfigPortId1, hwConfigPortId2, hwConfigPortId3, hwConfigPortId4."
        ::= { hwErpsObjects 4 }


    -- 1.3.6.1.4.1.2011.5.25.256.1.4.1
    hwErpsPortConfigEntry OBJECT-TYPE
        SYNTAX HwErpsPortConfigEntry
        MAX-ACCESS not-accessible
        STATUS current
        DESCRIPTION
            "The table includes the configuration of ERPS ports.
            The indexes of this entry are hwConfigRingId, hwConfigPortType, hwConfigPortId1, hwConfigPortId2, hwConfigPortId3, hwConfigPortId4."
        INDEX { hwConfigRingId, hwConfigPortType, hwConfigPortId1, hwConfigPortId2, hwConfigPortId3,
            hwConfigPortId4 }
        ::= { hwErpsPortConfigTable 1 }


    HwErpsPortConfigEntry ::=
        SEQUENCE {
            hwConfigPortType
                Unsigned32,
            hwConfigPortId1
                Unsigned32,
            hwConfigPortId2
                Unsigned32,
            hwConfigPortId3
                Unsigned32,
            hwConfigPortId4
                Unsigned32,
            hwConfigPortRowStatus
                RowStatus,
            hwConfigPortConfigRole
                Integer32
                  }

    -- 1.3.6.1.4.1.2011.5.25.256.1.4.1.1
    hwConfigPortType OBJECT-TYPE
        SYNTAX Unsigned32 (1)
        MAX-ACCESS not-accessible
        STATUS current
        DESCRIPTION
            "The port type.Currently ERPS just supports ethernet port and the value is 1."
        ::= { hwErpsPortConfigEntry 1 }


    -- 1.3.6.1.4.1.2011.5.25.256.1.4.1.2
    hwConfigPortId1 OBJECT-TYPE
        SYNTAX Unsigned32 (0..2147483647)
        MAX-ACCESS accessible-for-notify
        STATUS current
        DESCRIPTION
            "The port identifier1, when the hwConfigPortType is 1, the value of the object is the IfIndex of the port."
        ::= { hwErpsPortConfigEntry 2 }


    -- 1.3.6.1.4.1.2011.5.25.256.1.4.1.3
    hwConfigPortId2 OBJECT-TYPE
        SYNTAX Unsigned32 (0..2147483647)
        MAX-ACCESS not-accessible
        STATUS current
        DESCRIPTION
            "The port identifier2, currently it is not used and only for extension, should be set 0."
        ::= { hwErpsPortConfigEntry 3 }


    -- 1.3.6.1.4.1.2011.5.25.256.1.4.1.4
    hwConfigPortId3 OBJECT-TYPE
        SYNTAX Unsigned32 (0..2147483647)
        MAX-ACCESS not-accessible
        STATUS current
        DESCRIPTION
            "The port identifier3, currently it is not used and only for extension, should be set 0."
        ::= { hwErpsPortConfigEntry 4 }


    -- 1.3.6.1.4.1.2011.5.25.256.1.4.1.5
    hwConfigPortId4 OBJECT-TYPE
        SYNTAX Unsigned32 (0..2147483647)
        MAX-ACCESS not-accessible
        STATUS current
        DESCRIPTION
            "The port identifier4, currently it is not used and only for extension, should be set 0."
        ::= { hwErpsPortConfigEntry 5 }

    -- 1.3.6.1.4.1.2011.5.25.256.1.4.1.6
    hwConfigPortRowStatus OBJECT-TYPE
        SYNTAX RowStatus
        MAX-ACCESS read-create
        STATUS current
        DESCRIPTION
            "Operation of CreateAndGo can be used to have a port join the ERPS ring,
             and operation of Destroy be used to have a port leave the ERPS ring.
             Options:
             1. active(1)      -indicates the query operation
             2. createAndGo(4) -indicates creating an ERPS ring
             3. destroy(6)     -indicates deleting an ERPS ring"
        ::= { hwErpsPortConfigEntry 6 }

    -- 1.3.6.1.4.1.2011.5.25.256.1.4.1.7
    hwConfigPortConfigRole OBJECT-TYPE
        SYNTAX Integer32
        MAX-ACCESS read-create
        STATUS current
        DESCRIPTION
            "The configured port role:
            role                       value
            common                      0x10
            rplOwner                    0x21"
        ::= { hwErpsPortConfigEntry 7 }


    --port status table
    --1.3.6.1.4.1.2011.5.25.256.1.5
    hwErpsPortStatusTable OBJECT-TYPE
        SYNTAX SEQUENCE OF HwErpsPortStatusEntry
        MAX-ACCESS not-accessible
        STATUS current
        DESCRIPTION
            "The table includes the status of ERPS ports.
            The indexes of this table are hwConfigRingId, hwConfigPortType, hwConfigPortId1, hwConfigPortId2, hwConfigPortId3, hwConfigPortId4."
        ::= { hwErpsObjects 5 }


    -- 1.3.6.1.4.1.2011.5.25.256.1.5.1
    hwErpsPortStatusEntry OBJECT-TYPE
        SYNTAX HwErpsPortStatusEntry
        MAX-ACCESS not-accessible
        STATUS current
        DESCRIPTION
            "The table includes the status of ERPS ports.
            The indexes of this entry are hwConfigRingId, hwConfigPortType, hwConfigPortId1, hwConfigPortId2, hwConfigPortId3, hwConfigPortId4."
        INDEX { hwConfigRingId, hwConfigPortType, hwConfigPortId1, hwConfigPortId2, hwConfigPortId3,
        hwConfigPortId4 }
        ::= { hwErpsPortStatusTable 1 }


    HwErpsPortStatusEntry ::=
        SEQUENCE {
            hwPortStatusActiveRole
                Integer32,
            hwPortStatusSignalStatus
                INTEGER,
            hwPortStatusFwdStatus
                INTEGER
                }

    -- 1.3.6.1.4.1.2011.5.25.256.1.5.1.1
    hwPortStatusActiveRole OBJECT-TYPE
        SYNTAX Integer32
        MAX-ACCESS read-only
        STATUS current
        DESCRIPTION
            "The active port role:
            role                       value
            common                      0x10
            rplOwner                    0x21"
        ::= { hwErpsPortStatusEntry 1 }

    -- 1.3.6.1.4.1.2011.5.25.256.1.5.1.7
    hwPortStatusSignalStatus OBJECT-TYPE
        SYNTAX INTEGER
                {
                failed(1),
                nonFailed(2)
                }
        MAX-ACCESS read-only
        STATUS current
        DESCRIPTION
                "The signal status of the port:
                 Options:
                 1. failed(1)    - Failed
                 2. nonFailed(2) - NonFailed"
            ::= { hwErpsPortStatusEntry 2 }


    -- 1.3.6.1.4.1.2011.5.25.256.1.5.1.8
    hwPortStatusFwdStatus OBJECT-TYPE
            SYNTAX INTEGER
                {
                discarding(1),
                forwarding(2)
                }
            MAX-ACCESS read-only
            STATUS current
            DESCRIPTION
                "The forwarding status of the port:
                 Options:
                 1. discarding(1) - discarding
                 2. forwarding(2) - forwarding"
            ::= { hwErpsPortStatusEntry 3 }


    --port Statistics table
    --1.3.6.1.4.1.2011.5.25.256.1.6
    hwErpsPortStatisticsTable OBJECT-TYPE
        SYNTAX SEQUENCE OF HwErpsPortStatisticsEntry
        MAX-ACCESS not-accessible
        STATUS current
        DESCRIPTION
            "The table includes the statistics of ERPS ports.
            The indexes of this table are hwConfigRingId, hwConfigPortType, hwConfigPortId1, hwConfigPortId2, hwConfigPortId3, hwConfigPortId4."
        ::= { hwErpsObjects 6 }


    -- 1.3.6.1.4.1.2011.5.25.256.1.6.1
    hwErpsPortStatisticsEntry OBJECT-TYPE
        SYNTAX HwErpsPortStatisticsEntry
        MAX-ACCESS not-accessible
        STATUS current
        DESCRIPTION
            "The table includes the statistics of ERPS ports.
            The indexes of this entry are hwConfigRingId, hwConfigPortType, hwConfigPortId1, hwConfigPortId2, hwConfigPortId3, hwConfigPortId4."
        INDEX { hwConfigRingId, hwConfigPortType, hwConfigPortId1, hwConfigPortId2, hwConfigPortId3, hwConfigPortId4}
        ::= { hwErpsPortStatisticsTable 1 }


    HwErpsPortStatisticsEntry ::=
        SEQUENCE {
            hwRxRapsSfPktCnt
                Counter32,
            hwTxRapsSfPktCnt
                Counter32,
            hwRxRapsNrPktCnt
                Counter32,
            hwTxRapsNrPktCnt
                Counter32,
            hwRxRapsNrRbPktCnt
                Counter32,
            hwTxRapsNrRbPktCnt
                Counter32
             }


    -- 1.3.6.1.4.1.2011.5.25.256.1.6.1.1
    hwRxRapsSfPktCnt OBJECT-TYPE
        SYNTAX Counter32
        MAX-ACCESS read-only
        STATUS current
        DESCRIPTION
            "The number of received RAPS SF packets."
        ::= { hwErpsPortStatisticsEntry 1 }


    -- 1.3.6.1.4.1.2011.5.25.256.1.6.1.2
    hwTxRapsSfPktCnt OBJECT-TYPE
        SYNTAX Counter32
        MAX-ACCESS read-only
        STATUS current
        DESCRIPTION
            "The number of transmitted RAPS SF packets."
        ::= { hwErpsPortStatisticsEntry 2 }


    -- 1.3.6.1.4.1.2011.5.25.256.1.6.1.3
    hwRxRapsNrPktCnt OBJECT-TYPE
        SYNTAX Counter32
        MAX-ACCESS read-only
        STATUS current
        DESCRIPTION
                "The number of received RAPS NR packets."
        ::= { hwErpsPortStatisticsEntry 3 }


    -- 1.3.6.1.4.1.2011.5.25.256.1.6.1.4
    hwTxRapsNrPktCnt OBJECT-TYPE
        SYNTAX Counter32
        MAX-ACCESS read-only
        STATUS current
        DESCRIPTION
                "The number of transmitted RAPS NR packets."
        ::= { hwErpsPortStatisticsEntry 4 }


    -- 1.3.6.1.4.1.2011.5.25.256.1.6.1.5
    hwRxRapsNrRbPktCnt OBJECT-TYPE
        SYNTAX Counter32
        MAX-ACCESS read-only
        STATUS current
        DESCRIPTION
                "The number of received RAPS NRRB packets."
        ::= { hwErpsPortStatisticsEntry 5 }


    -- 1.3.6.1.4.1.2011.5.25.256.1.6.1.6
    hwTxRapsNrRbPktCnt OBJECT-TYPE
        SYNTAX Counter32
        MAX-ACCESS read-only
        STATUS current
        DESCRIPTION
                "The number of transmitted RAPS NRRB packets."
        ::= { hwErpsPortStatisticsEntry 6 }

    -- ERPS port is in forwarding state trap
    -- 1.3.6.1.4.1.2011.5.25.256.1.7
    hwErpsPortStateForwarding  NOTIFICATION-TYPE
        OBJECTS {
            hwConfigRingId,
            hwConfigPortId1
            }
        STATUS  current
        DESCRIPTION
            "ERPS port is in forwarding state, when ERPS port change from discarding to forwarding.
            "
        ::= { hwErpsObjects 7 }

    -- ERPS port is in discarding state trap
    -- 1.3.6.1.4.1.2011.5.25.256.1.8
    hwErpsPortStateDiscarding  NOTIFICATION-TYPE
        OBJECTS {
            hwConfigRingId,
            hwConfigPortId1
            }
        STATUS  current
        DESCRIPTION
            "ERPS port is in discarding state, when ERPS port change from forwarding to discarding.
            "
        ::= { hwErpsObjects 8 }

    -- Inner forwarding fault trigger shutdown ERPS port switch
    -- 1.3.6.1.4.1.2011.5.25.256.1.9
    hwErpsInnerForwardingFaultTriggerSwitch OBJECT-TYPE
        SYNTAX  INTEGER {
            enable(1),
            disable(2)
            }
		MAX-ACCESS  read-write
        STATUS      current
        DESCRIPTION
            "Describes the inner forwarding fault trigger shutdown ERPS port switch.
             Options: 
             1. enable(1)  - enable inner forwarding fault trigger shutdown ERPS port
             2. disable(2) - disable inner forwarding fault trigger shutdown ERPS port
             Default: disable(2)
            "
        ::= { hwErpsObjects 9 }

    --Inner forwarding fault trigger shutdown ERPS port information table
    -- 1.3.6.1.4.1.2011.5.25.256.1.10
    hwErpsInnerForwardingFaultTriggerTable OBJECT-TYPE
        SYNTAX SEQUENCE OF HwErpsInnerForwardingFaultTriggerEntry
        MAX-ACCESS not-accessible
        STATUS current
        DESCRIPTION
            "The table includes the inner forwarding fault trigger shutdown ERPS ports.
            The index of this table is hwErpsInnerForwardingFaultTriggerRingId."
        ::= { hwErpsObjects 10 }

    -- 1.3.6.1.4.1.2011.5.25.256.1.10.1
    hwErpsInnerForwardingFaultTriggerEntry OBJECT-TYPE
        SYNTAX HwErpsInnerForwardingFaultTriggerEntry
        MAX-ACCESS not-accessible
        STATUS current
        DESCRIPTION
            "The table includes the inner forwarding fault trigger shutdown ERPS ports.
            The index of this entry is hwErpsInnerForwardingFaultTriggerRingId."
        INDEX { hwErpsInnerForwardingFaultTriggerRingId }
        ::= { hwErpsInnerForwardingFaultTriggerTable 1 }

    HwErpsInnerForwardingFaultTriggerEntry ::=
        SEQUENCE {
               hwErpsInnerForwardingFaultTriggerRingId
                Integer32,
               hwErpsInnerForwardingFaultTriggerTime
                DateAndTime,
               hwErpsInnerForwardingFaultTriggerPortIfindex
                Integer32
                 }

    -- 1.3.6.1.4.1.2011.5.25.256.1.10.1.1
    hwErpsInnerForwardingFaultTriggerRingId OBJECT-TYPE
        SYNTAX Integer32 (1..255)
        MAX-ACCESS not-accessible
        STATUS current
        DESCRIPTION
            "ERPS ring Identifier."
        ::= { hwErpsInnerForwardingFaultTriggerEntry 1 }

    -- 1.3.6.1.4.1.2011.5.25.256.1.10.1.2
    hwErpsInnerForwardingFaultTriggerTime OBJECT-TYPE
        SYNTAX DateAndTime
        MAX-ACCESS read-only
        STATUS current
        DESCRIPTION
            "Indicates the time when inner forwarding fault trigger shutdown ERPS ports."
        ::= { hwErpsInnerForwardingFaultTriggerEntry 2 }

    -- 1.3.6.1.4.1.2011.5.25.256.1.10.1.3
    hwErpsInnerForwardingFaultTriggerPortIfindex OBJECT-TYPE
        SYNTAX Integer32
        MAX-ACCESS read-only
        STATUS current
        DESCRIPTION
            "The meaning of hwErpsInnerForwardingFaultTriggerPortIfindex is the same as that of ifindex in standard IF MIB,
             which contains frame ID,slot ID and port ID.
            "
        ::= { hwErpsInnerForwardingFaultTriggerEntry 3 }

    -- 1.3.6.1.4.1.2011.5.25.256.2
    hwErpsGroups OBJECT IDENTIFIER ::= { hwErpsMIB 2 }


    -- 1.3.6.1.4.1.2011.5.25.256.2.1
    hwErpsGlobalInfoGroup OBJECT-GROUP
        OBJECTS { hwErpsGlobalResetRapsPktCnt }
        STATUS current
        DESCRIPTION
            "The group of global information."
        ::= { hwErpsGroups 1 }


    -- 1.3.6.1.4.1.2011.5.25.256.2.2
    hwErpsRingConfigInfoGroup OBJECT-GROUP
        OBJECTS { hwConfigRingRowStatus, hwConfigDescription, hwConfigControlVlanId, hwConfigProtectedInstanceList,
            hwConfigWtrTimerSettingValue, hwConfigGuardTimerSettingValue, hwConfigHoldoffTimerSettingValue,
            hwConfigResetRapsPktCnt, hwConfigRapsMel}
        STATUS current
        DESCRIPTION
            "The group of ring configuration."
        ::= { hwErpsGroups 2 }

    -- 1.3.6.1.4.1.2011.5.25.256.2.3
    hwErpsRingStatusInfoGroup OBJECT-GROUP
        OBJECTS { hwStatusWtrTimerRemainingValue, hwStatusGuardTimerRemainingValue, hwStatusHoldoffTimerRemainingValue,
            hwStatusMachineState, hwStatusTopoLastChangeTime }
        STATUS current
        DESCRIPTION
            "The group of ring status."
        ::= { hwErpsGroups 3 }

    -- 1.3.6.1.4.1.2011.5.25.256.2.4
    hwErpsPortConfigInfoGroup OBJECT-GROUP
        OBJECTS { hwConfigPortRowStatus, hwConfigPortConfigRole }
        STATUS current
        DESCRIPTION
            "The group of port configuration."
        ::= { hwErpsGroups 4 }


    -- 1.3.6.1.4.1.2011.5.25.256.2.5
    hwErpsPortStatusInfoGroup OBJECT-GROUP
        OBJECTS { hwPortStatusActiveRole, hwPortStatusSignalStatus, hwPortStatusFwdStatus }
        STATUS current
        DESCRIPTION
            "The group of port status."
        ::= { hwErpsGroups 5 }


    -- 1.3.6.1.4.1.2011.5.25.256.2.6
    hwErpsPortStatisticsInfoGroup OBJECT-GROUP
        OBJECTS { hwRxRapsSfPktCnt, hwTxRapsSfPktCnt, hwRxRapsNrPktCnt, hwTxRapsNrPktCnt,
            hwRxRapsNrRbPktCnt, hwTxRapsNrRbPktCnt }
        STATUS current
        DESCRIPTION
            "The group of port information."
        ::= { hwErpsGroups 6 }

    END

--
-- HUAWEI-ERPS-MIBv2.my
--
