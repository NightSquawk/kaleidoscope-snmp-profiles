--
-- ISM-STORAGE-SVC-MIB.mib
-- MIB generated by MG-SOFT Visual MIB Builder Version 3.0 Build 253
-- Wednesday, June 29, 2016 at 16:08:37
--

--  ISM-STORAGE-SVC-MIB.mib
-- MIB generated by MG-SOFT Visual MIB Builder Version 4.0 Build 347
-- Thursday, March 27, 2014 at 11:54:11
-- 

	ISM-STORAGE-SVC-MIB DEFINITIONS ::= BEGIN
 
		IMPORTS
			OBJECT-GROUP, MODULE-COMPLIANCE			
				FROM SNMPv2-CONF			
			enterprises, IpAddress, Integer32, Unsigned32, 
			Counter64, OBJECT-TYPE, MODULE-IDENTITY			
				FROM SNMPv2-SMI			
			DisplayString, RowStatus, TEXTUAL-CONVENTION			
				FROM SNMPv2-TC;
	
	
--  September 17, 2008 at 16:28 GMT
-- April 07, 2013 at 19:15 GMT
		huaweistorage MODULE-IDENTITY 
			LAST-UPDATED "201304071915Z"		-- April 07, 2013 at 19:15 GMT
			ORGANIZATION 
				"Huawei Technologies Co.,Ltd."
			CONTACT-INFO 
				"Huawei Industrial Base
				Bantian, Longgang
				Shenzhen 518129
				People's Republic of China
				Website: http://www.huawei.com
				Email: support@huawei.com"
			DESCRIPTION 
				"The ISM-STORAGE-SVC-MIB contains objects to query physical storage module informations."
			REVISION "201304071915Z"		-- April 07, 2013 at 19:15 GMT
			DESCRIPTION
				" "
			REVISION "200809171628Z"
			DESCRIPTION 
				"Description."
			::= { enterprises 34774 }
		
	
--
-- Textual conventions
--
	
--  Textual conventions
-- 
		NodeCodeString ::= TEXTUAL-CONVENTION
			DISPLAY-HINT 
				"255a"
			STATUS current
			DESCRIPTION 
				"characters in length."
			SYNTAX OCTET STRING (SIZE (15..17))
			
	
--
-- Node definitions
--
	
--  Node definitions
-- 
		-- 1.3.6.1.4.1.34774.4
		hwStorage OBJECT IDENTIFIER ::= { huaweistorage 4 }
		
		-- 1.3.6.1.4.1.34774.4.1
		hwISM OBJECT IDENTIFIER ::= { hwStorage 1 }
		
		-- 1.3.6.1.4.1.34774.4.1.1
		common OBJECT IDENTIFIER ::= { hwISM 1 }
		
		-- 1.3.6.1.4.1.34774.4.1.1.1
		deviceId OBJECT-TYPE
			SYNTAX DisplayString
			MAX-ACCESS read-only
			STATUS current
			DESCRIPTION
				"Device serial number, namely,unique identifier of the device."
			::= { common 1 }
		
		-- 1.3.6.1.4.1.34774.4.1.1.2
		deviceType OBJECT-TYPE
			SYNTAX Integer32
			MAX-ACCESS read-only
			STATUS current
			DESCRIPTION
				"Type of the storage device. For details, see:
				0 V1500
				1 V1800
				2 S2100
				3 S2300
				4 S5100
				5 S5300
				6 S5500
				7 S5600
				8 VIS
				9 S2600
				10 S6800E
				11 V1500N
				12 S2300E
				13 COMMON
				15 N8000
				16 S6900
				17 S3900
				18 S5500T
				19 S5600T
				20 S6800T
				21 S6900-M100
				22 S3900-M200
				23 S3900-M300
				24 S5900-M100
				25 S8100
				26 S5800T
				27 V1600N
				28 S5900-M200
				29 N8001
				30 S2600T
				31 S8000-I
				32 Dorado5100
				33 T3200
				34 T3500
				35 N8000-R710
				36 N8000-C2
				40 8000-C2-SYMC
				41 VTL
				42 S2900
				43 S2200T
				44 Dorado2100_G2
				45 VIS 6000
				46 HVS85T
				47 HVS88T
				48 9000
				49 T3200 G2
				50 T3500 G2
				51 T3200 G3
				52 T3500 G3
				53 S5700
				54 CE6800
				55 CE12800
				56 18800F
				57 18500
				58 18800
				60 Dorado2100
				61 6800 V3
				62 6900 V3
				63 5600 V3
				64 5800 V3
				65 T3200 G3
				66 WUSHAN_SQL
				67 WUSHAN_HD
				68 5500 V3
				69 2600 V3
				70 5300 V3
				71 2800 V3
				72 18500 V3
				73 18800 V3
				74 High-Density Controller Enclosure
				78 2200 V3
				79 5100 V3
				82 2600 V3 for Video
				84 2600F V3
				85 5500F V3
				86 5600F V3
				87 5800F V3
				88 6800F V3
				89 18500F V3
				90 18800F V3
				92 2800 V5
				93 5300 V5
				94 5300F V5
				95 5500 V5
				96 5500F V5
				97 5600 V5
				98 5600F V5
				99 5800 V5
				100 5800F V5
				101 6800 V5
				102 6800F V5
				103 18500 V5
				104 18500F V5
				105 18800 V5
				106 18800F V5
				107 5500 V5 Elite
				108 2100 V3
				112 2200V3 Enhanced
				113 2600V3 Enhanced
				114 2600FV3 Enhanced
				115 5300V5 Enhanced
				116 5110 V5
				117 5110F V5
				118 5210 V5
				119 5210F V5
				120 5310 V5
				121 5310F V5
				122 5510 V5
				123 5510F V5
				124 5610 V5
				125 5610F V5
				126 5810 V5
				127 5810F V5
				128 6810 V5
				129 6810F V5
				130 18510 V5
				131 18510F V5
				132 18810 V5
				133 18810F V5
				134 5210 V5 Enhanced
				135 5210F V5 Enhanced
				139 5110 V5 Enhanced
				140 5110F V5 Enhanced
				141 2600 V5
				401 N5000
				800 VIS8200
				801 VIS8400
				802 VIS8600
				803 VIS8800
				804 Cloud Protecto
				805 Dorado 5000
				806 Dorado 6000
				807 Dorado 18000"
			::= { common 2 }
		
		-- 1.3.6.1.4.1.34774.4.1.1.3
		status OBJECT-TYPE
			SYNTAX Integer32
			MAX-ACCESS read-only
			STATUS current
			DESCRIPTION
				"System operating status. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { common 3 }
		
		-- 1.3.6.1.4.1.34774.4.1.1.4
		usedCapacity OBJECT-TYPE
			SYNTAX Counter64
			MAX-ACCESS read-only
			STATUS current
			DESCRIPTION
				"Used capacity of the storage device. The unit is MB."
			::= { common 4 }
		
		-- 1.3.6.1.4.1.34774.4.1.1.5
		totalCapacity OBJECT-TYPE
			SYNTAX Counter64
			MAX-ACCESS read-only
			STATUS current
			DESCRIPTION
				"Total capacity of the storage device. The unit is MB."
			::= { common 5 }
		
		-- 1.3.6.1.4.1.34774.4.1.1.6
		version OBJECT-TYPE
			SYNTAX DisplayString
			MAX-ACCESS read-only
			STATUS current
			DESCRIPTION
				"Device version."
			::= { common 6 }

                -- 1.3.6.1.4.1.34774.4.1.1.7
		hardware OBJECT-TYPE
			SYNTAX DisplayString
			MAX-ACCESS read-only
			STATUS deprecated
			DESCRIPTION
				"Device hardware."
			::= { common 7 }

		
		-- 1.3.6.1.4.1.34774.4.1.19
		hwStorageService OBJECT IDENTIFIER ::= { hwISM 19 }
		
		-- 1.3.6.1.4.1.34774.4.1.19.8
		hwStoragePhysicalModule OBJECT IDENTIFIER ::= { hwStorageService 8 }
		
		-- 1.3.6.1.4.1.34774.4.1.19.8.7
		hwStorageFCPortTable OBJECT-TYPE
			SYNTAX SEQUENCE OF HwStorageFCPortEntry
			MAX-ACCESS not-accessible
			STATUS current
			DESCRIPTION
				"This table provides information about FC ports."
			::= { hwStoragePhysicalModule 7 }
		
		-- 1.3.6.1.4.1.34774.4.1.19.8.7.1
		hwStorageFCPortEntry OBJECT-TYPE
			SYNTAX HwStorageFCPortEntry
			MAX-ACCESS not-accessible
			STATUS current
			DESCRIPTION
				"A table containing the part component."
			INDEX { hwStorageFCPortIfIndex }
			::= { hwStorageFCPortTable 1 }
		
		HwStorageFCPortEntry ::=
			SEQUENCE { 
				hwStorageFCPortIfIndex
					Unsigned32,
				hwStorageFCPortBoardIfIndex
					Unsigned32,
				hwStorageFCPortID
					Unsigned32,
				hwStorageFCPortStatus
					INTEGER,
				hwStorageFCPortConfigRate
					INTEGER,
				hwStorageFCPortMode
					INTEGER,
				hwStorageFCPortWWN
					OCTET STRING,
				hwStorageFCPortLogicType
					INTEGER,
				hwStorageFCPortSpeedRate
					INTEGER
			 }

		-- 1.3.6.1.4.1.34774.4.1.19.8.7.1.1
		hwStorageFCPortIfIndex OBJECT-TYPE
			SYNTAX Unsigned32
			MAX-ACCESS read-only
			STATUS current
			DESCRIPTION
				"Index to the FC host port."
			::= { hwStorageFCPortEntry 1 }
		
		-- 1.3.6.1.4.1.34774.4.1.19.8.7.1.2
		hwStorageFCPortBoardIfIndex OBJECT-TYPE
			SYNTAX Unsigned32
			MAX-ACCESS read-only
			STATUS current
			DESCRIPTION
				"Index to the board of the FC host port."
			::= { hwStorageFCPortEntry 2 }
		
		-- 1.3.6.1.4.1.34774.4.1.19.8.7.1.3
		hwStorageFCPortID OBJECT-TYPE
			SYNTAX Unsigned32
			MAX-ACCESS read-only
			STATUS current
			DESCRIPTION
				"ID of the FC host port.."
			::= { hwStorageFCPortEntry 3 }
		
		-- 1.3.6.1.4.1.34774.4.1.19.8.7.1.4
		hwStorageFCPortStatus OBJECT-TYPE
			SYNTAX INTEGER
				{
				linkdown(0),
				linkup(1),
				fault(2)
				}
			MAX-ACCESS read-only
			STATUS current
			DESCRIPTION
				"Status of the FC host port.
				The value can be:
				0: Disconnected
				1: Connected
				2: Faulty"
			::= { hwStorageFCPortEntry 4 }
		
		-- 1.3.6.1.4.1.34774.4.1.19.8.7.1.5
		hwStorageFCPortConfigRate OBJECT-TYPE
			SYNTAX INTEGER
				{
				auto(0),
				gbps1(1),
				gbps2(2),
				gbps4(4),
				gbps8(8),
				gbps16(16)
				}
			MAX-ACCESS read-write
			STATUS current
			DESCRIPTION
				"Working Rate of the FC host port, (unit: 1000Mbit/s). The value can be:
				0: Auto
				1: GBPS-1
				2: GBPS-2
				4: GBPS-4
				8: GBPS-8
				16: GBPS-16
				The Current rate can be 1 Gbit/s, 2 Gbit/s, 4 Gbit/s, 8 Gbit/s, or 16 Gbit/s. The conversion unit is 1000. 0 indicates auto-negotiation. -1 indicates invalid.
				"
			::= { hwStorageFCPortEntry 5 }
		
		-- 1.3.6.1.4.1.34774.4.1.19.8.7.1.6
		hwStorageFCPortMode OBJECT-TYPE
			SYNTAX INTEGER
				{
				fabric(1),
				publicloop(2),
				pointtopoint(3)
				}
			MAX-ACCESS read-write
			STATUS current
			DESCRIPTION
				"Mode of the FC host port. The value can be:
				-1: Invalid
				0: fabric
				1: FC-AL
				2: P2P
				3: Auto"
			::= { hwStorageFCPortEntry 6 }
		
		-- 1.3.6.1.4.1.34774.4.1.19.8.7.1.7
		hwStorageFCPortWWN OBJECT-TYPE
			SYNTAX OCTET STRING
			MAX-ACCESS read-only
			STATUS current
			DESCRIPTION
				"WWN of the FC host port."
			::= { hwStorageFCPortEntry 7 }
		
		-- 1.3.6.1.4.1.34774.4.1.19.8.7.1.8
		hwStorageFCPortLogicType OBJECT-TYPE
			SYNTAX INTEGER
				{
				service(1),
				ibc(2),
				ibs(3),
				expansion(4),
				management(5),
				upsmanagement(6),
				maintenance(8)
				}
			MAX-ACCESS read-only
			STATUS current
			DESCRIPTION
				"Logical type of FC host port. The value can be:
				 1: service
				 2: ibc
				 3: ibs
				 4: expansion
				 5: management
				 6: upsmanagement
				 8: maintenance"
			::= { hwStorageFCPortEntry 8 }
		
		-- 1.3.6.1.4.1.34774.4.1.19.8.7.1.9
		hwStorageFCPortSpeedRate OBJECT-TYPE
			SYNTAX INTEGER
				{
				auto(0),
				gbps1(1),
				gbps2(2),
				gbps4(4),
				gbps8(8),
				gbps16(16)
				}
			MAX-ACCESS read-only
			STATUS current
			DESCRIPTION
				"Speed rate of FC host port(unit: Mbit/s). If the parameter value is -1, this parameter is invalid."
			::= { hwStorageFCPortEntry 9 }
		
		-- 1.3.6.1.4.1.34774.4.1.19.8.8
		hwStorageSASPortTable OBJECT-TYPE
			SYNTAX SEQUENCE OF HwStorageSASPortEntry
			MAX-ACCESS not-accessible
			STATUS current
			DESCRIPTION
				"This table provides information about SAS ports."
			::= { hwStoragePhysicalModule 8 }
		
		-- 1.3.6.1.4.1.34774.4.1.19.8.8.1
		hwStorageSASPortEntry OBJECT-TYPE
			SYNTAX HwStorageSASPortEntry
			MAX-ACCESS not-accessible
			STATUS current
			DESCRIPTION
				"A table containing the part component."
			INDEX { hwStorageSASPortIfIndex }
			::= { hwStorageSASPortTable 1 }
		
		HwStorageSASPortEntry ::=
			SEQUENCE { 
				hwStorageSASPortIfIndex
					Unsigned32,
				hwStorageSASPortBoardIfIndex
					Unsigned32,
				hwStorageSASPortID
					Unsigned32,
				hwStorageSASPortStatus
					INTEGER,
				hwStorageSASPortConfigRate
					INTEGER,
				hwStorageSASPortWWN
					OCTET STRING,
				hwStorageSASPortLogicType
					INTEGER,
				hwStorageSASPortSpeedRate
					INTEGER
			 }

		-- 1.3.6.1.4.1.34774.4.1.19.8.8.1.1
		hwStorageSASPortIfIndex OBJECT-TYPE
			SYNTAX Unsigned32
			MAX-ACCESS read-only
			STATUS current
			DESCRIPTION
				"Index to the SAS host port."
			::= { hwStorageSASPortEntry 1 }
		
		-- 1.3.6.1.4.1.34774.4.1.19.8.8.1.2
		hwStorageSASPortBoardIfIndex OBJECT-TYPE
			SYNTAX Unsigned32
			MAX-ACCESS read-only
			STATUS current
			DESCRIPTION
				"Index to the board of the SAS host port."
			::= { hwStorageSASPortEntry 2 }
		
		-- 1.3.6.1.4.1.34774.4.1.19.8.8.1.3
		hwStorageSASPortID OBJECT-TYPE
			SYNTAX Unsigned32
			MAX-ACCESS read-only
			STATUS current
			DESCRIPTION
				"ID of the SAS host port."
			::= { hwStorageSASPortEntry 3 }
		
		-- 1.3.6.1.4.1.34774.4.1.19.8.8.1.4
		hwStorageSASPortStatus OBJECT-TYPE
			SYNTAX INTEGER
				{
				linkdown(0),
				linkup(1),
				fault(2)
				}
			MAX-ACCESS read-only
			STATUS current
			DESCRIPTION
				"Status of the SAS host port. The value can be:
				0: disconnected
				1: connected
				2: faulty"
			::= { hwStorageSASPortEntry 4 }
		
		-- 1.3.6.1.4.1.34774.4.1.19.8.8.1.5
		hwStorageSASPortConfigRate OBJECT-TYPE
			SYNTAX INTEGER
				{
				gbps15(1500),
				gbps30(3000),
				gbps60(6000)
				}
			MAX-ACCESS read-only
			STATUS current
			DESCRIPTION
				"Rate of the SAS host port. (unit: 1000 Mbit/s). If the parameter value is -1, this parameter is invalid."
			::= { hwStorageSASPortEntry 5 }
		
		-- 1.3.6.1.4.1.34774.4.1.19.8.8.1.6
		hwStorageSASPortWWN OBJECT-TYPE
			SYNTAX OCTET STRING
			MAX-ACCESS read-only
			STATUS current
			DESCRIPTION
				"WWN of the SAS host port."
			::= { hwStorageSASPortEntry 6 }
		
		-- 1.3.6.1.4.1.34774.4.1.19.8.8.1.7
		hwStorageSASPortLogicType OBJECT-TYPE
			SYNTAX INTEGER
				{
				service(1),
				ibc(2),
				ibs(3),
				expansion(4),
				management(5),
				upsmanagement(6),
				maintenance(8)
				}
			MAX-ACCESS read-only
			STATUS current
			DESCRIPTION
				"Logical type of SAShost port. The value can be:
				 1: service
				 2: ibc
				 3: ibs
				 4: expansion
				 5: management
				 6: upsmanagement
				 8: maintenance"
			::= { hwStorageSASPortEntry 7 }
		
		-- 1.3.6.1.4.1.34774.4.1.19.8.8.1.8
		hwStorageSASPortSpeedRate OBJECT-TYPE
			SYNTAX INTEGER
				{
				gbps15(1500),
				gbps30(3000),
				gbps60(6000)
				}
			MAX-ACCESS read-only
			STATUS current
			DESCRIPTION
				"Speed rate of SAS host port. The value can be:
				 1: Gbps15
				 2: Gbps30
				 3: Gbps60"
			::= { hwStorageSASPortEntry 8 }
		
		-- 1.3.6.1.4.1.34774.4.1.19.8.9
		hwStorageISCSIPortTable OBJECT-TYPE
			SYNTAX SEQUENCE OF HwStorageISCSIPortEntry
			MAX-ACCESS not-accessible
			STATUS current
			DESCRIPTION
				"This table provides information about iSCSI ports."
			::= { hwStoragePhysicalModule 9 }
		
		-- 1.3.6.1.4.1.34774.4.1.19.8.9.1
		hwStorageISCSIPortEntry OBJECT-TYPE
			SYNTAX HwStorageISCSIPortEntry
			MAX-ACCESS not-accessible
			STATUS current
			DESCRIPTION
				"A table containing the part component."
			INDEX { hwStorageISCSIPortIfIndex }
			::= { hwStorageISCSIPortTable 1 }
		
		HwStorageISCSIPortEntry ::=
			SEQUENCE { 
				hwStorageISCSIPortIfIndex
					Unsigned32,
				hwStorageISCSIPortBoardIfIndex
					Unsigned32,
				hwStorageISCSIPortID
					Unsigned32,
				hwStorageISCSIPortStatus
					INTEGER,
				hwStorageISCSIPortIP
					IpAddress,
				hwStorageISCSIPortNetMask
					IpAddress,
				hwStorageISCSIPortBindMode
					Integer32,
				hwStorageISCSIPortLogicType
					INTEGER
			 }

		-- 1.3.6.1.4.1.34774.4.1.19.8.9.1.1
		hwStorageISCSIPortIfIndex OBJECT-TYPE
			SYNTAX Unsigned32
			MAX-ACCESS read-only
			STATUS current
			DESCRIPTION
				"Index to the iSCSI host port."
			::= { hwStorageISCSIPortEntry 1 }
		
		-- 1.3.6.1.4.1.34774.4.1.19.8.9.1.2
		hwStorageISCSIPortBoardIfIndex OBJECT-TYPE
			SYNTAX Unsigned32
			MAX-ACCESS read-only
			STATUS current
			DESCRIPTION
				"Index to the board of the iSCSI host port."
			::= { hwStorageISCSIPortEntry 2 }
		
		-- 1.3.6.1.4.1.34774.4.1.19.8.9.1.3
		hwStorageISCSIPortID OBJECT-TYPE
			SYNTAX Unsigned32
			MAX-ACCESS read-only
			STATUS current
			DESCRIPTION
				"ID of the iSCSI host port."
			::= { hwStorageISCSIPortEntry 3 }
		
		-- 1.3.6.1.4.1.34774.4.1.19.8.9.1.4
		hwStorageISCSIPortStatus OBJECT-TYPE
			SYNTAX INTEGER
				{
				linkdown(0),
				linkup(1),
				fault(2)
				}
			MAX-ACCESS read-only
			STATUS current
			DESCRIPTION
				"Status of the iSCSI host port. The value can be:
				0: disconnected
				1: connected
				2: faulty"
			::= { hwStorageISCSIPortEntry 4 }
		
		-- 1.3.6.1.4.1.34774.4.1.19.8.9.1.5
		hwStorageISCSIPortIP OBJECT-TYPE
			SYNTAX IpAddress
			MAX-ACCESS read-write
			STATUS current
			DESCRIPTION
				"IP address of the iSCSI host port."
			::= { hwStorageISCSIPortEntry 5 }
		
		-- 1.3.6.1.4.1.34774.4.1.19.8.9.1.6
		hwStorageISCSIPortNetMask OBJECT-TYPE
			SYNTAX IpAddress
			MAX-ACCESS read-write
			STATUS current
			DESCRIPTION
				"Mask of the iSCSI host port."
			::= { hwStorageISCSIPortEntry 6 }
		
		-- 1.3.6.1.4.1.34774.4.1.19.8.9.1.7
		hwStorageISCSIPortBindMode OBJECT-TYPE
			SYNTAX Integer32
			MAX-ACCESS read-only
			STATUS current
			DESCRIPTION
				"Bind mode of the iSCSI host port, not used currently."
			::= { hwStorageISCSIPortEntry 7 }
		
		-- 1.3.6.1.4.1.34774.4.1.19.8.9.1.8
		hwStorageISCSIPortLogicType OBJECT-TYPE
			SYNTAX INTEGER
				{
				service(1),
				ibc(2),
				ibs(3),
				expansion(4),
				management(5),
				upsmanagement(6),
				maintenance(8)
				}
			MAX-ACCESS read-only
			STATUS current
			DESCRIPTION
				"Logical type of ISCSI host port. The value can be:
				 1: service
				 2: ibc
				 3: ibs
				 4: expansion
				 5: management
				 6: upsmanagement
				 8: maintenance"
			::= { hwStorageISCSIPortEntry 8 }
		
		-- 1.3.6.1.4.1.34774.4.1.19.8.11
		hwStorageFrontEndHostPortTable OBJECT-TYPE
			SYNTAX SEQUENCE OF HwStorageFrontEndHostPortEntry
			MAX-ACCESS not-accessible
			STATUS current
			DESCRIPTION
				"This table provides basic information about the SAS, FC, iSCSI ports whose performance statistics can be collected."
			::= { hwStoragePhysicalModule 11 }
		
		-- 1.3.6.1.4.1.34774.4.1.19.8.11.1
		hwStorageFrontEndHostPortEntry OBJECT-TYPE
			SYNTAX HwStorageFrontEndHostPortEntry
			MAX-ACCESS not-accessible
			STATUS current
			DESCRIPTION
				"A table containing the part component."
			INDEX { hwStorageFrontEndHostPortIfIndex }
			::= { hwStorageFrontEndHostPortTable 1 }
		
		HwStorageFrontEndHostPortEntry ::=
			SEQUENCE { 
				hwStorageFrontEndHostPortIfIndex
					Unsigned32,
				hwStorageFrontEndHostPortType
					INTEGER,
				hwStorageFrontEndHostPortStatus
					INTEGER,
				hwStorageFrontEndHostPortPhysAddress
					OCTET STRING,
				hwStorageFrontEndHostPortDescription
					OCTET STRING
			 }

		-- 1.3.6.1.4.1.34774.4.1.19.8.11.1.1
		hwStorageFrontEndHostPortIfIndex OBJECT-TYPE
			SYNTAX Unsigned32
			MAX-ACCESS read-only
			STATUS current
			DESCRIPTION
				"Combination index to the host ports."
			::= { hwStorageFrontEndHostPortEntry 1 }
		
		-- 1.3.6.1.4.1.34774.4.1.19.8.11.1.2
		hwStorageFrontEndHostPortType OBJECT-TYPE
			SYNTAX INTEGER
				{
				sas(0),
				fc(1),
				iscsi(5)
				}
			MAX-ACCESS read-only
			STATUS current
			DESCRIPTION
				"Physical type of a host port:
				 0: SAS
				 1: FC
				 5: iSCSI"
			::= { hwStorageFrontEndHostPortEntry 2 }
		
		-- 1.3.6.1.4.1.34774.4.1.19.8.11.1.3
		hwStorageFrontEndHostPortStatus OBJECT-TYPE
			SYNTAX INTEGER
				{
				linkdown(0),
				linkup(1),
				fault(2),
				unknown(3)
				}
			MAX-ACCESS read-only
			STATUS current
			DESCRIPTION
				"Connection state of a host port:
				 0: link down
				 1: link up
				 2: not exist
				 3: link bad
				 4: hardware error
				 5: speed no match
				 6: enable
				 7: disable
				 8: mac error
				 9: lane no match"
			::= { hwStorageFrontEndHostPortEntry 3 }
		
		-- 1.3.6.1.4.1.34774.4.1.19.8.11.1.4
		hwStorageFrontEndHostPortPhysAddress OBJECT-TYPE
			SYNTAX OCTET STRING
			MAX-ACCESS read-only
			STATUS current
			DESCRIPTION
				"IP address of a host port. If "--" is displayed, the value is invalid."
			::= { hwStorageFrontEndHostPortEntry 4 }
		
		-- 1.3.6.1.4.1.34774.4.1.19.8.11.1.5
		hwStorageFrontEndHostPortDescription OBJECT-TYPE
			SYNTAX OCTET STRING
			MAX-ACCESS read-only
			STATUS current
			DESCRIPTION
				"Description of a host port."
			::= { hwStorageFrontEndHostPortEntry 5 }
		
		-- 1.3.6.1.4.1.34774.4.1.19.8.12
		hwStorageControllerTable OBJECT-TYPE
			SYNTAX SEQUENCE OF HwStorageControllerEntry
			MAX-ACCESS not-accessible
			STATUS current
			DESCRIPTION
				"This table provides basic information about the controller."
			::= { hwStoragePhysicalModule 12 }
		
		-- 1.3.6.1.4.1.34774.4.1.19.8.12.1
		hwStorageControllerEntry OBJECT-TYPE
			SYNTAX HwStorageControllerEntry
			MAX-ACCESS not-accessible
			STATUS current
			DESCRIPTION
				"A table containing the part component."
			INDEX { hwStorageControllerID }
			::= { hwStorageControllerTable 1 }
		
		HwStorageControllerEntry ::=
			SEQUENCE { 
				hwStorageControllerID
					Unsigned32,
				hwStorageControllerName
					OCTET STRING,
				hwStorageControllerLocation
					OCTET STRING,
				hwStorageControllerHealthStatus
					INTEGER,
				hwStorageControllerRunningStatus
					INTEGER,
				hwStorageControllerSoftVer
					OCTET STRING,
				hwStorageControllerTemperature
					Integer32,
				hwStorageControllerIsMaster
					Unsigned32,
				hwStorageControllerELabel
					OCTET STRING,
				hwStorageControllerPCBVer
					OCTET STRING,
				hwStorageControllerBMCVer
					OCTET STRING,
				hwStorageControllerLogicVer
					OCTET STRING,
				hwStorageControllerBIOSVer
					OCTET STRING,
				hwStorageControllerMemorySize
					Unsigned32,
				hwStorageControllerCPUInfo
					OCTET STRING,
				hwStorageControllerVoltage
					Unsigned32
			 }

		-- 1.3.6.1.4.1.34774.4.1.19.8.12.1.1
		hwStorageControllerID OBJECT-TYPE
			SYNTAX Unsigned32
			MAX-ACCESS read-only
			STATUS current
			DESCRIPTION
				"Controller node ID.
				 Controller node ID = Controller enclosure ID x Number of controllers in the controller enclosure + Controller ID. In controller name 1A, 1 indicates the controller enclosure ID and A indicates the controller ID (A, B, C, D correspond to 0, 1, 2, 3, respectively). If a controller enclosure has two controllers, the node ID is 2. If a controller enclosure has four controllers, the node ID is 4."
			::= { hwStorageControllerEntry 1 }
		
		-- 1.3.6.1.4.1.34774.4.1.19.8.12.1.2
		hwStorageControllerName OBJECT-TYPE
			SYNTAX OCTET STRING
			MAX-ACCESS read-only
			STATUS current
			DESCRIPTION
				"Controller name"
			::= { hwStorageControllerEntry 2 }
		
		-- 1.3.6.1.4.1.34774.4.1.19.8.12.1.3
		hwStorageControllerLocation OBJECT-TYPE
			SYNTAX OCTET STRING
			MAX-ACCESS read-only
			STATUS current
			DESCRIPTION
				"Controller location"
			::= { hwStorageControllerEntry 3 }
		
		-- 1.3.6.1.4.1.34774.4.1.19.8.12.1.4
		hwStorageControllerHealthStatus OBJECT-TYPE
			SYNTAX INTEGER
				{
				normal(1),
				fault(2),
				preFail(3),
				partiallyBroken(4),
				degraded(5),
				badSectorsFound(6),
				bitErrorsFound(7),
				consistent(8),
				inconsistent(9),
				busy(10),
				noInput(11),
				lowBattery(12),
				singleLinkFault(13)
				}
			MAX-ACCESS read-only
			STATUS current
			DESCRIPTION
				"Controller health status. For details, see:
				1 Normal
				2 Fault
				3 Pre-Fail
				4 Partially Broken
				5 Degraded
				6 Bad Sectors Found
				7 Bit Errors Found
				8 Consistent
				9 Inconsistent
				10 Busy
				11 No Input
				12 Low Battery
				13 Single Link Fault
				14 Invalid
				15 Write Protect
				16 single link
				17 No Redundant Link
				18 Offline"
			::= { hwStorageControllerEntry 4 }
		
		-- 1.3.6.1.4.1.34774.4.1.19.8.12.1.5
		hwStorageControllerRunningStatus OBJECT-TYPE
			SYNTAX INTEGER
				{
				normal(1),
				running(2),
				notRunning(3),
				notExisted(4),
				sleepInHighTemperature(5),
				starting(6),
				powerFailureProtecting(7),
				spinDown(8),
				started(9),
				linkUp(10),
				linkDown(11),
				poweringOn(12),
				poweredOff(13),
				precopy(14),
				copyback(15),
				reconstruction(16),
				expansion(17),
				unformatted(18),
				formatting(19),
				unmapped(20),
				initialSynchronizing(21),
				consistent(22),
				synchronizing(23),
				synchronized(24),
				unsynchronized(25),
				splited(26),
				online(27),
				offline(28),
				locked(29),
				enabled(30),
				disabled(31),
				balancing(32),
				toBeRecoverd(33),
				interrupted(34),
				invalid(35),
				notStart(36),
				queuing(37),
				stopped(38),
				copying(39),
				completed(40),
				paused(41),
				reverseSynchronizing(42),
				activated(43),
				restore(44),
				inactive(45),
				idle(46),
				poweringOff(47),
				charging(48),
				chargingCompleted(49),
				discharging(50),
				upgrading(51),
				runningNormal(63),
				runningFail(64)
				}
			MAX-ACCESS read-only
			STATUS current
			DESCRIPTION
				"Controller running status. For details, see:
				1: Normal
				2: Running
				3: Not running
				4: Not existed
				5: Sleep in high temperature
				6: Starting
				7: Power failure rotection
				8: Spin down
				9: Started
				10: Link Up
				11: Link Down
				12: Powering on
				13: Powered off
				14: Pre-copy
				15: Copyback
				16: Reconstruction
				17: Expansion
				18: Unformatted
				19: Formatting
				20: Unmapped
				21: Initial synchronizing
				22: Consistent
				23: Synchronizing
				24: Synchronized
				25: Unsynchronized
				26: Split
				27: Online
				28: Offline
				29: Locked
				30: Enabled
				31: Disabled
				32: Balancing
				33: To be recovered
				34: Interrupted
				35: Invalid
				36: Not start
				37: Queuing
				38: Stopped
				39: Copying
				40: Completed
				41: Paused
				42: Reverse synchronizing
				43: Activated
				44: Restore
				45: Inactive
				46: Idle
				47: Powering off
				48: Charging
				49: Charging completed
				50: Discharging
				51: Upgrading
				52: Power Lost
				53: Initializing
				54: Apply change
				55: Online disable
				56: Offline disable
				57: Online frozen
				58: Offline frozen
				59: Closed
				60: Removing
				61: In service
				62: Out of service
				63: Running normal
				64: Running fail
				65: Running success
				66: Running success
				67: Running failed
				68: Waiting
				69: Canceling
				70: Canceled
				71: About to synchronize
				72: Synchronizing data
				73: Failed to synchronize
				74: Fault
				75: Migrating
				76: Migrated
				77: Activating
				78: Deactivating
				79: Start failed
				80: Stop failed
				81: Decommissioning
				82: Decommissioned
				83: Recommissioning
				84: Replacing node
				85: Scheduling
				86: Pausing
				87: Suspending
				88: Suspended
				89: Overload
				90: To be switch
				91: Switching
				92: To be cleanup
				93: Forced start
				94: Error
				95: Job completed
				96: Partition Migrating
				97: Mount
				98: Umount
				99: INSTALLING
				100: To Be Synchronized
				101: Connecting
				102: Service Switching
				103: Power-on failed
				104: REPAIRING
				105: abnormal
				106: Deleting
				107: Modifying
				108: Running(clearing data)
				109: Running(synchronizing data)
				110: Standby
				111: STOPPING
				112: RESTORE FAULT
				113: Cut Over
				114: Erasing
				115: Verifying
				119: Creating"
			::= { hwStorageControllerEntry 5 }
		
		-- 1.3.6.1.4.1.34774.4.1.19.8.12.1.6
		hwStorageControllerSoftVer OBJECT-TYPE
			SYNTAX OCTET STRING
			MAX-ACCESS read-only
			STATUS current
			DESCRIPTION
				"Controller software version."
			::= { hwStorageControllerEntry 6 }
		
		-- 1.3.6.1.4.1.34774.4.1.19.8.12.1.7
		hwStorageControllerTemperature OBJECT-TYPE
			SYNTAX Integer32
			MAX-ACCESS read-only
			STATUS current
			DESCRIPTION
				"Controller temperature, unit: degree, not used currently."
			::= { hwStorageControllerEntry 7 }
		
		-- 1.3.6.1.4.1.34774.4.1.19.8.12.1.8
		hwStorageControllerIsMaster OBJECT-TYPE
			SYNTAX Unsigned32
			MAX-ACCESS read-only
			STATUS current
			DESCRIPTION
				"The state of controller, master or slave
				0: Slave
				1: Master
				Not used currently."
			::= { hwStorageControllerEntry 8 }
		
		-- 1.3.6.1.4.1.34774.4.1.19.8.12.1.9
		hwStorageControllerELabel OBJECT-TYPE
			SYNTAX OCTET STRING
			MAX-ACCESS read-only
			STATUS current
			DESCRIPTION
				"Controller electronic label."
			::= { hwStorageControllerEntry 9 }
		
		-- 1.3.6.1.4.1.34774.4.1.19.8.12.1.10
		hwStorageControllerPCBVer OBJECT-TYPE
			SYNTAX OCTET STRING
			MAX-ACCESS read-only
			STATUS current
			DESCRIPTION
				"Controller PCB version"
			::= { hwStorageControllerEntry 10 }
		
		-- 1.3.6.1.4.1.34774.4.1.19.8.12.1.11
		hwStorageControllerBMCVer OBJECT-TYPE
			SYNTAX OCTET STRING
			MAX-ACCESS read-only
			STATUS current
			DESCRIPTION
				"Controller BMC version. When the value is empty or "--", indicates unknown or invalid."
			::= { hwStorageControllerEntry 11 }
		
		-- 1.3.6.1.4.1.34774.4.1.19.8.12.1.12
		hwStorageControllerLogicVer OBJECT-TYPE
			SYNTAX OCTET STRING
			MAX-ACCESS read-only
			STATUS current
			DESCRIPTION
				"Controller logical version"
			::= { hwStorageControllerEntry 12 }
		
		-- 1.3.6.1.4.1.34774.4.1.19.8.12.1.13
		hwStorageControllerBIOSVer OBJECT-TYPE
			SYNTAX OCTET STRING
			MAX-ACCESS read-only
			STATUS current
			DESCRIPTION
				"Controller BIOS version"
			::= { hwStorageControllerEntry 13 }
		
		-- 1.3.6.1.4.1.34774.4.1.19.8.12.1.14
		hwStorageControllerMemorySize OBJECT-TYPE
			SYNTAX Unsigned32
			MAX-ACCESS read-only
			STATUS current
			DESCRIPTION
				"Controller memory size, unit: MB"
			::= { hwStorageControllerEntry 14 }
		
		-- 1.3.6.1.4.1.34774.4.1.19.8.12.1.15
		hwStorageControllerCPUInfo OBJECT-TYPE
			SYNTAX OCTET STRING
			MAX-ACCESS read-only
			STATUS current
			DESCRIPTION
				"CPU information, composed by four fields: manufacturer, make, model, and frequency."
			::= { hwStorageControllerEntry 15 }
		
		-- 1.3.6.1.4.1.34774.4.1.19.8.12.1.16
		hwStorageControllerVoltage OBJECT-TYPE
			SYNTAX Unsigned32
			MAX-ACCESS read-only
			STATUS current
			DESCRIPTION
				"Controller voltage, unit: 0.1V."
			::= { hwStorageControllerEntry 16 }
		
		-- 1.3.6.1.4.1.34774.4.1.19.9
		hwStorageLogicModule OBJECT IDENTIFIER ::= { hwStorageService 9 }
		
		-- 1.3.6.1.4.1.34774.4.1.19.9.1
		hwStorageCacheTable OBJECT-TYPE
			SYNTAX SEQUENCE OF HwStorageCacheEntry
			MAX-ACCESS not-accessible
			STATUS current
			DESCRIPTION
				"This table provides cache information such as cache ID, cache size, cache high water level, and cache low water level."
			::= { hwStorageLogicModule 1 }
		
		-- 1.3.6.1.4.1.34774.4.1.19.9.1.1
		hwStorageCacheEntry OBJECT-TYPE
			SYNTAX HwStorageCacheEntry
			MAX-ACCESS not-accessible
			STATUS current
			DESCRIPTION
				"A table containing the part component."
			INDEX { hwStorageCacheID }
			::= { hwStorageCacheTable 1 }
		
		HwStorageCacheEntry ::=
			SEQUENCE { 
				hwStorageCacheID
					Unsigned32,
				hwStorageCacheTotalCapacity
					Unsigned32,
				hwStorageCacheHighWaterLevel
					Unsigned32,
				hwStorageCacheLowWaterLevel
					Unsigned32,
				hwStorageCacheRowStatus
					RowStatus
			 }

		-- 1.3.6.1.4.1.34774.4.1.19.9.1.1.1
		hwStorageCacheID OBJECT-TYPE
			SYNTAX Unsigned32
			MAX-ACCESS read-only
			STATUS current
			DESCRIPTION
				"Controller node ID.
				 Controller node ID = Controller enclosure ID x Number of controllers in the controller enclosure + Controller ID. In controller name 1A, 1 indicates the controller enclosure ID and A indicates the controller ID (A, B, C, D correspond to 0, 1, 2, 3, respectively). If a controller enclosure has two controllers, the node ID is 2. If a controller enclosure has four controllers, the node ID is 4."
			::= { hwStorageCacheEntry 1 }
		
		-- 1.3.6.1.4.1.34774.4.1.19.9.1.1.2
		hwStorageCacheTotalCapacity OBJECT-TYPE
			SYNTAX Unsigned32
			UNITS "MB"
			MAX-ACCESS read-only
			STATUS current
			DESCRIPTION
				"Cache size (unit: MB)."
			::= { hwStorageCacheEntry 2 }
		
		-- 1.3.6.1.4.1.34774.4.1.19.9.1.1.3
		hwStorageCacheHighWaterLevel OBJECT-TYPE
			SYNTAX Unsigned32
			MAX-ACCESS read-write
			STATUS current
			DESCRIPTION
				"Cache high water level."
			::= { hwStorageCacheEntry 3 }
		
		-- 1.3.6.1.4.1.34774.4.1.19.9.1.1.4
		hwStorageCacheLowWaterLevel OBJECT-TYPE
			SYNTAX Unsigned32
			MAX-ACCESS read-write
			STATUS current
			DESCRIPTION
				"Cache low water level."
			::= { hwStorageCacheEntry 4 }
		
		-- 1.3.6.1.4.1.34774.4.1.19.9.1.1.5
		hwStorageCacheRowStatus OBJECT-TYPE
			SYNTAX RowStatus
			MAX-ACCESS read-write
			STATUS current
			DESCRIPTION
				" Row status.
				 1: Active"
			::= { hwStorageCacheEntry 5 }
		
		-- 1.3.6.1.4.1.34774.4.1.19.9.4
		hwStorageLunTable OBJECT-TYPE
			SYNTAX SEQUENCE OF HwStorageLunEntry
			MAX-ACCESS not-accessible
			STATUS current
			DESCRIPTION
				"This table is used to query the LUN information about a device."
			::= { hwStorageLogicModule 4 }
		
		-- 1.3.6.1.4.1.34774.4.1.19.9.4.1
		hwStorageLunEntry OBJECT-TYPE
			SYNTAX HwStorageLunEntry
			MAX-ACCESS not-accessible
			STATUS current
			DESCRIPTION
				"A table containing the part component."
			INDEX { hwStorageLunID }
			::= { hwStorageLunTable 1 }
		
		HwStorageLunEntry ::=
			SEQUENCE { 
				hwStorageLunID
					Unsigned32,
				hwStorageLunName
					OCTET STRING,
				hwStorageLunWWN
					OCTET STRING,
				hwStorageLunPoolID
					Unsigned32,
				hwStorageLunCapacity
					Counter64,
				hwStorageLunOwningController
					Unsigned32,
				hwStorageLunStripDepth
					Unsigned32,
				hwStorageLunWriteStrategy
					INTEGER,
				hwStorageLunPrefetchStrategy
					INTEGER,
				hwStorageLunPrefetchValue
					Unsigned32,
				hwStorageLunStatus
					INTEGER,
				hwStorageLunRowStatus
					RowStatus
			 }

		-- 1.3.6.1.4.1.34774.4.1.19.9.4.1.1
		hwStorageLunID OBJECT-TYPE
			SYNTAX Unsigned32
			MAX-ACCESS read-only
			STATUS current
			DESCRIPTION
				"ID of the LUN."
			::= { hwStorageLunEntry 1 }
		
		-- 1.3.6.1.4.1.34774.4.1.19.9.4.1.2
		hwStorageLunName OBJECT-TYPE
			SYNTAX OCTET STRING
			MAX-ACCESS read-only
			STATUS current
			DESCRIPTION
				"Name of the LUN."
			::= { hwStorageLunEntry 2 }
		
		-- 1.3.6.1.4.1.34774.4.1.19.9.4.1.3
		hwStorageLunWWN OBJECT-TYPE
			SYNTAX OCTET STRING
			MAX-ACCESS read-only
			STATUS current
			DESCRIPTION
				"WWN of the LUN."
			::= { hwStorageLunEntry 3 }
		
		-- 1.3.6.1.4.1.34774.4.1.19.9.4.1.4
		hwStorageLunPoolID OBJECT-TYPE
			SYNTAX Unsigned32
			MAX-ACCESS read-only
			STATUS current
			DESCRIPTION
				"ID of the storage pool to which the LUN belongs."
			::= { hwStorageLunEntry 4 }
		
		-- 1.3.6.1.4.1.34774.4.1.19.9.4.1.5
		hwStorageLunCapacity OBJECT-TYPE
			SYNTAX Counter64
			MAX-ACCESS read-only
			STATUS current
			DESCRIPTION
				"Capacity of the LUN. The unit is KB."
			::= { hwStorageLunEntry 5 }
		
		-- 1.3.6.1.4.1.34774.4.1.19.9.4.1.6
		hwStorageLunOwningController OBJECT-TYPE
			SYNTAX Unsigned32
			MAX-ACCESS read-only
			STATUS current
			DESCRIPTION
				"Node id of the owning controller of the LUN.
				Controller node ID = Controller enclosure ID x Number of controllers in the controller enclosure + Controller ID. In controller name 1A, 1 indicates the controller enclosure ID and A indicates the controller ID (A, B, C, D correspond to 0, 1, 2, 3, respectively). If a controller enclosure has two controllers, the node ID is 2. If a controller enclosure has four controllers, the node ID is 4."
			::= { hwStorageLunEntry 6 }
		
		-- 1.3.6.1.4.1.34774.4.1.19.9.4.1.7
		hwStorageLunStripDepth OBJECT-TYPE
			SYNTAX Unsigned32
			MAX-ACCESS read-only
			STATUS current
			DESCRIPTION
				"Stripe depth of the LUN. Not used currently."
			::= { hwStorageLunEntry 7 }
		
		-- 1.3.6.1.4.1.34774.4.1.19.9.4.1.8
		hwStorageLunWriteStrategy OBJECT-TYPE
			SYNTAX INTEGER
				{
				writethrough(1),
				writebacknomirroring(2),
				writebackmirroring(3),
				writebackmandatorynomirroring(4),
				writebackmandatorymirroring(5)
				}
			MAX-ACCESS read-only
			STATUS current
			DESCRIPTION
				"Write policy of the LUN. The value can be:
				1: Write through
				2: Write back no mirroring
				3: Write back mirroring
				4: Write back mandatory nomirroring
				5: Write back mandatory mirroring"
			::= { hwStorageLunEntry 8 }
		
		-- 1.3.6.1.4.1.34774.4.1.19.9.4.1.9
		hwStorageLunPrefetchStrategy OBJECT-TYPE
			SYNTAX INTEGER
				{
				none(0),
				constant(1),
				variable(2),
				intelligent(3)
				}
			MAX-ACCESS read-only
			STATUS current
			DESCRIPTION
				"Prefetch policy of the LUN. The value can be:
				0: Non-prefetch
				1: Constant prefetch
				2: Variable prefetch
				3: Intelligent prefetch"
			::= { hwStorageLunEntry 9 }
		
		-- 1.3.6.1.4.1.34774.4.1.19.9.4.1.10
		hwStorageLunPrefetchValue OBJECT-TYPE
			SYNTAX Unsigned32
			MAX-ACCESS read-only
			STATUS current
			DESCRIPTION
				"Cache prefetch value of the LUN. The cache prefech policy can be:
				1. constant prefetch (unit: KB)
				2. variable prefetch (unit: times)
				3. non-prefetch or intelligent prefetch. If 4294967295 is returned, the value is invalid"
			::= { hwStorageLunEntry 10 }
		
		-- 1.3.6.1.4.1.34774.4.1.19.9.4.1.11
		hwStorageLunStatus OBJECT-TYPE
			SYNTAX INTEGER
				{
				normal(1),
				fault(2),
				notformat(3),
				formatting(4)
				}
			MAX-ACCESS read-only
			STATUS current
			DESCRIPTION
				"Status of the LUN. The value can be:
				1: Normal
				2: Faulty
				3: Unformatted
				4: Formatting"
			::= { hwStorageLunEntry 11 }
		
		-- 1.3.6.1.4.1.34774.4.1.19.9.4.1.50
		hwStorageLunRowStatus OBJECT-TYPE
			SYNTAX RowStatus
			MAX-ACCESS read-only
			STATUS current
			DESCRIPTION
				"Row status.
				1: Active"
			::= { hwStorageLunEntry 50 }
		
		-- 1.6
		isoConformance OBJECT IDENTIFIER ::= { iso 6 }
		
		-- 1.6.1
		isoGroups OBJECT IDENTIFIER ::= { isoConformance 1 }
		
		-- 1.6.1.1
		currentObjectGroup OBJECT-GROUP
			OBJECTS { hwStorageFCPortIfIndex, hwStorageFCPortBoardIfIndex, hwStorageFCPortID, hwStorageFCPortStatus, hwStorageFCPortConfigRate, 
				hwStorageFCPortMode, hwStorageFCPortWWN, hwStorageISCSIPortIfIndex, hwStorageISCSIPortBoardIfIndex, hwStorageISCSIPortID, 
				hwStorageISCSIPortStatus, hwStorageISCSIPortIP, hwStorageISCSIPortNetMask, hwStorageISCSIPortBindMode, hwStorageLunID, 
				hwStorageLunName, hwStorageLunWWN, hwStorageLunPoolID, hwStorageLunCapacity, hwStorageLunOwningController, 
				hwStorageLunStripDepth, hwStorageLunWriteStrategy, hwStorageLunPrefetchValue, hwStorageLunStatus, hwStorageLunRowStatus, 
				version, totalCapacity, usedCapacity, deviceType, deviceId, 
				hwStorageSASPortIfIndex, hwStorageSASPortBoardIfIndex, hwStorageSASPortID, hwStorageSASPortStatus, hwStorageSASPortConfigRate, 
				hwStorageFrontEndHostPortIfIndex, hwStorageFrontEndHostPortType, hwStorageFrontEndHostPortStatus, hwStorageFrontEndHostPortPhysAddress, hwStorageFrontEndHostPortDescription, 
				hwStorageCacheID, hwStorageCacheTotalCapacity, hwStorageCacheHighWaterLevel, hwStorageCacheLowWaterLevel, hwStorageCacheRowStatus, 
				hwStorageControllerID, hwStorageControllerName, hwStorageControllerLocation, hwStorageControllerRunningStatus, hwStorageControllerSoftVer, 
				hwStorageControllerTemperature, hwStorageControllerIsMaster, hwStorageControllerELabel, hwStorageControllerPCBVer, hwStorageControllerBMCVer, 
				hwStorageControllerLogicVer, hwStorageControllerBIOSVer, hwStorageControllerMemorySize, hwStorageControllerCPUInfo, hwStorageControllerVoltage, 
				hwStorageSASPortWWN, hwStorageFCPortLogicType, hwStorageFCPortSpeedRate, hwStorageSASPortLogicType, hwStorageSASPortSpeedRate, 
				hwStorageISCSIPortLogicType, hwStorageLunPrefetchStrategy, status, hwStorageControllerHealthStatus }
			STATUS current
			DESCRIPTION 
				"Enter the description of the created OBJECT-GROUP."
			::= { isoGroups 1 }
		
		-- 1.6.2
		isoCompliances OBJECT IDENTIFIER ::= { isoConformance 2 }
		
--  this module
		-- 1.6.2.1
		basicCompliance MODULE-COMPLIANCE
			STATUS current
			DESCRIPTION 
				"Enter the description of the created MODULE-COMPLIANCE."
			MODULE -- this module
				MANDATORY-GROUPS { currentObjectGroup }
			::= { isoCompliances 1 }
		
	
	END

--
-- ISM-STORAGE-SVC-MIB.mib
--
