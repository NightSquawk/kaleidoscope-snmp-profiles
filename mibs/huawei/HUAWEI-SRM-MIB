-- 
-- HUAWEI-SRM.mib
-- MIB generated by MG-SOFT Visual MIB Builder Version 3.0 Build 253
-- Monday, March 31, 2003 at 10:22:34
-- Modified by Liukai 2003/10/22
--

--   =============================================================================
-- Copyright (C) 2010 by HUAWEI TECHNOLOGIES. All rights reserved.
--    
-- Description:  
-- Reference: Huawei Enterprise MIB
-- Version: V1.00
-- History: 
--          V1.00 The initial version created by Liukai. 
-- =============================================================================

    HUAWEI-SRM-MIB DEFINITIONS ::= BEGIN
 
        IMPORTS                                            
            OBJECT-GROUP, MODULE-COMPLIANCE, NOTIFICATION-GROUP            
                FROM SNMPv2-CONF            
            DisplayString, RowStatus                        
                FROM SNMPv2-TC
            TimeTicks, Integer32, Unsigned32, IpAddress, Counter32, OBJECT-TYPE, 
            MODULE-IDENTITY, NOTIFICATION-TYPE            
                FROM SNMPv2-SMI
            mlsr            
                FROM HUAWEI-MIB;
    
    
        hwSRM MODULE-IDENTITY 
            LAST-UPDATED "201008111600Z"        
            ORGANIZATION 
                  "Huawei Technologies Co.,Ltd."
            CONTACT-INFO 
                  "Huawei Industrial Base
  Bantian, Longgang
   Shenzhen 518129
   People's Republic of China
   Website: http://www.huawei.com
   Email: support@huawei.com
 "
            DESCRIPTION 
                "Please provide the descritpion."
            REVISION    "201008111600Z"   
            DESCRIPTION "V1.00, initial version."
    
            ::= { mlsr 20 }

    
--
-- Node definitions
--
    
    
        -- 1.3.6.1.4.1.2011.2.33.20.1
        hw8060DevObjects OBJECT IDENTIFIER ::= { hwSRM 1 }
        
        -- 1.3.6.1.4.1.2011.2.33.20.1.1
        hw8060FrameTable OBJECT-TYPE
            SYNTAX SEQUENCE OF HwFrameEntry
            MAX-ACCESS not-accessible
            STATUS current
            DESCRIPTION
                "Frame table."
            ::= { hw8060DevObjects 1 }
        
        -- 1.3.6.1.4.1.2011.2.33.20.1.1.1
        hw8060FrameEntry OBJECT-TYPE
            SYNTAX HwFrameEntry
            MAX-ACCESS not-accessible
            STATUS current
            DESCRIPTION
                "Frame table entry."
            INDEX { hw8060FrameIndex }
            ::= { hw8060FrameTable 1 }
        
        HwFrameEntry ::=
            SEQUENCE { 
                hw8060FrameIndex
                    Integer32,
                hw8060FrameType
                    Integer32,
                hw8060FrameDesc
                    OCTET STRING,
                hw8060FrameSlotNumber
                    Integer32
--                hw8060FrameAdminStatus
--                    Integer32
             }

        -- 1.3.6.1.4.1.2011.2.33.20.1.1.1.1
        hw8060FrameIndex OBJECT-TYPE
            SYNTAX Integer32 (0..100)
            MAX-ACCESS read-only
            STATUS current
            DESCRIPTION
                "This variable indicates the index of 8060 frame"
            ::= { hw8060FrameEntry 1 }
        
        -- 1.3.6.1.4.1.2011.2.33.20.1.1.1.2
        hw8060FrameType OBJECT-TYPE
            SYNTAX Integer32
            MAX-ACCESS read-only
            STATUS current
            DESCRIPTION
                "This variable indicates the type of 8060 frame"
            ::= { hw8060FrameEntry 2 }
        
        -- 1.3.6.1.4.1.2011.2.33.20.1.1.1.3
        hw8060FrameDesc OBJECT-TYPE
            SYNTAX OCTET STRING (SIZE (1..64))
            MAX-ACCESS read-write
            STATUS current
            DESCRIPTION
                "This variable indicates the description of 8060 frame"
            ::= { hw8060FrameEntry 3 }
        
        -- 1.3.6.1.4.1.2011.2.33.20.1.1.1.4
        hw8060FrameSlotNumber OBJECT-TYPE
            SYNTAX Integer32
            MAX-ACCESS read-only
            STATUS current
            DESCRIPTION
                "This variable indicates the total number of slots in this 8060 frame"
            ::= { hw8060FrameEntry 4 }
        
        -- 1.3.6.1.4.1.2011.2.33.20.1.1.1.5
--        hw8060FrameAdminStatus OBJECT-TYPE
--            SYNTAX Integer32
--            MAX-ACCESS read-only
--            STATUS current
--            DESCRIPTION
--                "This variable indicates the administration status of 8060 frame"
--            ::= { hw8060FrameEntry 5 }
        
        -- 1.3.6.1.4.1.2011.2.33.20.1.2
        hw8060SlotTable OBJECT-TYPE
            SYNTAX SEQUENCE OF HwSlotEntry
            MAX-ACCESS not-accessible
            STATUS current
            DESCRIPTION
                "Slot table."
            ::= { hw8060DevObjects 2 }
        
        -- 1.3.6.1.4.1.2011.2.33.20.1.2.1
        hw8060SlotEntry OBJECT-TYPE
            SYNTAX HwSlotEntry
            MAX-ACCESS not-accessible
            STATUS current
            DESCRIPTION
                "Slot table entry."
            INDEX { hw8060SlotIndex }
            ::= { hw8060SlotTable 1 }
        
        HwSlotEntry ::=
            SEQUENCE { 
                hw8060SlotIndex
                    Integer32,
                hw8060SlotType
                    Integer32,
                hw8060SlotDesc
                    OCTET STRING,
                hw8060SlotCpuRatio
                    Integer32,
                hw8060SlotPcbVersion
                    OCTET STRING,
                hw8060SlotSoftwareVersion
                    OCTET STRING,
                hw8060SlotSubslotNumber
                    Integer32,
--                hw8060SlotAdminStatus
--                    Integer32,
                hw8060SlotOperStatus
                    Integer32
             }

        -- 1.3.6.1.4.1.2011.2.33.20.1.2.1.1
        hw8060SlotIndex OBJECT-TYPE
            SYNTAX Integer32 (0..100)
            MAX-ACCESS read-only
            STATUS current
            DESCRIPTION
                "This variable indicates the index of the current slot"
            ::= { hw8060SlotEntry 1 }
        
        -- 1.3.6.1.4.1.2011.2.33.20.1.2.1.2
        hw8060SlotType OBJECT-TYPE
            SYNTAX Integer32
            MAX-ACCESS read-only
            STATUS current
            DESCRIPTION
                "This variable indicates the type of the current slot"
            ::= { hw8060SlotEntry 2 }
        
        -- 1.3.6.1.4.1.2011.2.33.20.1.2.1.3
        hw8060SlotDesc OBJECT-TYPE
            SYNTAX OCTET STRING (SIZE (0..64))
            MAX-ACCESS read-write
            STATUS current
            DESCRIPTION
                "This variable indicates the description of the current slot"
            ::= { hw8060SlotEntry 3 }
        
        -- 1.3.6.1.4.1.2011.2.33.20.1.2.1.4
        hw8060SlotCpuRatio OBJECT-TYPE
            SYNTAX Integer32
            MAX-ACCESS read-only
            STATUS current
            DESCRIPTION
                "This variable indicates the ratio of CPU the current slot occupied"
            ::= { hw8060SlotEntry 4 }
        
        -- 1.3.6.1.4.1.2011.2.33.20.1.2.1.5
        hw8060SlotPcbVersion OBJECT-TYPE
            SYNTAX OCTET STRING
            MAX-ACCESS read-only
            STATUS current
            DESCRIPTION
                "This variable indicates the PCB version of the current slot"
            ::= { hw8060SlotEntry 5 }
        
        -- 1.3.6.1.4.1.2011.2.33.20.1.2.1.6
        hw8060SlotSoftwareVersion OBJECT-TYPE
            SYNTAX OCTET STRING
            MAX-ACCESS read-only
            STATUS current
            DESCRIPTION
                "This variable indicates the software version of the current slot"
            ::= { hw8060SlotEntry 6 }
        
        -- 1.3.6.1.4.1.2011.2.33.20.1.2.1.7
        hw8060SlotSubslotNumber OBJECT-TYPE
            SYNTAX Integer32
            MAX-ACCESS read-only
            STATUS current
            DESCRIPTION
                "This variable indicates the total number of subslots in the current slot"
            ::= { hw8060SlotEntry 7 }
        
        -- 1.3.6.1.4.1.2011.2.33.20.1.2.1.8
--        hw8060SlotAdminStatus OBJECT-TYPE
--            SYNTAX Integer32
--            MAX-ACCESS read-only
--            STATUS current
--            DESCRIPTION
--                "This variable indicates the administration status of the current slot"
--            ::= { hw8060SlotEntry 8 }
        
        -- 1.3.6.1.4.1.2011.2.33.20.1.2.1.9
        hw8060SlotOperStatus OBJECT-TYPE
            SYNTAX Integer32
            MAX-ACCESS read-write
            STATUS current
            DESCRIPTION
                "This variable indicates the operatrion status of the current slot"
            ::= { hw8060SlotEntry 9 }
        
        -- 1.3.6.1.4.1.2011.2.33.20.1.3
        hw8060SubslotTable OBJECT-TYPE
            SYNTAX SEQUENCE OF HwSubslotEntry
            MAX-ACCESS not-accessible
            STATUS current
            DESCRIPTION
                "Subslot table."
            ::= { hw8060DevObjects 3 }
        
        -- 1.3.6.1.4.1.2011.2.33.20.1.3.1
        hw8060SubslotEntry OBJECT-TYPE
            SYNTAX HwSubslotEntry
            MAX-ACCESS not-accessible
            STATUS current
            DESCRIPTION
                "Subslot table entry."
            INDEX { hw8060SlotIndex, hw8060SubslotIndex }
            ::= { hw8060SubslotTable 1 }
        
        HwSubslotEntry ::=
            SEQUENCE { 
                hw8060SubslotIndex
                    Integer32,
                hw8060SubslotType
                    Integer32,
                hw8060SubslotPortNum
                    Integer32
--                hw8060SubslotAdminStatus
--                    Integer32
             }

        -- 1.3.6.1.4.1.2011.2.33.20.1.3.1.1
        hw8060SubslotIndex OBJECT-TYPE
            SYNTAX Integer32 (0..100)
            MAX-ACCESS read-only
            STATUS current
            DESCRIPTION
                "This variable indicates the index of the current subslot"
            ::= { hw8060SubslotEntry 1 }
        
        -- 1.3.6.1.4.1.2011.2.33.20.1.3.1.2
        hw8060SubslotType OBJECT-TYPE
            SYNTAX Integer32
            MAX-ACCESS read-only
            STATUS current
            DESCRIPTION
                "This variable indicates the type of the current subslot"
            ::= { hw8060SubslotEntry 2 }
        
        -- 1.3.6.1.4.1.2011.2.33.20.1.3.1.3
        hw8060SubslotPortNum OBJECT-TYPE
            SYNTAX Integer32
            MAX-ACCESS read-only
            STATUS current
            DESCRIPTION
                "This variable indicates the total number of ports in the current subslot"
            ::= { hw8060SubslotEntry 3 }
        
        -- 1.3.6.1.4.1.2011.2.33.20.1.3.1.4
--        hw8060SubslotAdminStatus OBJECT-TYPE
--            SYNTAX Integer32
--            MAX-ACCESS read-only
--            STATUS current
--            DESCRIPTION
--                "This variable indicates the administration status of the current subslot"
--            ::= { hw8060SubslotEntry 4 }
        
        -- 1.3.6.1.4.1.2011.2.33.20.1.4
        hw8060PortTable OBJECT-TYPE
            SYNTAX SEQUENCE OF HwPortEntry
            MAX-ACCESS not-accessible
            STATUS current
            DESCRIPTION
                "Port table."
            ::= { hw8060DevObjects 4 }
        
        -- 1.3.6.1.4.1.2011.2.33.20.1.4.1
        hw8060PortEntry OBJECT-TYPE
            SYNTAX HwPortEntry
            MAX-ACCESS not-accessible
            STATUS current
            DESCRIPTION
                "Port table entry."
            INDEX { hw8060SlotIndex, hw8060SubslotIndex, hw8060PortIndex }
            ::= { hw8060PortTable 1 }
        
        HwPortEntry ::=
            SEQUENCE { 
                hw8060PortIndex
                    Integer32,
                hw8060PortType
                    Integer32,
                hw8060PortDesc
                    OCTET STRING,
                hw8060PortSpeed
                    Integer32,
--                hw8060PortAdminStatus
--                    Integer32,
                hw8060PortOperateStatus
                    Integer32
             }

        -- 1.3.6.1.4.1.2011.2.33.20.1.4.1.1
        hw8060PortIndex OBJECT-TYPE
            SYNTAX Integer32 (0..100)
            MAX-ACCESS read-only
            STATUS current
            DESCRIPTION
                "This variable indicates the index of the current port"
            ::= { hw8060PortEntry 1 }
        
        -- 1.3.6.1.4.1.2011.2.33.20.1.4.1.2
        hw8060PortType OBJECT-TYPE
            SYNTAX Integer32
            MAX-ACCESS read-only
            STATUS current
            DESCRIPTION
                "This variable indicates the type of the current subslot"
            ::= { hw8060PortEntry 2 }
        
        -- 1.3.6.1.4.1.2011.2.33.20.1.4.1.3
        hw8060PortDesc OBJECT-TYPE
            SYNTAX OCTET STRING (SIZE (1..64))
            MAX-ACCESS read-only
            STATUS current
            DESCRIPTION
                "This variable indicates the description of the current subslot"
            ::= { hw8060PortEntry 3 }
        
        -- 1.3.6.1.4.1.2011.2.33.20.1.4.1.4
        hw8060PortSpeed OBJECT-TYPE
            SYNTAX Integer32
            MAX-ACCESS read-only
            STATUS current
            DESCRIPTION
                "This variable indicates the speed in bps of the current subslot"
            ::= { hw8060PortEntry 4 }
        
        -- 1.3.6.1.4.1.2011.2.33.20.1.4.1.5
--        hw8060PortAdminStatus OBJECT-TYPE
--            SYNTAX Integer32
--            MAX-ACCESS read-only
--            STATUS current
--            DESCRIPTION
--                "This variable indicates the administration status of the current subslot"
--            ::= { hw8060PortEntry 5 }
        
        -- 1.3.6.1.4.1.2011.2.33.20.1.4.1.6
        hw8060PortOperateStatus OBJECT-TYPE
            SYNTAX Integer32
            MAX-ACCESS read-write
            STATUS current
            DESCRIPTION
                "This variable indicates the operation status of the current subslot"
            ::= { hw8060PortEntry 6 }
        
        -- 1.3.6.1.4.1.2011.2.33.20.1.5
        dev8060MPowerStatusTable OBJECT-TYPE
            SYNTAX SEQUENCE OF DevMPowerStatusEntry
            MAX-ACCESS not-accessible
            STATUS current
            DESCRIPTION             " "
            ::= { hw8060DevObjects 5 }
        
        -- 1.3.6.1.4.1.2011.2.33.20.1.5.1
        dev8060MPowerStatusEntry OBJECT-TYPE
            SYNTAX DevMPowerStatusEntry
            MAX-ACCESS not-accessible
            STATUS current
            DESCRIPTION
                "Description."
            INDEX { dev8060MPowerNum }
            ::= { dev8060MPowerStatusTable 1 }
        
        DevMPowerStatusEntry ::=
            SEQUENCE { 
                dev8060MPowerNum
                    Integer32,
                dev8060MPowerStatus
                    Integer32
             }

        -- 1.3.6.1.4.1.2011.2.33.20.1.5.1.1
        dev8060MPowerNum OBJECT-TYPE
            SYNTAX Integer32 (0..10)
            MAX-ACCESS read-only
            STATUS current
            DESCRIPTION
                "This variable indicates the sequence number of the current power"
            ::= { dev8060MPowerStatusEntry 1 }
        
        -- 1.3.6.1.4.1.2011.2.33.20.1.5.1.2
        dev8060MPowerStatus OBJECT-TYPE
            SYNTAX Integer32
            MAX-ACCESS read-only
            STATUS current
            DESCRIPTION
                "This variable indicates the working status of the current power"
            ::= { dev8060MPowerStatusEntry 2 }
        
        -- 1.3.6.1.4.1.2011.2.33.20.1.6
        dev8060MFanStatusTable OBJECT-TYPE
            SYNTAX SEQUENCE OF DevMFanStatusEntry
            MAX-ACCESS not-accessible
            STATUS current
            DESCRIPTION             " "
            ::= { hw8060DevObjects 6 }
        
        -- 1.3.6.1.4.1.2011.2.33.20.1.6.1
        dev8060MFanStatusEntry OBJECT-TYPE
            SYNTAX DevMFanStatusEntry
            MAX-ACCESS not-accessible
            STATUS current
            DESCRIPTION
                "Description."
            INDEX { dev8060MFanNum }
            ::= { dev8060MFanStatusTable 1 }
        
        DevMFanStatusEntry ::=
            SEQUENCE { 
                dev8060MFanNum
                    Integer32,
                dev8060MFanStatus
                    Integer32
             }

        -- 1.3.6.1.4.1.2011.2.33.20.1.6.1.1
        dev8060MFanNum OBJECT-TYPE
            SYNTAX Integer32 (0..10)
            MAX-ACCESS read-only
            STATUS current
            DESCRIPTION
                "This variable indicates the sequence number of the current fan"
            ::= { dev8060MFanStatusEntry 1 }
        
        -- 1.3.6.1.4.1.2011.2.33.20.1.6.1.2
        dev8060MFanStatus OBJECT-TYPE
            SYNTAX Integer32
            MAX-ACCESS read-write
            STATUS current
            DESCRIPTION
                "This variable indicates the working status of the current fan"
            ::= { dev8060MFanStatusEntry 2 }
        
        -- 1.3.6.1.4.1.2011.2.33.20.1.7
        dev8060MGlobalTable OBJECT IDENTIFIER ::= { hw8060DevObjects 7 }
        
        -- 1.3.6.1.4.1.2011.2.33.20.1.7.1
        hw8060DevMRpuTemperature OBJECT-TYPE
            SYNTAX Integer32
            MAX-ACCESS read-only
            STATUS current
            DESCRIPTION             " "
            ::= { dev8060MGlobalTable 1 }
        
        -- 1.3.6.1.4.1.2011.2.33.20.1.7.2
        hw8060DevMTemperatureMax OBJECT-TYPE
            SYNTAX Integer32
            MAX-ACCESS read-write
            STATUS current
            DESCRIPTION
                "This variable indicates the maximum temperature set by user"
            ::= { dev8060MGlobalTable 2 }
        
-- 
-- 
        -- 1.3.6.1.4.1.2011.2.33.20.1.7.3
        hw8060DevMTemperatureMin OBJECT-TYPE
            SYNTAX Integer32
            MAX-ACCESS read-write
            STATUS current
            DESCRIPTION
                "This variable indicates the minimum temperature set by user"
            ::= { dev8060MGlobalTable 3 }
        
        -- 1.3.6.1.4.1.2011.2.33.20.1.7.4
        hw8060SysVersion OBJECT-TYPE
            SYNTAX OCTET STRING
            MAX-ACCESS read-only
            STATUS current
            DESCRIPTION
                "This variable indicates the system version ( big version )"
            ::= { dev8060MGlobalTable 4 }
        
        -- 1.3.6.1.4.1.2011.2.33.20.1.7.5
        hw8060SysTime OBJECT-TYPE
            SYNTAX Integer32
            MAX-ACCESS read-write
            STATUS current
            DESCRIPTION
                "This variable indicates the system time"
            ::= { dev8060MGlobalTable 5 }
        
        -- 1.3.6.1.4.1.2011.2.33.20.1.7.6
        hw8060DevMVentTemperature OBJECT-TYPE
            SYNTAX Integer32
            MAX-ACCESS read-only
            STATUS current
            DESCRIPTION             " "
            ::= { dev8060MGlobalTable 6 }
        
        -- 1.3.6.1.4.1.2011.2.33.20.2
        hw8060DevNotifications OBJECT IDENTIFIER ::= { hwSRM 2 }
        
        -- 1.3.6.1.4.1.2011.2.33.20.2.1
        hwRpuTempTooHigh NOTIFICATION-TYPE
            STATUS current
            DESCRIPTION 
            "Temperature of RPU too high."
            ::= { hw8060DevNotifications 1 }
        
        -- 1.3.6.1.4.1.2011.2.33.20.2.2
        hwRpuTempOK NOTIFICATION-TYPE
            STATUS current
            DESCRIPTION 
                "The temperature of RPU is normal"
            ::= { hw8060DevNotifications 2 }
        
        -- 1.3.6.1.4.1.2011.2.33.20.2.3
        hwNpTempTooHigh NOTIFICATION-TYPE
            STATUS current
            DESCRIPTION 
                "The temperature of NP exceeds the maximum"
            ::= { hw8060DevNotifications 3 }
        
        -- 1.3.6.1.4.1.2011.2.33.20.2.4
        hwNpTempOK NOTIFICATION-TYPE
            STATUS current
            DESCRIPTION 
                "The temperature of NP is normal"
            ::= { hw8060DevNotifications 4 }
        
        -- 1.3.6.1.4.1.2011.2.33.20.2.5
        hwRpuTempTooLow NOTIFICATION-TYPE
            STATUS current
            DESCRIPTION 
                "The temperature of RPU is too low"
            ::= { hw8060DevNotifications 5 }
        
        -- 1.3.6.1.4.1.2011.2.33.20.2.6
        hwNpTempTooLow NOTIFICATION-TYPE
            STATUS current
            DESCRIPTION 
                "The temperature of NP is too low"
            ::= { hw8060DevNotifications 6 }
        
        -- 1.3.6.1.4.1.2011.2.33.20.2.7
        hwVentTempTooHigh NOTIFICATION-TYPE
            STATUS current
            DESCRIPTION 
                "The temperature of VENT exceeds the maximum
                "
            ::= { hw8060DevNotifications 7 }
        
        -- 1.3.6.1.4.1.2011.2.33.20.2.9
        hwVentTempOK NOTIFICATION-TYPE
            STATUS current
            DESCRIPTION 
                "The temperature of VENT is normal"
            ::= { hw8060DevNotifications 9 }
        
        -- 1.3.6.1.4.1.2011.2.33.20.2.10
        hwRpuReset NOTIFICATION-TYPE
            STATUS current
            DESCRIPTION 
            "Description."
            ::= { hw8060DevNotifications 10 }
        
        -- 1.3.6.1.4.1.2011.2.33.20.2.11
        hwRpuResetOK NOTIFICATION-TYPE
            STATUS current
            DESCRIPTION 
                "RPU reset successfully
                "
            ::= { hw8060DevNotifications 11 }
        
        -- 1.3.6.1.4.1.2011.2.33.20.2.12
        hwNpReset NOTIFICATION-TYPE
            STATUS current
            DESCRIPTION 
                "NP reset"
            ::= { hw8060DevNotifications 12 }
        
        -- 1.3.6.1.4.1.2011.2.33.20.2.13
        hwNpResetOK NOTIFICATION-TYPE
            STATUS current
            DESCRIPTION 
                "NP reset successfully"
            ::= { hw8060DevNotifications 13 }
        
        -- 1.3.6.1.4.1.2011.2.33.20.2.14
        hwSlotReset NOTIFICATION-TYPE
            OBJECTS { hw8060SubslotIndex }
            STATUS current
            DESCRIPTION 
                "Slot reset"
            ::= { hw8060DevNotifications 14 }
        
        -- 1.3.6.1.4.1.2011.2.33.20.2.15
        hwSlotResetOK NOTIFICATION-TYPE
            OBJECTS { hw8060SubslotIndex }
            STATUS current
            DESCRIPTION 
                "Slot reset successfully"
            ::= { hw8060DevNotifications 15 }
        
        -- 1.3.6.1.4.1.2011.2.33.20.2.16
        hwPciAlarm NOTIFICATION-TYPE
            STATUS current
            DESCRIPTION 
                "PCI alarm occurred"
            ::= { hw8060DevNotifications 16 }
        
        -- 1.3.6.1.4.1.2011.2.33.20.2.17
        hwPciNormal NOTIFICATION-TYPE
            STATUS current
            DESCRIPTION 
                "PCI is normal"
            ::= { hw8060DevNotifications 17 }
        
        -- 1.3.6.1.4.1.2011.2.33.20.2.18
        hwRpuIntReportErr NOTIFICATION-TYPE
            STATUS current
            DESCRIPTION 
                "RPU report wrong interrupts too frequently"
            ::= { hw8060DevNotifications 18 }
        
        -- 1.3.6.1.4.1.2011.2.33.20.2.19
        hwNpIntReportErr NOTIFICATION-TYPE
            STATUS current
            DESCRIPTION 
                "NP report wrong interrupts too frequently"
            ::= { hw8060DevNotifications 19 }
        
        -- 1.3.6.1.4.1.2011.2.33.20.2.20
        hwSlotIntReportErr NOTIFICATION-TYPE
            OBJECTS { hw8060SubslotIndex }
            STATUS current
            DESCRIPTION 
                "Slot report wrong interrupts too frequently"
            ::= { hw8060DevNotifications 20 }
        
        -- 1.3.6.1.4.1.2011.2.33.20.2.21
        hwWriteFlashErr NOTIFICATION-TYPE
            STATUS current
            DESCRIPTION 
                "Write FLASH failed"
            ::= { hw8060DevNotifications 21 }
        
        -- 1.3.6.1.4.1.2011.2.33.20.2.22
        hwPowerError NOTIFICATION-TYPE
            OBJECTS { dev8060MPowerNum }
            STATUS current
            DESCRIPTION 
                "Power failed"
            ::= { hw8060DevNotifications 22 }
        
        -- 1.3.6.1.4.1.2011.2.33.20.2.23
        hwPowerNormal NOTIFICATION-TYPE
            OBJECTS { dev8060MPowerNum }
            STATUS current
            DESCRIPTION 
                "Power is normal"
            ::= { hw8060DevNotifications 23 }
        
        -- 1.3.6.1.4.1.2011.2.33.20.2.24
        hwFanError NOTIFICATION-TYPE
            OBJECTS { dev8060MFanNum }
            STATUS current
            DESCRIPTION 
                "Fan failed"
            ::= { hw8060DevNotifications 24 }
        
        -- 1.3.6.1.4.1.2011.2.33.20.2.25
        hwFanNormal NOTIFICATION-TYPE
            OBJECTS { dev8060MFanNum }
            STATUS current
            DESCRIPTION 
                "Fan is normal"
            ::= { hw8060DevNotifications 25 }
        
        -- 1.3.6.1.4.1.2011.2.33.20.2.26
        hwFtpLoadFail NOTIFICATION-TYPE
            STATUS current
            DESCRIPTION 
                "FTP failed"
            ::= { hw8060DevNotifications 26 }
        
        -- 1.3.6.1.4.1.2011.2.33.20.2.27
        hwTftpLoadFail NOTIFICATION-TYPE
            STATUS current
            DESCRIPTION 
                "TFTP failed"
            ::= { hw8060DevNotifications 27 }
        
        -- 1.3.6.1.4.1.2011.2.33.20.2.28
        hwXmodemLoadFail NOTIFICATION-TYPE
            STATUS current
            DESCRIPTION 
                "XMODEM failed"
            ::= { hw8060DevNotifications 28 }
        
        -- 1.3.6.1.4.1.2011.2.33.20.2.29
        hwNpConfPathErr NOTIFICATION-TYPE
            STATUS current
            DESCRIPTION 
                "NP configuration path is abnormal"
            ::= { hw8060DevNotifications 29 }
        
        -- 1.3.6.1.4.1.2011.2.33.20.2.30
        hwHSCardConfPathErr NOTIFICATION-TYPE
            OBJECTS { hw8060SubslotIndex }
            STATUS current
            DESCRIPTION 
                "High speed card configuration path is abnormal"
            ::= { hw8060DevNotifications 30 }
        
        -- 1.3.6.1.4.1.2011.2.33.20.2.31
        hwLSCardJtagErr NOTIFICATION-TYPE
            OBJECTS { hw8060SubslotIndex }
            STATUS current
            DESCRIPTION 
                "Low speed card JTAG path is abnormal"
            ::= { hw8060DevNotifications 31 }
        
        -- 1.3.6.1.4.1.2011.2.33.20.2.32
        hwHSCardJtagErr NOTIFICATION-TYPE
            OBJECTS { hw8060SubslotIndex }
            STATUS current
            DESCRIPTION 
                "High speed card JTAG path is abnormal"
            ::= { hw8060DevNotifications 32 }
        
        -- 1.3.6.1.4.1.2011.2.33.20.2.33
        hwNpuJtagErr NOTIFICATION-TYPE
            STATUS current
            DESCRIPTION 
                "NP JTAG path is abnormal"
            ::= { hw8060DevNotifications 33 }
        
        -- 1.3.6.1.4.1.2011.2.33.20.2.34
        hwNpRpuDmuErr NOTIFICATION-TYPE
            STATUS current
            DESCRIPTION 
                "DMU path between NP and RPU is abnormal"
            ::= { hw8060DevNotifications 34 }
        
        -- 1.3.6.1.4.1.2011.2.33.20.2.35
        hwLSCardHealthyErr NOTIFICATION-TYPE
            OBJECTS { hw8060SubslotIndex }
            STATUS current
            DESCRIPTION 
                "Low speed card healthy signal is abnormal"
            ::= { hw8060DevNotifications 35 }
        
        -- 1.3.6.1.4.1.2011.2.33.20.2.36
        hwHSCardHealthyErr NOTIFICATION-TYPE
            OBJECTS { hw8060SubslotIndex }
            STATUS current
            DESCRIPTION 
                "High speed card healthy signal is abnormal"
            ::= { hw8060DevNotifications 36 }
        
        -- 1.3.6.1.4.1.2011.2.33.20.2.37
        hwCardPciHealthyErr NOTIFICATION-TYPE
            OBJECTS { hw8060SubslotIndex }
            STATUS current
            DESCRIPTION 
                "Slot PCI_HEALTHY signal is abnormal"
            ::= { hw8060DevNotifications 37 }
        
        -- 1.3.6.1.4.1.2011.2.33.20.2.38
        hwHSCardPowerErr NOTIFICATION-TYPE
            OBJECTS { hw8060SubslotIndex }
            STATUS current
            DESCRIPTION 
                "Slot HEALTHY signal is invalid"
            ::= { hw8060DevNotifications 38 }
        
        -- 1.3.6.1.4.1.2011.2.33.20.2.39
        hwVentTempTooLow NOTIFICATION-TYPE
            STATUS current
            DESCRIPTION 
                "The temperature of VENT is too low"
            ::= { hw8060DevNotifications 39 }
        
        -- 1.3.6.1.4.1.2011.2.33.20.2.40
        hwTempSensorErr NOTIFICATION-TYPE
            STATUS current
            DESCRIPTION 
                "The temperature of RPU sensor is abnormal"
            ::= { hw8060DevNotifications 40 }

        -- 1.3.6.1.4.1.2011.2.33.20.2.41
        hwShutDown NOTIFICATION-TYPE
            STATUS current
            DESCRIPTION 
                "The temperature of RPU exceeds the maximum"
            ::= { hw8060DevNotifications 41 }
 
         -- 1.3.6.1.4.1.2011.2.33.20.2.42
        hwShutDownRecover NOTIFICATION-TYPE 
            STATUS current
            DESCRIPTION 
                "The temperature of RPU recover the normal"
            ::= { hw8060DevNotifications 42 }

		
        -- 1.3.6.1.4.1.2011.2.33.20.3
        hw8060DevConformance OBJECT IDENTIFIER ::= { hwSRM 3 }	       
 
    END
--
-- HUAWEI-SRM-MIB.mib
--
