--
-- OPTIX-OSN902-FUNCTION-MIB.mib
-- MIB generated by MG-SOFT Visual MIB Builder Version 3.0 Build 253
-- Friday, March 28, 2014 at 09:45:35
--
-- =================================================================
-- Copyright (C) 2006 by HUAWEI TECHNOLOGIES. All rights reserved
-- 
-- Description:
-- Reference:
-- Version: V1.00
-- History:
-- <author>,<date>,<contents>
-- =================================================================
-- 

	OPTIX-OSN908-FUNCTION-MIB DEFINITIONS ::= BEGIN
 
		IMPORTS
			optixProvisionWDM			
				FROM OPTIX-OID-MIB			
			OBJECT-TYPE			
				FROM SNMPv2-SMI;
	
	
--
-- Node definitions
--
	
		-- 1.3.6.1.4.1.2011.2.25.4.70.10
		optixWDMFunction OBJECT IDENTIFIER ::= { optixProvisionWDM 10 }
		
		-- 1.3.6.1.4.1.2011.2.25.4.70.10.20
		optixWDMBdinfo OBJECT IDENTIFIER ::= { optixWDMFunction 20 }
		
		-- 1.3.6.1.4.1.2011.2.25.4.70.10.20.10
		optixWDMGetBdInfoTable OBJECT-TYPE
			SYNTAX SEQUENCE OF OptixWDMGetBdInfoEntry
			MAX-ACCESS not-accessible
			STATUS current
			DESCRIPTION
				"Table for querying board manufacture information."
			::= { optixWDMBdinfo 10 }
		
		-- 1.3.6.1.4.1.2011.2.25.4.70.10.20.10.1
		optixWDMGetBdInfoEntry OBJECT-TYPE
			SYNTAX OptixWDMGetBdInfoEntry
			MAX-ACCESS not-accessible
			STATUS current
			DESCRIPTION
				"Description."
			INDEX { optixWDMGetBdInfoBID }
			::= { optixWDMGetBdInfoTable 1 }
		
		OptixWDMGetBdInfoEntry ::=
			SEQUENCE { 
				optixWDMGetBdInfoBID
					OCTET STRING,
				optixWDMGetBdInfoData
					OCTET STRING
			 }

		-- 1.3.6.1.4.1.2011.2.25.4.70.10.20.10.1.1
		optixWDMGetBdInfoBID OBJECT-TYPE
			SYNTAX OCTET STRING (SIZE (0..8))
			MAX-ACCESS read-only
			STATUS current
			DESCRIPTION
				"Board ID."
			::= { optixWDMGetBdInfoEntry 1 }
		
		-- 1.3.6.1.4.1.2011.2.25.4.70.10.20.10.1.2
		optixWDMGetBdInfoData OBJECT-TYPE
			SYNTAX OCTET STRING (SIZE (0..4620))
			MAX-ACCESS read-only
			STATUS current
			DESCRIPTION
				"Board Information."
			::= { optixWDMGetBdInfoEntry 2 }
					  
		-- 1.3.6.1.4.1.2011.2.25.4.70.20
		optixWDMDeviceMgr OBJECT IDENTIFIER ::= { optixProvisionWDM 20 }
		
		-- 1.3.6.1.4.1.2011.2.25.4.70.20.10
		optixWDMFanMgr OBJECT IDENTIFIER ::= { optixWDMDeviceMgr 10 }
		
		-- 1.3.6.1.4.1.2011.2.25.4.70.20.10.10
		optixWDMFanTable OBJECT-TYPE
			SYNTAX SEQUENCE OF OptixWDMFanEntry
			MAX-ACCESS not-accessible
			STATUS current
			DESCRIPTION
				"Table for querying Fan speed information."
			::= { optixWDMFanMgr 10 }
			
		-- 1.3.6.1.4.1.2011.2.25.4.70.20.10.10.1
		optixWDMFanEntry OBJECT-TYPE
			SYNTAX OptixWDMFanEntry
			MAX-ACCESS not-accessible
			STATUS current
			DESCRIPTION
				"Table for query Fan speed information."
			INDEX { optixWDMGetFanBID }
			::= { optixWDMFanTable 1 }
		
		OptixWDMFanEntry ::=
			SEQUENCE { 
				optixWDMGetFanBID
					INTEGER,
				optixWDMGetFanSpeed
					INTEGER
			 }

		-- 1.3.6.1.4.1.2011.2.25.4.70.20.10.10.1.1
		optixWDMGetFanBID OBJECT-TYPE
			SYNTAX INTEGER (0..65535)
			MAX-ACCESS read-only
			STATUS current
			DESCRIPTION
				"Fan board slot ID."
			::= { optixWDMFanEntry 1 }
		
		-- 1.3.6.1.4.1.2011.2.25.4.70.20.10.10.1.2
		optixWDMGetFanSpeed OBJECT-TYPE
			SYNTAX INTEGER
				{
				low(1),
				mid(2),
				high(3),
				stop(4),
				auto-low(5),
				auto-mid(6),
				auto-high(7),
				auto(9),
				mid-low(10),
				mid-high(11),
				}
			MAX-ACCESS read-only
			STATUS current
			DESCRIPTION
				"Current Fan speed."
			::= { optixWDMFanEntry 2 }

		-- 1.3.6.1.4.1.2011.2.25.4.70.20.20
		optixWDMPsuMgr OBJECT IDENTIFIER ::= { optixWDMDeviceMgr 20 }
		
		-- 1.3.6.1.4.1.2011.2.25.4.70.20.20.10
		optixWDMPsuTable OBJECT-TYPE
			SYNTAX SEQUENCE OF OptixWDMPsuEntry
			MAX-ACCESS not-accessible
			STATUS current
			DESCRIPTION
				"Table for querying power save information."
			::= { optixWDMPsuMgr 10 }
			
		-- 1.3.6.1.4.1.2011.2.25.4.70.20.20.10.1
		optixWDMPsuEntry OBJECT-TYPE
			SYNTAX OptixWDMPsuEntry
			MAX-ACCESS not-accessible
			STATUS current
			DESCRIPTION
				"Table for query power save information."
			INDEX { optixWDMGetPsuBID }
			::= { optixWDMPsuTable 1 }
		
		OptixWDMPsuEntry ::=
			SEQUENCE { 
				optixWDMGetPsuBID
					INTEGER,
				optixWDMGetPsuPowerConsumption
					INTEGER
			 }

		-- 1.3.6.1.4.1.2011.2.25.4.70.20.20.10.1.1
		optixWDMGetPsuBID OBJECT-TYPE
			SYNTAX INTEGER (0..65535)
			MAX-ACCESS read-only
			STATUS current
			DESCRIPTION
				"Piu board slot ID."
			::= { optixWDMPsuEntry 1 }
		
		-- 1.3.6.1.4.1.2011.2.25.4.70.20.20.10.1.2
		optixWDMGetPsuPowerConsumption OBJECT-TYPE
			SYNTAX INTEGER (0..65535)
			MAX-ACCESS read-only
			STATUS current
			DESCRIPTION
				"Current psu power consumption."
			::= { optixWDMPsuEntry 2 }
	END

--
-- 10_OPTIX-OSN908-FUNCTION-MIB.mib9.173.22.198
--
