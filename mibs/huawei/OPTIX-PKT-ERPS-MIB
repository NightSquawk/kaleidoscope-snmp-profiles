-- OPTIX-PKT-ERPS-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-PKT-ERPS-MIB DEFINITIONS ::= BEGIN
    IMPORTS
        optixProvisionPtn
            FROM OPTIX-OID-MIB
        OBJECT-GROUP,MODULE-COMPLIANCE
            FROM SNMPv2-CONF
        Unsigned32,OBJECT-TYPE,MODULE-IDENTITY,NOTIFICATION-TYPE
            FROM SNMPv2-SMI
        RowStatus,MacAddress
            FROM SNMPv2-TC
        optixLogBoardId,optixLogSubCardId
            FROM OPTIX-BOARD-MANAGE-MIB
        optixPortId
            FROM OPTIX-PORT-MANAGE-MIB
        ;

    optixPktErps MODULE-IDENTITY
        LAST-UPDATED "201204200000Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "This mib specifies the MSTP configuration information of device"
        REVISION "201204200000Z"
        DESCRIPTION
            "The initial revision of this MIB module1."
        ::={ optixProvisionPtn 26 }

    -- 1.3.6.1.4.1.2011.2.25.4.50.26.1
    optixPktErpsGroup OBJECT IDENTIFIER ::= { optixPktErps 1 }

    -- 1.3.6.1.4.1.2011.2.25.4.50.26.1.1
    optixERPSTable OBJECT-TYPE
        SYNTAX SEQUENCE OF OptixERPSEntry
        MAX-ACCESS not-accessible
        STATUS current
        DESCRIPTION
            "This table describes the basicERPS configurations."
        ::= { optixPktErpsGroup 1 }

    -- 1.3.6.1.4.1.2011.2.25.4.50.26.1.1.1
    optixERPSEntry OBJECT-TYPE
        SYNTAX OptixERPSEntry
        MAX-ACCESS not-accessible
        STATUS current
        DESCRIPTION
            "This entry describes the basicERPS configurations."
        INDEX{ optixERPSId }
        ::= { optixERPSTable 1 }

    OptixERPSEntry ::=
        SEQUENCE {
            optixERPSId
                Unsigned32,
            optixERPSEastBoardId
                Unsigned32,
            optixERPSEastSubboardId
                Unsigned32,
            optixERPSEastPort
                Unsigned32,
            optixERPSWestBoardId
                Unsigned32,
            optixERPSWestSubboardId
                Unsigned32,
            optixERPSWestPort
                Unsigned32,
            optixERPSRplBoardId
                Unsigned32,
            optixERPSRplSubboardId
                Unsigned32,
            optixERPSRplPort
                Unsigned32,
            optixERPSRplownerFlag
                INTEGER,
            optixERPSCtrlVlan
                Unsigned32,
            optixERPSDmac
                OCTET STRING,
            optixERPSNodeId
                OCTET STRING,
            optixERPSHoldoffTime
                Unsigned32,
            optixERPSWtrTime
                Unsigned32,
            optixERPSGuardTime
                Unsigned32,
            optixERPSMel
                Unsigned32,
            optixERPSInterval
                Unsigned32,
            optixERPSLastRequest
                INTEGER,
            optixERPSRbState
                INTEGER,
            optixERPSDnfState
                INTEGER,
            optixERPSReceiveNodeId
                OCTET STRING,
            optixERPSFsmState
                INTEGER,
            optixERPSEastPortState
                INTEGER,
            optixERPSWestPortState
                INTEGER,
            optixERPSvchannelState
                INTEGER,
            optixERPSmajorID
                Unsigned32,
            optixERPSVerId
                INTEGER,
            optixERPSRvtMode
                INTEGER,
            optixERPSSWCMode
                INTEGER,
            optixERPSVchannelIdNum
                Unsigned32,
            optixERPSVchannelIdList
                OCTET STRING,
            optixERPSEastSendMSGNum
                Unsigned32,
            optixERPSWestSendMSGNum
                Unsigned32,
            optixERPSEastReceiveMSGNum
                Unsigned32,
            optixERPSWestReceiveMSGNum
                Unsigned32,
            optixERPSEastReceiveErrMSGNum
                Unsigned32,
            optixERPSWestReceiveErrMSGNum
                Unsigned32,
            optixERPSCLrMSGStatic
                INTEGER,
            optixERPSDebugWtrTime
                Unsigned32,
            optixERPSEthType
                Unsigned32,
            optixERPSLoopDetect
                INTEGER,
            optixERPSRingRole
                INTEGER,
            optixERPSInternode
                INTEGER,
            optixERPSMultifailure
                INTEGER,
            optixERPSRowStatus
                RowStatus
        }

    -- 1.3.6.1.4.1.2011.2.25.4.50.26.1.1.1.1
    optixERPSId OBJECT-TYPE
        SYNTAX Unsigned32
        MAX-ACCESS read-only
        STATUS current
        DESCRIPTION
            "This object indicates the ERPS protocol instance ID. Value range: 1 to 8."
        ::= { optixERPSEntry 1 }

    -- 1.3.6.1.4.1.2011.2.25.4.50.26.1.1.1.2
    optixERPSEastBoardId OBJECT-TYPE
        SYNTAX Unsigned32
        MAX-ACCESS read-create
        STATUS current
        DESCRIPTION
            "This object indicates the east slot ID of the ERPS. If there is no east port, the slot ID is 0xffff."
        ::= { optixERPSEntry 2 }

    -- 1.3.6.1.4.1.2011.2.25.4.50.26.1.1.1.3
    optixERPSEastSubboardId OBJECT-TYPE
        SYNTAX Unsigned32
        MAX-ACCESS read-create
        STATUS current
        DESCRIPTION
            "This object indicates the east subboard ID of the ERPS. If there is no subboard, the value is 0xFF."
        ::= { optixERPSEntry 3 }

    -- 1.3.6.1.4.1.2011.2.25.4.50.26.1.1.1.4
    optixERPSEastPort OBJECT-TYPE
        SYNTAX Unsigned32
        MAX-ACCESS read-create
        STATUS current
        DESCRIPTION
            "This object indicates the east port number of the ERPS. Value range: 1 to MAX_ETH_PORT. If there is no east port, the value is 0xffff."
        ::= { optixERPSEntry 4 }

    -- 1.3.6.1.4.1.2011.2.25.4.50.26.1.1.1.5
    optixERPSWestBoardId OBJECT-TYPE
        SYNTAX Unsigned32
        MAX-ACCESS read-create
        STATUS current
        DESCRIPTION
            "This object indicates the west slot ID of the ERPS. If there is no west port, the slot ID is 0xffff."
        ::= { optixERPSEntry 5 }

    -- 1.3.6.1.4.1.2011.2.25.4.50.26.1.1.1.6
    optixERPSWestSubboardId OBJECT-TYPE
        SYNTAX Unsigned32
        MAX-ACCESS read-create
        STATUS current
        DESCRIPTION
            "This object indicates the westsubboard ID of the ERPS. If there is no subboard, the value is 0xFF."
        ::= { optixERPSEntry 6 }

    -- 1.3.6.1.4.1.2011.2.25.4.50.26.1.1.1.7
    optixERPSWestPort OBJECT-TYPE
        SYNTAX Unsigned32
        MAX-ACCESS read-create
        STATUS current
        DESCRIPTION
            "This object indicates the west port number of the ERPS. Value range: 1 to MAX_ETH_PORT. If there is no west port, the value is 0xffff."
        ::= { optixERPSEntry 7 }

    -- 1.3.6.1.4.1.2011.2.25.4.50.26.1.1.1.8
    optixERPSRplBoardId OBJECT-TYPE
        SYNTAX Unsigned32
        MAX-ACCESS read-create
        STATUS current
        DESCRIPTION
            "This object indicates the slot ID of the ERPSRPL port. If there is no RPL port, the slot ID is 0xffff."
        ::= { optixERPSEntry 8 }

    -- 1.3.6.1.4.1.2011.2.25.4.50.26.1.1.1.9
    optixERPSRplSubboardId OBJECT-TYPE
        SYNTAX Unsigned32
        MAX-ACCESS read-create
        STATUS current
        DESCRIPTION
            "This object indicates the subboard ID of the ERPS RPL port. If there is no subboard, the value is 0xFF."
        ::= { optixERPSEntry 9 }

    -- 1.3.6.1.4.1.2011.2.25.4.50.26.1.1.1.10
    optixERPSRplPort OBJECT-TYPE
        SYNTAX Unsigned32
        MAX-ACCESS read-create
        STATUS current
        DESCRIPTION
            "This object indicates the port number of the ERPS RPL port. Value range: 1 to MAX_ETH_PORT. If there is no RPL port, the value is 0xffff."
        ::= { optixERPSEntry 10 }

    -- 1.3.6.1.4.1.2011.2.25.4.50.26.1.1.1.11
    optixERPSRplownerFlag OBJECT-TYPE
        SYNTAX INTEGER
        {
            none(0),
            rplport(1),
            rplneigh(2),
            rplnextneigh(3)
        }
        MAX-ACCESS read-create
        STATUS current
        DESCRIPTION
            "This object indicates whether a node is an RPL owner ring node. 0: none, 1: rplport, 2: rplneigh, 3: rplnextneigh"
        ::= { optixERPSEntry 11 }

    -- 1.3.6.1.4.1.2011.2.25.4.50.26.1.1.1.12
    optixERPSCtrlVlan OBJECT-TYPE
        SYNTAX Unsigned32
        MAX-ACCESS read-create
        STATUS current
        DESCRIPTION
            "This object indicates the ERPS control VLAN. Value range: 1 to 4094."
        ::= { optixERPSEntry 12 }

    -- 1.3.6.1.4.1.2011.2.25.4.50.26.1.1.1.13
    optixERPSDmac OBJECT-TYPE
        SYNTAX OCTET STRING (SIZE(0..64))
        MAX-ACCESS read-create
        STATUS current
        DESCRIPTION
            "This object indicates the ERPS DMAC. Value range: 01-19-A7-00-00-00 to 01-19-A7-00- 00 -FF. The current version uses a fixed value of 01-19-A7-00-00-01."
        ::= { optixERPSEntry 13 }

    -- 1.3.6.1.4.1.2011.2.25.4.50.26.1.1.1.14
    optixERPSNodeId OBJECT-TYPE
        SYNTAX OCTET STRING (SIZE(0..64))
        MAX-ACCESS read-only
        STATUS current
        DESCRIPTION
            "This object indicates the current node ID of the ERPS. Value range: 01-19-A7-00-00-00 to 01-19-A7-00- 00 -FF. The current version uses a fixed value of 01-19-A7-00-00-01."
        ::= { optixERPSEntry 14 }

    -- 1.3.6.1.4.1.2011.2.25.4.50.26.1.1.1.15
    optixERPSHoldoffTime OBJECT-TYPE
        SYNTAX Unsigned32
        MAX-ACCESS read-create
        STATUS current
        DESCRIPTION
            "This object indicates the ERPS delay time. Value range: 0 to 10000 (unit: ms). The default value is 0 and the step length is 100."
        ::= { optixERPSEntry 15 }

    -- 1.3.6.1.4.1.2011.2.25.4.50.26.1.1.1.16
    optixERPSWtrTime OBJECT-TYPE
        SYNTAX Unsigned32
        MAX-ACCESS read-create
        STATUS current
        DESCRIPTION
            "This object indicates the ERPSWTR time. Value range: 1 to 12 (unit: minute). The default value is 5 and the step length is 1."
        ::= { optixERPSEntry 16 }

    -- 1.3.6.1.4.1.2011.2.25.4.50.26.1.1.1.17
    optixERPSGuardTime OBJECT-TYPE
        SYNTAX Unsigned32
        MAX-ACCESS read-create
        STATUS current
        DESCRIPTION
            "This object indicates the ERPS guard time. Value range: 10 to 2000 (unit: ms). The default value is 500 and the step length is 10."
        ::= { optixERPSEntry 17 }

    -- 1.3.6.1.4.1.2011.2.25.4.50.26.1.1.1.18
    optixERPSMel OBJECT-TYPE
        SYNTAX Unsigned32
        MAX-ACCESS read-create
        STATUS current
        DESCRIPTION
            "This object indicates the ERPS MEL. Value range: 0 to 7. The default value is 4."
        ::= { optixERPSEntry 18 }

    -- 1.3.6.1.4.1.2011.2.25.4.50.26.1.1.1.19
    optixERPSInterval OBJECT-TYPE
        SYNTAX Unsigned32
        MAX-ACCESS read-create
        STATUS current
        DESCRIPTION
            "This object indicates the ERPS packet transmitting interval. Value range: 1 to 10 (unit: s). The default value is 5 and the step length is 1."
        ::= { optixERPSEntry 19 }

    -- 1.3.6.1.4.1.2011.2.25.4.50.26.1.1.1.20
    optixERPSLastRequest OBJECT-TYPE
        SYNTAX INTEGER
        {
            rapsNr(1),
            rapsNrRb(2),
            wtrRunning(3),
            wtrExpires(4),
            rapsSf(5),
            localSf(6),
            localClrSf(7),
            initRequest(8),
            clear(9),
            rapsMs(12),
            ms(13),
            wtbRunning(14),
            wtbExpires(15),
            fs(10),
            rapsFs(11)
        }
        MAX-ACCESS read-only
        STATUS current
        DESCRIPTION
            "This object indicates the last ERPS switching request. 1: rapsNr, 2: rapsNrRb, 3: wtrRunning, 4: wtrExpires, 5: rapsSf, 6: localSf, 7: localClrSf, 8: initRequest, 9: clear, 10: fs, 11: rapsFs, 12: rapsMs, 13: ms, 14: wtbRunning, 15: wtbExpires"
        ::= { optixERPSEntry 20 }

    -- 1.3.6.1.4.1.2011.2.25.4.50.26.1.1.1.21
    optixERPSRbState OBJECT-TYPE
        SYNTAX INTEGER
        {
            noRb(0),
            rb(1)
        }
        MAX-ACCESS read-only
        STATUS current
        DESCRIPTION
            "This object indicates the RB status of the ERPS. 0: no RB, 1: RB"
        ::= { optixERPSEntry 21 }

    -- 1.3.6.1.4.1.2011.2.25.4.50.26.1.1.1.22
    optixERPSDnfState OBJECT-TYPE
        SYNTAX INTEGER
        {
            noDnf(0),
            dnf(1)
        }
        MAX-ACCESS read-only
        STATUS current
        DESCRIPTION
            "This object indicates whether the remote request of the ERPS is in DNF state. 0: no DNF, 1: DNF"
        ::= { optixERPSEntry 22 }

    -- 1.3.6.1.4.1.2011.2.25.4.50.26.1.1.1.23
    optixERPSReceiveNodeId OBJECT-TYPE
        SYNTAX OCTET STRING (SIZE(0..64))
        MAX-ACCESS read-only
        STATUS current
        DESCRIPTION
            "This object indicates the source node ID of the ERPS switching request, which is an MAC address. Value range: 01-19-A7-00-00-00 to 01-19-A7-00- 00 -FF. The current version uses a fixed value of 01-19-A7-00-00-01."
        ::= { optixERPSEntry 23 }

    -- 1.3.6.1.4.1.2011.2.25.4.50.26.1.1.1.24
    optixERPSFsmState OBJECT-TYPE
        SYNTAX INTEGER
        {
            idle(0),
            protection(1),
            forceswitch(2),
            manualswitch(3),
            pending(4)
        }
        MAX-ACCESS read-only
        STATUS current
        DESCRIPTION
            "This object indicates the state machine status of the current node of the ERPS. 0: idle, 1: protection, 2: forceswitch, 3: manualswitch, 4: pending"
        ::= { optixERPSEntry 24 }

    -- 1.3.6.1.4.1.2011.2.25.4.50.26.1.1.1.25
    optixERPSEastPortState OBJECT-TYPE
        SYNTAX INTEGER
        {
            block(0),
            unblock(1)
        }
        MAX-ACCESS read-only
        STATUS current
        DESCRIPTION
            "This object indicates the current status of the east port of the ERPS. 0: block, 1: unblock"
        ::= { optixERPSEntry 25 }

    -- 1.3.6.1.4.1.2011.2.25.4.50.26.1.1.1.26
    optixERPSWestPortState OBJECT-TYPE
        SYNTAX INTEGER
        {
            block(0),
            unblock(1)
        }
        MAX-ACCESS read-only
        STATUS current
        DESCRIPTION
            "This object indicates the current status of the west port of the ERPS. 0: block, 1: unblock"
        ::= { optixERPSEntry 26 }

    -- 1.3.6.1.4.1.2011.2.25.4.50.26.1.1.1.27
    optixERPSvchannelState OBJECT-TYPE
        SYNTAX INTEGER
        {
            enable(1),
            disable(0)
        }
        MAX-ACCESS read-create
        STATUS current
        DESCRIPTION
            "This object indicates the enable status of the virtual channel of the ERPS. 0: disable, 1: enable"
        ::= { optixERPSEntry 27 }

    -- 1.3.6.1.4.1.2011.2.25.4.50.26.1.1.1.28
    optixERPSmajorID OBJECT-TYPE
        SYNTAX Unsigned32
        MAX-ACCESS read-create
        STATUS current
        DESCRIPTION
            "This object indicates the master ring network ID of the ERPS. Value range: 1 to 8."
        ::= { optixERPSEntry 28 }

    -- 1.3.6.1.4.1.2011.2.25.4.50.26.1.1.1.29
    optixERPSVerId OBJECT-TYPE
        SYNTAX INTEGER
        {
            ver1(1),
            ver2(2)
        }
        MAX-ACCESS read-create
        STATUS current
        DESCRIPTION
            "This object indicates the version of the ERPS. 1: ver1, 2: ver2"
        ::= { optixERPSEntry 29 }

    -- 1.3.6.1.4.1.2011.2.25.4.50.26.1.1.1.30
    optixERPSRvtMode OBJECT-TYPE
        SYNTAX INTEGER
        {
            norvt(0),
            rvt(1)
        }
        MAX-ACCESS read-create
        STATUS current
        DESCRIPTION
            "This object indicates revert mode of the ERPS. 0: norvt, 1: rvt"
        ::= { optixERPSEntry 30 }

    -- 1.3.6.1.4.1.2011.2.25.4.50.26.1.1.1.31
    optixERPSSWCMode OBJECT-TYPE
        SYNTAX INTEGER
        {
            clear(0),
            mseast(1),
            mswest(2),
            fseast(3),
            fswest(4),
            invalid(255)
        }
        MAX-ACCESS read-create
        STATUS current
        DESCRIPTION
            "This object indicates the external switch mode of the ERPS,but the getting operator is invalid,assigning it 255. 0: clear, 1: mseast, 2: mswest, 3: fseast, 4: fswest, 255: invalide"
        ::= { optixERPSEntry 31 }

    -- 1.3.6.1.4.1.2011.2.25.4.50.26.1.1.1.32
    optixERPSVchannelIdNum OBJECT-TYPE
        SYNTAX Unsigned32
        MAX-ACCESS read-create
        STATUS current
        DESCRIPTION
            "This object indicates the number of the VLAN ID of the ERPS. Value range: 0 to 255. The value 0 indicates that all VLANs are deleted."
        ::= { optixERPSEntry 32 }

    -- 1.3.6.1.4.1.2011.2.25.4.50.26.1.1.1.33
    optixERPSVchannelIdList OBJECT-TYPE
        SYNTAX OCTET STRING (SIZE(0..64))
        MAX-ACCESS read-create
        STATUS current
        DESCRIPTION
            "This object indicates the VLAN List of the ERPS. Value range: 1 to 4094. &amp;amp; is used to separate multiple VLANs. For example, 1 &amp;amp; 2 &amp;amp; 3"
        ::= { optixERPSEntry 33 }

    -- 1.3.6.1.4.1.2011.2.25.4.50.26.1.1.1.34
    optixERPSEastSendMSGNum OBJECT-TYPE
        SYNTAX Unsigned32
        MAX-ACCESS not-accessible
        STATUS current
        DESCRIPTION
            "This object indicates the number of East send message of the ERPS. Value range: 0 to 0xffffffff."
        ::= { optixERPSEntry 34 }

    -- 1.3.6.1.4.1.2011.2.25.4.50.26.1.1.1.35
    optixERPSWestSendMSGNum OBJECT-TYPE
        SYNTAX Unsigned32
        MAX-ACCESS not-accessible
        STATUS current
        DESCRIPTION
            "This object indicates the number of West send message of the ERPS. Value range: 0 to 0xffffffff."
        ::= { optixERPSEntry 35 }

    -- 1.3.6.1.4.1.2011.2.25.4.50.26.1.1.1.36
    optixERPSEastReceiveMSGNum OBJECT-TYPE
        SYNTAX Unsigned32
        MAX-ACCESS not-accessible
        STATUS current
        DESCRIPTION
            "This object indicates the number of East receive message of the ERPS. Value range: 0 to 0xffffffff."
        ::= { optixERPSEntry 36 }

    -- 1.3.6.1.4.1.2011.2.25.4.50.26.1.1.1.37
    optixERPSWestReceiveMSGNum OBJECT-TYPE
        SYNTAX Unsigned32
        MAX-ACCESS not-accessible
        STATUS current
        DESCRIPTION
            "This object indicates the number of West receive message of the ERPS. Value range: 0 to 0xffffffff."
        ::= { optixERPSEntry 37 }

    -- 1.3.6.1.4.1.2011.2.25.4.50.26.1.1.1.38
    optixERPSEastReceiveErrMSGNum OBJECT-TYPE
        SYNTAX Unsigned32
        MAX-ACCESS not-accessible
        STATUS current
        DESCRIPTION
            "This object indicates the number of East send error message of the ERPS. Value range: 0 to 0xffffffff."
        ::= { optixERPSEntry 38 }

    -- 1.3.6.1.4.1.2011.2.25.4.50.26.1.1.1.39
    optixERPSWestReceiveErrMSGNum OBJECT-TYPE
        SYNTAX Unsigned32
        MAX-ACCESS not-accessible
        STATUS current
        DESCRIPTION
            "This object indicates the number of West send error message of the ERPS. Value range: 0 to 0xffffffff."
        ::= { optixERPSEntry 39 }

    -- 1.3.6.1.4.1.2011.2.25.4.50.26.1.1.1.40
    optixERPSCLrMSGStatic OBJECT-TYPE
        SYNTAX INTEGER
        {
            clear(0),
            invalid(255)
        }
        MAX-ACCESS not-accessible
        STATUS current
        DESCRIPTION
            "This object indicates clearing the message of the ERPS,but the getting operator is invalid,assigning it 255."
        ::= { optixERPSEntry 40 }

    -- 1.3.6.1.4.1.2011.2.25.4.50.26.1.1.1.41
    optixERPSDebugWtrTime OBJECT-TYPE
        SYNTAX Unsigned32
        MAX-ACCESS not-accessible
        STATUS current
        DESCRIPTION
            "This object indicates debugging the waiting for resuming time of the ERPS. Value range: 1 to 65535 (unit: s). The default value is 300."
        ::= { optixERPSEntry 41 }

    -- 1.3.6.1.4.1.2011.2.25.4.50.26.1.1.1.42
    optixERPSEthType OBJECT-TYPE
        SYNTAX Unsigned32
        MAX-ACCESS read-create
        STATUS current
        DESCRIPTION
            "This object indicates the ETH type of the ERPS. 0x8809: transmission mode, 0x8902: standard mode"
        ::= { optixERPSEntry 42 }

    -- 1.3.6.1.4.1.2011.2.25.4.50.26.1.1.1.43
    optixERPSLoopDetect OBJECT-TYPE
        SYNTAX INTEGER
        {
            disable(0),
            enable(1)
        }
        MAX-ACCESS read-create
        STATUS current
        DESCRIPTION
            "This object indicates the state of loop detect of the ERPS. 0: disable, 1: enable"
        ::= { optixERPSEntry 43 }

    -- 1.3.6.1.4.1.2011.2.25.4.50.26.1.1.1.44
    optixERPSRingRole OBJECT-TYPE
        SYNTAX INTEGER
        {
            unknown(255),
            major(1),
            sub(2)
        }
        MAX-ACCESS read-create
        STATUS current
        DESCRIPTION
            "This object indicates the ring role of the ERPS. 255: unknown, 1: major,2:sub"
        ::= { optixERPSEntry 44 }

    -- 1.3.6.1.4.1.2011.2.25.4.50.26.1.1.1.45
    optixERPSInternode OBJECT-TYPE
        SYNTAX INTEGER
        {
            none(0),
            primary(1),
            secondary(2)
        }
        MAX-ACCESS read-create
        STATUS current
        DESCRIPTION
            "This parameter indicates the interconnection attribute of current node ID of ERPS ."
        ::= { optixERPSEntry 45 }

    -- 1.3.6.1.4.1.2011.2.25.4.50.26.1.1.1.46
    optixERPSMultifailure OBJECT-TYPE
        SYNTAX INTEGER
        {
            disable(0),
            primary(1),
            secondary(2)
        }
        MAX-ACCESS read-create
        STATUS current
        DESCRIPTION
            "This parameter indicates the multifailure attribute of current node ID of ERPS ."
        ::= { optixERPSEntry 46 }

    -- 1.3.6.1.4.1.2011.2.25.4.50.26.1.1.1.255
    optixERPSRowStatus OBJECT-TYPE
        SYNTAX RowStatus
        MAX-ACCESS read-create
        STATUS current
        DESCRIPTION
            "This object indicates the row status of the ERPS."
        ::= { optixERPSEntry 255 }

    -- 1.3.6.1.4.1.2011.2.25.4.50.26.1.2
    optixL2ErpsStateChangeEvent OBJECT IDENTIFIER ::= { optixPktErpsGroup 2 }

    -- 1.3.6.1.4.1.2011.2.25.4.50.26.1.2.1
    optixL2ErpsStateChange NOTIFICATION-TYPE
        OBJECTS{ optixERPSId,optixERPSLastRequest,optixERPSFsmState }
        STATUS current
        DESCRIPTION
            "This object is used to report ERPS switching events."
        ::= { optixL2ErpsStateChangeEvent 1 }

    -- 1.3.6.1.4.1.2011.2.25.4.50.26.1.3
    optixERPSVchannelTable OBJECT-TYPE
        SYNTAX SEQUENCE OF OptixERPSVchannelEntry
        MAX-ACCESS not-accessible
        STATUS current
        DESCRIPTION
            "This table describes the basic ERPS V-channel configurations."
        ::= { optixPktErpsGroup 3 }

    -- 1.3.6.1.4.1.2011.2.25.4.50.26.1.3.1
    optixERPSVchannelEntry OBJECT-TYPE
        SYNTAX OptixERPSVchannelEntry
        MAX-ACCESS not-accessible
        STATUS current
        DESCRIPTION
            "This entry describes the basic ERPS V-channel configurations."
        INDEX{ optixERPSId,optixERPSVchannelId }
        ::= { optixERPSVchannelTable 1 }

    OptixERPSVchannelEntry ::=
        SEQUENCE {
            optixERPSVchannelId
                Unsigned32,
            optixERPSVchannelRowStatus
                RowStatus
        }

    -- 1.3.6.1.4.1.2011.2.25.4.50.26.1.3.1.1
    optixERPSVchannelId OBJECT-TYPE
        SYNTAX Unsigned32
        MAX-ACCESS not-accessible
        STATUS current
        DESCRIPTION
            "This object indicates the ERPS V-channel ID. Value range: 1 to 4094."
        ::= { optixERPSVchannelEntry 1 }

    -- 1.3.6.1.4.1.2011.2.25.4.50.26.1.3.1.255
    optixERPSVchannelRowStatus OBJECT-TYPE
        SYNTAX RowStatus
        MAX-ACCESS read-only
        STATUS current
        DESCRIPTION
            "This object indicates the row status of the ERPS V-channel."
        ::= { optixERPSVchannelEntry 255 }

    -- 1.3.6.1.4.1.2011.2.25.4.50.26.1.4
    optixERPSVlanTable OBJECT-TYPE
        SYNTAX SEQUENCE OF OptixERPSVlanEntry
        MAX-ACCESS not-accessible
        STATUS current
        DESCRIPTION
            "This table describes the basic ERPS VLAN configurations."
        ::= { optixPktErpsGroup 4 }

    -- 1.3.6.1.4.1.2011.2.25.4.50.26.1.4.1
    optixERPSVlanEntry OBJECT-TYPE
        SYNTAX OptixERPSVlanEntry
        MAX-ACCESS not-accessible
        STATUS current
        DESCRIPTION
            "This entry describes the basic ERPS VLAN configurations."
        INDEX{ optixERPSId,optixERPSSubVlanID }
        ::= { optixERPSVlanTable 1 }

    OptixERPSVlanEntry ::=
        SEQUENCE {
            optixERPSSubVlanID
                Unsigned32,
            optixERPSMainErpsID
                Unsigned32,
            optixERPSMainVlanID
                Unsigned32,
            optixERPSVlanRowStatus
                RowStatus
        }

    -- 1.3.6.1.4.1.2011.2.25.4.50.26.1.4.1.1
    optixERPSSubVlanID OBJECT-TYPE
        SYNTAX Unsigned32
        MAX-ACCESS not-accessible
        STATUS current
        DESCRIPTION
            "This object indicates the ERPS sub-VLAN ID. Value range: 1 to 4094."
        ::= { optixERPSVlanEntry 1 }

    -- 1.3.6.1.4.1.2011.2.25.4.50.26.1.4.1.2
    optixERPSMainErpsID OBJECT-TYPE
        SYNTAX Unsigned32
        MAX-ACCESS read-create
        STATUS current
        DESCRIPTION
            "This object indicates the master ring network protocol ID of theERPS. Value range: 1 to 8."
        ::= { optixERPSVlanEntry 2 }

    -- 1.3.6.1.4.1.2011.2.25.4.50.26.1.4.1.3
    optixERPSMainVlanID OBJECT-TYPE
        SYNTAX Unsigned32
        MAX-ACCESS read-create
        STATUS current
        DESCRIPTION
            "This object indicates the master ERPS VLAN ID. Value range: 1 to 4094."
        ::= { optixERPSVlanEntry 3 }

    -- 1.3.6.1.4.1.2011.2.25.4.50.26.1.4.1.255
    optixERPSVlanRowStatus OBJECT-TYPE
        SYNTAX RowStatus
        MAX-ACCESS read-create
        STATUS current
        DESCRIPTION
            "This object indicates the row status of the ERPS VLAN."
        ::= { optixERPSVlanEntry 255 }

    -- 1.3.6.1.4.1.2011.2.25.4.50.26.1.5
    optixPktErpsMepTable OBJECT-TYPE
        SYNTAX SEQUENCE OF OptixPktErpsMepEntry
        MAX-ACCESS not-accessible
        STATUS current
        DESCRIPTION
            "This table describes the basic configurations of the association between ERPS and MEP."
        ::= { optixPktErpsGroup 5 }

    -- 1.3.6.1.4.1.2011.2.25.4.50.26.1.5.1
    optixPktErpsMepEntry OBJECT-TYPE
        SYNTAX OptixPktErpsMepEntry
        MAX-ACCESS not-accessible
        STATUS current
        DESCRIPTION
            "This entry describes the basic configurations of the association between ERPS and MEP."
        INDEX{ optixERPSId,optixLogBoardId,optixLogSubCardId,optixPortId }
        ::= { optixPktErpsMepTable 1 }

    OptixPktErpsMepEntry ::=
        SEQUENCE {
            optixPktErpsMepNum
                Unsigned32,
            optixPktErpsMepInfo
                OCTET STRING
        }

    -- 1.3.6.1.4.1.2011.2.25.4.50.26.1.5.1.1
    optixPktErpsMepNum OBJECT-TYPE
        SYNTAX Unsigned32
        MAX-ACCESS read-write
        STATUS current
        DESCRIPTION
            "This parameter indicates the number of the associations between one ERPS and many MEPs."
        ::= { optixPktErpsMepEntry 1 }

    -- 1.3.6.1.4.1.2011.2.25.4.50.26.1.5.1.2
    optixPktErpsMepInfo OBJECT-TYPE
        SYNTAX OCTET STRING
        MAX-ACCESS read-write
        STATUS current
        DESCRIPTION
            "This object indicates ERPS-related MEP information, including the MDID, MAID, and MEPID."
        ::= { optixPktErpsMepEntry 2 }

    -- 1.3.6.1.4.1.2011.2.25.4.50.26.1.6
    optixMultiInsERPSTable OBJECT-TYPE
        SYNTAX SEQUENCE OF OptixMultiInsERPSEntry
        MAX-ACCESS not-accessible
        STATUS current
        DESCRIPTION
            "This table describes the basic multi-instance ERPS configurations."
        ::= { optixPktErpsGroup 6 }

    -- 1.3.6.1.4.1.2011.2.25.4.50.26.1.6.1
    optixMultiInsERPSEntry OBJECT-TYPE
        SYNTAX OptixMultiInsERPSEntry
        MAX-ACCESS not-accessible
        STATUS current
        DESCRIPTION
            "This entry describes the basic multi-instance ERPS configurations."
        INDEX{ optixERPSId,optixERPSEastBoardId,optixERPSEastSubboardId,optixERPSEastPort,optixERPSWestBoardId,optixERPSWestSubboardId,optixERPSWestPort,optixERPSRplBoardId,optixERPSRplSubboardId,optixERPSRplPort,optixERPSRplownerFlag,optixERPSCtrlVlan,optixERPSDmac }
        ::= { optixMultiInsERPSTable 1 }

    OptixMultiInsERPSEntry ::=
        SEQUENCE {
            optixMultiInsERPSServiceVlanIdNum
                Unsigned32,
            optixMultiInsERPSServiceVlanIdList
                OCTET STRING,
            optixMultiInsERPSServiceVlanIdListToBeAdded
                OCTET STRING,
            optixMultiInsERPSServiceVlanIdListToBeDeleted
                OCTET STRING,
            optixMultiInsERPSRowStatus
                RowStatus
        }

    -- 1.3.6.1.4.1.2011.2.25.4.50.26.1.6.1.1
    optixMultiInsERPSServiceVlanIdNum OBJECT-TYPE
        SYNTAX Unsigned32
        MAX-ACCESS read-create
        STATUS current
        DESCRIPTION
            "This object indicates the number of service VLAN IDs of the multi-instance ERPS. Value range: 0 to 1024. The value 0 indicates that ERPS protects whole ports."
        ::= { optixMultiInsERPSEntry 1 }

    -- 1.3.6.1.4.1.2011.2.25.4.50.26.1.6.1.2
    optixMultiInsERPSServiceVlanIdList OBJECT-TYPE
        SYNTAX OCTET STRING
        MAX-ACCESS read-create
        STATUS current
        DESCRIPTION
            "This object indicates the service VLAN list of the multi-instance ERPS. Value range: 1 to 4094. &amp; is used to separate multiple service VLANs. For example, 1&amp;2&amp;3."
        ::= { optixMultiInsERPSEntry 2 }

    -- 1.3.6.1.4.1.2011.2.25.4.50.26.1.6.1.3
    optixMultiInsERPSServiceVlanIdListToBeAdded OBJECT-TYPE
        SYNTAX OCTET STRING
        MAX-ACCESS read-create
        STATUS current
        DESCRIPTION
            "This object indicates the service VLAN list to be added to the multi-instance ERPS. Value range: 1 to 4094. &amp; is used to separate multiple service VLANs. For example, 1&amp;2&amp;3."
        ::= { optixMultiInsERPSEntry 3 }

    -- 1.3.6.1.4.1.2011.2.25.4.50.26.1.6.1.4
    optixMultiInsERPSServiceVlanIdListToBeDeleted OBJECT-TYPE
        SYNTAX OCTET STRING
        MAX-ACCESS read-create
        STATUS current
        DESCRIPTION
            "This object indicates the service VLAN list to be deleted from the multi-instance ERPS. Value range: 1 to 4094. &amp; is used to separate multiple service VLANs. For example, 1&amp;2&amp;3."
        ::= { optixMultiInsERPSEntry 4 }

    -- 1.3.6.1.4.1.2011.2.25.4.50.26.1.6.1.255
    optixMultiInsERPSRowStatus OBJECT-TYPE
        SYNTAX RowStatus
        MAX-ACCESS read-create
        STATUS current
        DESCRIPTION
            "This object indicates the row status of the mulit-instance ERPS."
        ::= { optixMultiInsERPSEntry 255 }

END
