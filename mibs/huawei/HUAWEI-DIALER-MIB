-- ==================================================================
-- Copyright (C) 2010 by HUAWEI TECHNOLOGIES. All rights reserved.
-- 
-- Description:  This MIB module defines MIB objects of hwDccTable, hwDccRuleTable.
--
-- HUAWEI-DIALER-MIB.mib
-- MIB generated by MG-SOFT Visual MIB Builder Version 3.0 Build 253
-- Friday, December 17, 2010 at 17:35:53
-- Reference:
-- Version: V1.10
-- History:
-- V1.0 2007-10-21 publish
-- ==================================================================

	HUAWEI-DIALER-MIB DEFINITIONS ::= BEGIN
 
		IMPORTS
			hwDatacomm			
				FROM HUAWEI-MIB			
			OBJECT-GROUP, MODULE-COMPLIANCE, NOTIFICATION-GROUP            
				FROM SNMPv2-CONF            
			Integer32, OBJECT-TYPE, MODULE-IDENTITY			
				FROM SNMPv2-SMI;
	
	
--  1.3.6.1.4.1.2011.5.25.18
-- May 18, 2004 at 00:00 GMT
		hwDialer MODULE-IDENTITY 
			LAST-UPDATED "201012130000Z"		-- December 13, 2010 at 00:00 GMT
			ORGANIZATION 
              			"Huawei Technologies Co.,Ltd."
			CONTACT-INFO 
				"Huawei Industrial Base                
				Bantian, Longgang                     
				Shenzhen 518129                       
				People's Republic of China            
				Website: http://www.huawei.com        
				Email: support@huawei.com             
				"  
			DESCRIPTION 
				"The HUAWEI-MP-MIB provides read access to MP(Multilink PPP) link
				status information. The information available through this MIB includes:
				the father channel, the bundled son channel, the slot on which MP bundled, 
				the number of son channels, the bundle name,
				the statistic of lost fragments, reordered packets, unassigned packets, 
				interleaved packets, and the received/sent sequence, etc.
				"
			REVISION "201012142109Z"		-- December 14, 2010 at 21:09 GMT
			DESCRIPTION
				"v1.10 The HUAWEI-DCC-MIB provides read access to DCC 
								status information. The information available through this MIB includes:
								etc."
			REVISION "201012142103Z"		-- December 14, 2010 at 21:03 GMT
			DESCRIPTION
				"v1.00 123"
			::= { hwDatacomm 244 }
		
	
	
--
-- Node definitions
--
	
--  Node definitions
-- 
		-- 1.3.6.1.4.1.2011.5.25.244.1
		hwDccObjects OBJECT IDENTIFIER ::= { hwDialer 1 }
		
		-- 1.3.6.1.4.1.2011.5.25.244.1.1
		hwDccTable OBJECT-TYPE
			SYNTAX SEQUENCE OF HwDccEntry
			MAX-ACCESS not-accessible
			STATUS current
			DESCRIPTION
				"This table describes the information of MP link. 
				The index of this table is the interface index of MP group or 
				VT(Virtual Template)."
			::= { hwDccObjects 1 }
		
		-- 1.3.6.1.4.1.2011.5.25.244.1.1.1
		hwDccEntry OBJECT-TYPE
			SYNTAX HwDccEntry
			MAX-ACCESS not-accessible
			STATUS current
			DESCRIPTION
				"Each entry in this table describes the information of MP link.
				The available information includes: 
				the father channel, the slot on which MP bundled, 
				the number of bundled son channels, 
				the statistics of lost fragments, reordered packets, 
				unassigned packets, interleaved packets, 
				and received/sent sequence.                         
				"
			INDEX { hwDccIfIndex }
			::= { hwDccTable 1 }
		
		HwDccEntry ::=
			SEQUENCE { 
				hwDccIfIndex
					Integer32,
				hwCircular
					Integer32,
				hwIdleTime
					Integer32,
				hwDialUser
					OCTET STRING,
				hwDialGroup
					Integer32,
				hwDialBundle
					Integer32,
				hwDialNumber
					OCTET STRING,
				hwDialBundleMem
					Integer32,
				hwDialCirGroup
					Integer32
			 }

		-- 1.3.6.1.4.1.2011.5.25.244.1.1.1.1
		hwDccIfIndex OBJECT-TYPE
			SYNTAX Integer32 (1..40000000)
			MAX-ACCESS not-accessible
			STATUS current
			DESCRIPTION
				"Description."
			::= { hwDccEntry 1 }
		
		-- 1.3.6.1.4.1.2011.5.25.244.1.1.1.2
		hwCircular OBJECT-TYPE
			SYNTAX Integer32
			MAX-ACCESS read-write
			STATUS current
			DESCRIPTION
				"The interface name of the father interface on which MP bundled. 
				It is the name of a Virtual Temblate or a MP group."
			::= { hwDccEntry 2 }
		
		-- 1.3.6.1.4.1.2011.5.25.244.1.1.1.3
		hwIdleTime OBJECT-TYPE
			SYNTAX Integer32
			MAX-ACCESS read-write
			STATUS current
			DESCRIPTION
				"The bundle name of the multilink. 
				when authentication is configured, the bundle name is the authenticated
				user name; when authentication not configured, the bundle name is
				multilink.
				"
			::= { hwDccEntry 3 }
		
		-- 1.3.6.1.4.1.2011.5.25.244.1.1.1.4
		hwDialUser OBJECT-TYPE
			SYNTAX OCTET STRING
			MAX-ACCESS read-write
			STATUS current
			DESCRIPTION
				"The slot on which MP bundled. 
				"
			::= { hwDccEntry 4 }
		
		-- 1.3.6.1.4.1.2011.5.25.244.1.1.1.5
		hwDialGroup OBJECT-TYPE
			SYNTAX Integer32
			MAX-ACCESS read-write
			STATUS current
			DESCRIPTION
				"The number of the bundled son channel of the MP link. "
			::= { hwDccEntry 5 }
		
		-- 1.3.6.1.4.1.2011.5.25.244.1.1.1.6
		hwDialBundle OBJECT-TYPE
			SYNTAX Integer32
			MAX-ACCESS read-write
			STATUS current
			DESCRIPTION
				"The number of fragments of the MP link discarded because 
				bad fragments received, or assembling packet failed, etc."
			::= { hwDccEntry 6 }
		
		-- 1.3.6.1.4.1.2011.5.25.244.1.1.1.7
		hwDialNumber OBJECT-TYPE
			SYNTAX OCTET STRING
			MAX-ACCESS read-write
			STATUS current
			DESCRIPTION
				"The number of received packets of the MP link reordered.
				"
			::= { hwDccEntry 7 }
		
		-- 1.3.6.1.4.1.2011.5.25.244.1.1.1.8
		hwDialBundleMem OBJECT-TYPE
			SYNTAX Integer32
			MAX-ACCESS read-write
			STATUS current
			DESCRIPTION
				"The number of received packets of the MP link waiting for reordering.
				"
			::= { hwDccEntry 8 }
		
		-- 1.3.6.1.4.1.2011.5.25.244.1.1.1.9
		hwDialCirGroup OBJECT-TYPE
			SYNTAX Integer32
			MAX-ACCESS read-write
			STATUS current
			DESCRIPTION
				"The number of received packets of the MP link interleaved by the 
				packets queued in RTPQ(Real-time Transport Protocol Queue) or 
				LLQ(Low Latency Queue).
				"
			::= { hwDccEntry 9 }
		
		-- 1.3.6.1.4.1.2011.5.25.244.1.2
		hwDccRuleTable OBJECT-TYPE
			SYNTAX SEQUENCE OF HwDccRuleEntry
			MAX-ACCESS not-accessible
			STATUS current
			DESCRIPTION
				"Description."
			::= { hwDccObjects 2 }
		
		-- 1.3.6.1.4.1.2011.5.25.244.1.2.1
		hwDccRuleEntry OBJECT-TYPE
			SYNTAX HwDccRuleEntry
			MAX-ACCESS not-accessible
			STATUS current
			DESCRIPTION
				"Description."
			INDEX { hwDialRule }
			::= { hwDccRuleTable 1 }
		
		HwDccRuleEntry ::=
			SEQUENCE { 
				hwDialRule
					Integer32,
				hwDialProType
					Integer32,
				hwDialAclNumber
					Integer32
			 }

		-- 1.3.6.1.4.1.2011.5.25.244.1.2.1.1
		hwDialRule OBJECT-TYPE
			SYNTAX Integer32 (1..255)
			MAX-ACCESS not-accessible
			STATUS current
			DESCRIPTION
				"Description."
			::= { hwDccRuleEntry 1 }
		
		-- 1.3.6.1.4.1.2011.5.25.244.1.2.1.2
		hwDialProType OBJECT-TYPE
			SYNTAX Integer32
			MAX-ACCESS read-write
			STATUS current
			DESCRIPTION
				"Description."
			::= { hwDccRuleEntry 2 }
		
		-- 1.3.6.1.4.1.2011.5.25.244.1.2.1.3
		hwDialAclNumber OBJECT-TYPE
			SYNTAX Integer32
			MAX-ACCESS read-write
			STATUS current
			DESCRIPTION
				"Description."
			::= { hwDccRuleEntry 3 }
			
--  ============== conformance information ==============
		-- 1.3.6.1.4.1.2011.5.25.244.2
		hwDccMIBConformance OBJECT IDENTIFIER ::= { hwDialer 2 }
		        
	        hwDccMIBCompliances OBJECT IDENTIFIER ::= { hwDccMIBConformance 1 }
	        hwDccMIBCompliance MODULE-COMPLIANCE
	               STATUS      current
	               DESCRIPTION
	                   "The compliance statement for systems supporting 
	                the this module."
	
	               MODULE      -- this module
	               MANDATORY-GROUPS    {hwDccGroup,  hwDccRuleGroup}  
	                                               
	              ::= { hwDccMIBCompliances 1 } 
	              
	              
        --  ============== groups ==============  
		-- 1.3.6.1.4.1.2011.5.25.244.2.1
		hwDccMIBGroups OBJECT IDENTIFIER ::= { hwDccMIBConformance 2 }
		
		-- 1.3.6.1.4.1.2011.5.25.244.2.1.1
		hwDccGroup OBJECT-GROUP
			OBJECTS { hwCircular, hwIdleTime, hwDialUser, hwDialGroup, hwDialBundle, 
				hwDialNumber, hwDialBundleMem, hwDialCirGroup, hwDccIfIndex }
			STATUS current
			DESCRIPTION 
				"Description."
			::= { hwDccMIBGroups 1 }
		
		-- 1.3.6.1.4.1.2011.5.25.244.2.1.2
		hwDccRuleGroup OBJECT-GROUP
			OBJECTS { hwDialProType, hwDialAclNumber, hwDialRule }
			STATUS current
			DESCRIPTION 
				"Description."
			::= { hwDccMIBGroups 2 }
		
	
	END

--
-- HUAWEI-DIALER-MIB.mib
--
