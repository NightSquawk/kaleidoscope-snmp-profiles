-- OPTIX-GLOBAL-SFTM-TRAPS-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-SFTM-TRAPS-MIB DEFINITIONS ::= BEGIN
    IMPORTS
        optixCommonGlobal
            FROM OPTIX-OID-MIB
        MODULE-IDENTITY,OBJECT-TYPE,NOTIFICATION-TYPE
            FROM SNMPv2-SMI
        ;

    optixGlobalSftmTrap MODULE-IDENTITY
        LAST-UPDATED "201607061029Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "Information about SFTM TRAP nodes"
        REVISION "201607061029Z"
        DESCRIPTION
            "optixGlobalSftmTrap"
        ::={ optixCommonGlobal 8 }

    -- 1.3.6.1.4.1.2011.2.25.3.40.8.1
    optixTrapsSftmCommon OBJECT IDENTIFIER ::= { optixGlobalSftmTrap 1 }

    -- 1.3.6.1.4.1.2011.2.25.3.40.8.1.1
    rptPatchEvtType OBJECT-TYPE
        SYNTAX INTEGER
        {
            canntact(1),
            actstart(2),
            actfinish(3),
            actstop(4),
            actcancel(5),
            deactive(6),
            rollback(7),
            actfail(8),
            statechange(9),
            errreport(10),
            switchdisable(11),
            switchenable(12),
            bdcmdfinish(13),
            process(14),
            backupstart(15),
            backupend(16)
        }
        MAX-ACCESS accessible-for-notify
        STATUS current
        DESCRIPTION
            "rptPatchEvtType"
        ::= { optixTrapsSftmCommon 1 }

    -- 1.3.6.1.4.1.2011.2.25.3.40.8.1.2
    rptPatchEvtAction OBJECT-TYPE
        SYNTAX INTEGER
        {
            null(0),
            dnldpkg(1),
            loadfile(2),
            loadmem(3),
            active(4),
            deactive(5),
            run(6),
            install(7),
            delete(8),
            rollback(9),
            cancel(10),
            bdonline(11),
            checkstate(12),
            dnldhalt(13),
            matchbd(14),
            matchslv(15),
            commit(16),
            autoexclude(17),
            checksccchange(18)
        }
        MAX-ACCESS accessible-for-notify
        STATUS current
        DESCRIPTION
            "rptPatchEvtAction"
        ::= { optixTrapsSftmCommon 2 }

    -- 1.3.6.1.4.1.2011.2.25.3.40.8.1.3
    rptPatchEvtCmd OBJECT-TYPE
        SYNTAX INTEGER
        MAX-ACCESS accessible-for-notify
        STATUS current
        DESCRIPTION
            "rptPatchEvtCmd"
        ::= { optixTrapsSftmCommon 3 }

    -- 1.3.6.1.4.1.2011.2.25.3.40.8.1.4
    rptPatchEvtBid OBJECT-TYPE
        SYNTAX OCTET STRING (SIZE(0..8))
        MAX-ACCESS accessible-for-notify
        STATUS current
        DESCRIPTION
            "rptPatchEvtBid"
        ::= { optixTrapsSftmCommon 4 }

    -- 1.3.6.1.4.1.2011.2.25.3.40.8.1.5
    rptPatchEvtMsg OBJECT-TYPE
        SYNTAX OCTET STRING (SIZE(0..64))
        MAX-ACCESS accessible-for-notify
        STATUS current
        DESCRIPTION
            "rptPatchEvtMsg"
        ::= { optixTrapsSftmCommon 5 }

    -- 1.3.6.1.4.1.2011.2.25.3.40.8.2
    optixTrapsSftm OBJECT IDENTIFIER ::= { optixGlobalSftmTrap 2 }

    -- 1.3.6.1.4.1.2011.2.25.3.40.8.2.1
    sftmCopyRFileEnd NOTIFICATION-TYPE
        STATUS current
        DESCRIPTION
            "Trap of Sftm: CopyRFile done."
        ::= { optixTrapsSftm 1 }

    -- 1.3.6.1.4.1.2011.2.25.3.40.8.2.2
    sftmRollbackStart NOTIFICATION-TYPE
        STATUS current
        DESCRIPTION
            "Trap of Sftm: Rollback start."
        ::= { optixTrapsSftm 2 }

    -- 1.3.6.1.4.1.2011.2.25.3.40.8.2.3
    sftmRollbackEnd NOTIFICATION-TYPE
        STATUS current
        DESCRIPTION
            "Trap of Sftm: Rollback end."
        ::= { optixTrapsSftm 3 }

    -- 1.3.6.1.4.1.2011.2.25.3.40.8.2.4
    swdlCpymemEnd NOTIFICATION-TYPE
        STATUS current
        DESCRIPTION
            "Trap of Swdl: CopyMem end."
        ::= { optixTrapsSftm 4 }

    -- 1.3.6.1.4.1.2011.2.25.3.40.8.2.5
    swdlActivated NOTIFICATION-TYPE
        STATUS current
        DESCRIPTION
            "Trap of Swdl: Activated."
        ::= { optixTrapsSftm 5 }

    -- 1.3.6.1.4.1.2011.2.25.3.40.8.2.6
    swdlCommitFail NOTIFICATION-TYPE
        STATUS current
        DESCRIPTION
            "Trap of Swdl: Commit fail."
        ::= { optixTrapsSftm 6 }

    -- 1.3.6.1.4.1.2011.2.25.3.40.8.2.7
    swdlCommitEnd NOTIFICATION-TYPE
        STATUS current
        DESCRIPTION
            "Trap of Swdl: Commit end."
        ::= { optixTrapsSftm 7 }

    -- 1.3.6.1.4.1.2011.2.25.3.40.8.2.8
    patchActionResult NOTIFICATION-TYPE
        STATUS current
        DESCRIPTION
            "Trap of Patch: Action result."
        ::= { optixTrapsSftm 8 }

END
