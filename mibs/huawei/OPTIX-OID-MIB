--
-- OPTIX-OID-MIB.mib
-- MIB generated by MG-SOFT Visual MIB Builder Version 3.0 Build 253
-- Wednesday, February 22, 2006 at 18:31:35
--

-- =================================================================
-- Copyright (C) 2006 by HUAWEI TECHNOLOGIES. All rights reserved
-- 
-- Description:
-- Reference:
-- Version: V1.00
-- History:
-- <author>,<date>,<contents>
-- =================================================================
-- 

	OPTIX-OID-MIB DEFINITIONS ::= BEGIN
 
		IMPORTS
			enterprises			
				FROM SNMPv2-SMI;
	
	
--
-- Node definitions
--
	
		-- 1.3.6.1.4.1.2011
		huawei OBJECT IDENTIFIER ::= { enterprises 2011 }
		
		-- 1.3.6.1.4.1.2011.2
		products OBJECT IDENTIFIER ::= { huawei 2 }
		
		-- 1.3.6.1.4.1.2011.2.25
		transmission OBJECT IDENTIFIER ::= { products 25 }
		
		-- 1.3.6.1.4.1.2011.2.25.3
		optixCommon OBJECT IDENTIFIER ::= { transmission 3 }
		
		-- 1.3.6.1.4.1.2011.2.25.3.1
		optixCommonSnmp OBJECT IDENTIFIER ::= { optixCommon 1 }
		
		-- 1.3.6.1.4.1.2011.2.25.3.10
		optixCommonSdh OBJECT IDENTIFIER ::= { optixCommon 10 }
		
		-- 1.3.6.1.4.1.2011.2.25.3.20
		optixCommonSonet OBJECT IDENTIFIER ::= { optixCommon 20 }
		
		-- 1.3.6.1.4.1.2011.2.25.3.40
		optixCommonGlobal OBJECT IDENTIFIER ::= { optixCommon 40 }  
		
		-- 1.3.6.1.4.1.2011.2.25.3.70
		rtn OBJECT IDENTIFIER ::= { optixCommon 70 }	
		
		-- 1.3.6.1.4.1.2011.2.25.3.80
		--mstp OBJECT IDENTIFIER ::= { optixCommon 80 }				
		
		-- 1.3.6.1.4.1.2011.2.25.4
		optixProvision OBJECT IDENTIFIER ::= { transmission 4 }
		
		-- 1.3.6.1.4.1.2011.2.25.4.10
		optixProvisionSdh OBJECT IDENTIFIER ::= { optixProvision 10 }
		
		-- 1.3.6.1.4.1.2011.2.25.4.20
		optixProvisionSonet OBJECT IDENTIFIER ::= { optixProvision 20 }
		
		-- 1.3.6.1.4.1.2011.2.25.4.30
		optixProvisionEqpt OBJECT IDENTIFIER ::= { optixProvision 30 }
		
		-- 1.3.6.1.4.1.2011.2.25.4.40
		optixProvisionRtn OBJECT IDENTIFIER ::= { optixProvision 40 }
		
		-- 1.3.6.1.4.1.2011.2.25.4.50
		optixProvisionPtn OBJECT IDENTIFIER ::= { optixProvision 50 }
		
		-- 1.3.6.1.4.1.2011.2.25.4.70
		optixProvisionWDM OBJECT IDENTIFIER ::= { optixProvision 70 }
		
			
	END

--
-- OPTIX-OID-MIB.mib
--
