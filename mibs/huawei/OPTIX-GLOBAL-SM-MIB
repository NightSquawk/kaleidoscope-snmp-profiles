-- OPTIX-GLOBAL-SM-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-SM-MIB DEFINITIONS ::= BEGIN
    IMPORTS
        optixCommonGlobal
            FROM OPTIX-OID-MIB
        DateAndTime,TEXTUAL-CONVENTION
            FROM SNMPv2-TC
        Unsigned32,MODULE-IDENTITY,OBJECT-TYPE
            FROM SNMPv2-SMI 
        DisplayString, RowStatus
            FROM SNMPv2-TC;
        

    optixGlobalSM MODULE-IDENTITY
        LAST-UPDATED "201607041525Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "Security management module"
        REVISION "201607041525Z"
        DESCRIPTION
            "The initial version"
        ::={ optixCommonGlobal 4 }

    Week ::= TEXTUAL-CONVENTION
        STATUS current
        DESCRIPTION
            "Week"
        SYNTAX INTEGER
        {
            sun(0),
            mon(1),
            tue(2),
            wed(3),
            thu(4),
            fri(5),
            sat(6)
        }

    Date ::= TEXTUAL-CONVENTION
        DISPLAY-HINT "2d-1d-1d"
        STATUS current
        DESCRIPTION
            "Date"
        SYNTAX
            OCTET STRING (SIZE(4))
    Time ::= TEXTUAL-CONVENTION
        DISPLAY-HINT "1d:1d:1d"
        STATUS current
        DESCRIPTION
            "Time"
        SYNTAX
            OCTET STRING (SIZE(3))
    Tei ::= TEXTUAL-CONVENTION
        DISPLAY-HINT "x"
        STATUS current
        DESCRIPTION
            "Tei"
        SYNTAX
            INTEGER
    TeiType ::= TEXTUAL-CONVENTION
        STATUS current
        DESCRIPTION
            "TeiType"
        SYNTAX INTEGER
        {
            unlog(0),
            ems(1),
            lct(2),
            tm(3),
            tl1(4),
            snmp(5),
            web(6),
            lcd(7),
            toolkit(8),
            shell(9),
            ftp(10),
            ssh(11),
            usb(12),
            sdn(13)
        }
      
    -- 1.3.6.1.4.1.2011.2.25.3.40.4.1
    smUserMng OBJECT IDENTIFIER ::= { optixGlobalSM 1 }

    -- 1.3.6.1.4.1.2011.2.25.3.40.4.1.1
    smUserMngTable OBJECT-TYPE
        SYNTAX SEQUENCE OF SmUserMngEntry
        MAX-ACCESS not-accessible
        STATUS current
        DESCRIPTION
            "Indicates the user management table."
        ::= { smUserMng 1 }

    -- 1.3.6.1.4.1.2011.2.25.3.40.4.1.1.1
    smUserMngEntry OBJECT-TYPE
        SYNTAX SmUserMngEntry
        MAX-ACCESS not-accessible
        STATUS current
        DESCRIPTION
            "Indicates the entry node in the user management table."
        INDEX{ smUserName }
        ::= { smUserMngTable 1 }

    SmUserMngEntry ::=
        SEQUENCE {
            smUserName
                OCTET STRING,
            smNewUserName
                OCTET STRING,
            smUserPass
                OCTET STRING,
            smUserGroupName
                OCTET STRING,
            smUserAccountState
                INTEGER,
            smUserCreateTime
                Date,
            smUserExpireTime
                Date,
            smUserLogBeginWeek
                Week,
            smUserLogEndWeek
                Week,
            smUserLogBeginTime
                Time,
            smUserLogEndTime
                Time,
            smUserPassModTime
                DateAndTime,
            smUserAutoQuitTime
                INTEGER,
            smUserAutoQuitRemTime
                INTEGER,
            smUserNoActDisableDays
                INTEGER,
            smUserLastLogTime
                DateAndTime,
            smUserPassModImmediate
                INTEGER,
            smUserExpiredPassUsedCount
                INTEGER,
            smUserPassMaxAge
                INTEGER,
            smUserTei
                Tei,
            smUserTeiType
                TeiType,
            smNewUserStatus
                RowStatus
        }

    -- 1.3.6.1.4.1.2011.2.25.3.40.4.1.1.1.1
    smUserName OBJECT-TYPE
        SYNTAX OCTET STRING (SIZE(0..16))
        MAX-ACCESS not-accessible
        STATUS current
        DESCRIPTION
            "smUserName"
        ::= { smUserMngEntry 1 }

    -- 1.3.6.1.4.1.2011.2.25.3.40.4.1.1.1.2
    smNewUserName OBJECT-TYPE
        SYNTAX OCTET STRING (SIZE(0..16))
        MAX-ACCESS read-create
        STATUS current
        DESCRIPTION
            "smNewUserName"
        ::= { smUserMngEntry 2 }

    -- 1.3.6.1.4.1.2011.2.25.3.40.4.1.1.1.3
    smUserPass OBJECT-TYPE
        SYNTAX OCTET STRING (SIZE(0..16))
        MAX-ACCESS read-create
        STATUS current
        DESCRIPTION
            "smUserPass"
        ::= { smUserMngEntry 3 }

    -- 1.3.6.1.4.1.2011.2.25.3.40.4.1.1.1.4
    smUserGroupName OBJECT-TYPE
        SYNTAX OCTET STRING (SIZE(0..16))
        MAX-ACCESS read-create
        STATUS current
        DESCRIPTION
            "smUserGroupName"
        ::= { smUserMngEntry 4 }

    -- 1.3.6.1.4.1.2011.2.25.3.40.4.1.1.1.5
    smUserAccountState OBJECT-TYPE
        SYNTAX INTEGER
        {
            disable(0),
            enable(1)
        }
        MAX-ACCESS read-create
        STATUS current
        DESCRIPTION
            "smUserAccountState"
        ::= { smUserMngEntry 5 }

    -- 1.3.6.1.4.1.2011.2.25.3.40.4.1.1.1.6
    smUserCreateTime OBJECT-TYPE
        SYNTAX Date
        MAX-ACCESS read-only
        STATUS current
        DESCRIPTION
            "smUserCreateTime"
        ::= { smUserMngEntry 6 }

    -- 1.3.6.1.4.1.2011.2.25.3.40.4.1.1.1.7
    smUserExpireTime OBJECT-TYPE
        SYNTAX Date
        MAX-ACCESS read-only
        STATUS current
        DESCRIPTION
            "smUserExpireTime"
        ::= { smUserMngEntry 7 }

    -- 1.3.6.1.4.1.2011.2.25.3.40.4.1.1.1.8
    smUserLogBeginWeek OBJECT-TYPE
        SYNTAX Week
        MAX-ACCESS read-create
        STATUS current
        DESCRIPTION
            "smUserLogBeginWeek"
        ::= { smUserMngEntry 8 }

    -- 1.3.6.1.4.1.2011.2.25.3.40.4.1.1.1.9
    smUserLogEndWeek OBJECT-TYPE
        SYNTAX Week
        MAX-ACCESS read-create
        STATUS current
        DESCRIPTION
            "smUserLogEndWeek"
        ::= { smUserMngEntry 9 }

    -- 1.3.6.1.4.1.2011.2.25.3.40.4.1.1.1.10
    smUserLogBeginTime OBJECT-TYPE
        SYNTAX Time
        MAX-ACCESS read-create
        STATUS current
        DESCRIPTION
            "smUserLogBeginTime"
        ::= { smUserMngEntry 10 }

    -- 1.3.6.1.4.1.2011.2.25.3.40.4.1.1.1.11
    smUserLogEndTime OBJECT-TYPE
        SYNTAX Time
        MAX-ACCESS read-create
        STATUS current
        DESCRIPTION
            "smUserLogEndTime"
        ::= { smUserMngEntry 11 }

    -- 1.3.6.1.4.1.2011.2.25.3.40.4.1.1.1.12
    smUserPassModTime OBJECT-TYPE
        SYNTAX DateAndTime
        MAX-ACCESS read-only
        STATUS current
        DESCRIPTION
            "smUserPassModTime"
        ::= { smUserMngEntry 12 }

    -- 1.3.6.1.4.1.2011.2.25.3.40.4.1.1.1.13
    smUserAutoQuitTime OBJECT-TYPE
        SYNTAX INTEGER
        MAX-ACCESS read-create
        STATUS current
        DESCRIPTION
            "smUserAutoQuitTime"
        ::= { smUserMngEntry 13 }

    -- 1.3.6.1.4.1.2011.2.25.3.40.4.1.1.1.14
    smUserAutoQuitRemTime OBJECT-TYPE
        SYNTAX INTEGER
        MAX-ACCESS read-only
        STATUS current
        DESCRIPTION
            "smUserAutoQuitRemTime"
        ::= { smUserMngEntry 14 }

    -- 1.3.6.1.4.1.2011.2.25.3.40.4.1.1.1.15
    smUserNoActDisableDays OBJECT-TYPE
        SYNTAX INTEGER
        MAX-ACCESS read-create
        STATUS current
        DESCRIPTION
            "smUserNoActDisableDays"
        ::= { smUserMngEntry 15 }

    -- 1.3.6.1.4.1.2011.2.25.3.40.4.1.1.1.16
    smUserLastLogTime OBJECT-TYPE
        SYNTAX DateAndTime
        MAX-ACCESS read-only
        STATUS current
        DESCRIPTION
            "smUserLastLogTime"
        ::= { smUserMngEntry 16 }

    -- 1.3.6.1.4.1.2011.2.25.3.40.4.1.1.1.17
    smUserPassModImmediate OBJECT-TYPE
        SYNTAX INTEGER
        {
            disable(0),
            enable(1)
        }
        MAX-ACCESS read-create
        STATUS current
        DESCRIPTION
            "smUserPassModImmediate"
        ::= { smUserMngEntry 17 }

    -- 1.3.6.1.4.1.2011.2.25.3.40.4.1.1.1.18
    smUserExpiredPassUsedCount OBJECT-TYPE
        SYNTAX INTEGER
        MAX-ACCESS read-only
        STATUS current
        DESCRIPTION
            "smUserExpiredPassUsedCount"
        ::= { smUserMngEntry 18 }

    -- 1.3.6.1.4.1.2011.2.25.3.40.4.1.1.1.19
    smUserPassMaxAge OBJECT-TYPE
        SYNTAX INTEGER
        MAX-ACCESS read-create
        STATUS current
        DESCRIPTION
            "smUserPassMaxAge"
        ::= { smUserMngEntry 19 }

    -- 1.3.6.1.4.1.2011.2.25.3.40.4.1.1.1.20
    smUserTei OBJECT-TYPE
        SYNTAX Tei
        MAX-ACCESS read-only
        STATUS current
        DESCRIPTION
            "smUserTei"
        ::= { smUserMngEntry 20 }

    -- 1.3.6.1.4.1.2011.2.25.3.40.4.1.1.1.21
    smUserTeiType OBJECT-TYPE
        SYNTAX TeiType
        MAX-ACCESS read-only
        STATUS current
        DESCRIPTION
            "smUserTeiType"
        ::= { smUserMngEntry 21 }

    -- 1.3.6.1.4.1.2011.2.25.3.40.4.1.1.1.255
    smNewUserStatus OBJECT-TYPE
        SYNTAX RowStatus
        MAX-ACCESS read-create
        STATUS current
        DESCRIPTION
            "This object indicates the row status. 1: active 4: createAndGo 6: destroy"
        ::= { smUserMngEntry 255 }

    -- 1.3.6.1.4.1.2011.2.25.3.40.4.1.2
    smCurUserMngTable OBJECT-TYPE
        SYNTAX SEQUENCE OF SmCurUserMngEntry
        MAX-ACCESS not-accessible
        STATUS current
        DESCRIPTION
            "Indicates the current user management table."
        ::= { smUserMng 2 }

    -- 1.3.6.1.4.1.2011.2.25.3.40.4.1.2.1
    smCurUserMngEntry OBJECT-TYPE
        SYNTAX SmCurUserMngEntry
        MAX-ACCESS not-accessible
        STATUS current
        DESCRIPTION
            "Indicates the entry node in the cur user management table."
        INDEX{ smCurUserName }
        ::= { smCurUserMngTable 1 }

    SmCurUserMngEntry ::=
        SEQUENCE {
            smCurUserName
                OCTET STRING,
            smCurUserTeiType
                TeiType
        }

    -- 1.3.6.1.4.1.2011.2.25.3.40.4.1.2.1.2
    smCurUserName OBJECT-TYPE
        SYNTAX OCTET STRING (SIZE(0..16))
        MAX-ACCESS not-accessible
        STATUS current
        DESCRIPTION
            "smCurUserName"
        ::= { smCurUserMngEntry 2 }

    -- 1.3.6.1.4.1.2011.2.25.3.40.4.1.2.1.3
    smCurUserTeiType OBJECT-TYPE
        SYNTAX TeiType
        MAX-ACCESS read-only
        STATUS current
        DESCRIPTION
            "smCurUserTeiType"
        ::= { smCurUserMngEntry 3 }

    -- 1.3.6.1.4.1.2011.2.25.3.40.4.2
    smSecuCfg OBJECT IDENTIFIER ::= { optixGlobalSM 2 }

    -- 1.3.6.1.4.1.2011.2.25.3.40.4.2.1
    smSecuCfgExpPwdCnt OBJECT-TYPE
        SYNTAX INTEGER
        MAX-ACCESS read-only
        STATUS current
        DESCRIPTION
            "smSecuCfgExpPwdCnt"
        ::= { smSecuCfg 1 }

    -- 1.3.6.1.4.1.2011.2.25.3.40.4.2.2
    smSecuCfgPwdAgeMax OBJECT-TYPE
        SYNTAX INTEGER
        MAX-ACCESS read-only
        STATUS current
        DESCRIPTION
            "smSecuCfgPwdAgeMax"
        ::= { smSecuCfg 2 }

    -- 1.3.6.1.4.1.2011.2.25.3.40.4.2.3
    smSecuCfgPwdAgeMin OBJECT-TYPE
        SYNTAX INTEGER
        MAX-ACCESS read-write
        STATUS current
        DESCRIPTION
            "smSecuCfgPwdAgeMin"
        ::= { smSecuCfg 3 }

    -- 1.3.6.1.4.1.2011.2.25.3.40.4.2.4
    smSecuCfgPwdUnique OBJECT-TYPE
        SYNTAX INTEGER
        MAX-ACCESS read-write
        STATUS current
        DESCRIPTION
            "smSecuCfgPwdUnique"
        ::= { smSecuCfg 4 }

    -- 1.3.6.1.4.1.2011.2.25.3.40.4.2.5
    smSecuCfgTrlPeriod OBJECT-TYPE
        SYNTAX INTEGER
        MAX-ACCESS read-only
        STATUS current
        DESCRIPTION
            "smSecuCfgTrlPeriod"
        ::= { smSecuCfg 5 }

    -- 1.3.6.1.4.1.2011.2.25.3.40.4.2.6
    smSecuCfgAttemptCnt OBJECT-TYPE
        SYNTAX INTEGER
        MAX-ACCESS read-write
        STATUS current
        DESCRIPTION
            "smSecuCfgAttemptCnt"
        ::= { smSecuCfg 6 }

    -- 1.3.6.1.4.1.2011.2.25.3.40.4.2.7
    smSecuCfgLockDur OBJECT-TYPE
        SYNTAX Unsigned32
        MAX-ACCESS read-write
        STATUS current
        DESCRIPTION
            "smSecuCfgLockDur"
        ::= { smSecuCfg 7 }

    -- 1.3.6.1.4.1.2011.2.25.3.40.4.5
    smQuerySeculog OBJECT IDENTIFIER ::= { optixGlobalSM 5 }

    -- 1.3.6.1.4.1.2011.2.25.3.40.4.5.1
    smQuerySeculogTable OBJECT-TYPE
        SYNTAX SEQUENCE OF SmQuerySeculogEntry
        MAX-ACCESS not-accessible
        STATUS current
        DESCRIPTION
            "Indicates the secure log table on the NE"
        ::= { smQuerySeculog 1 }

    -- 1.3.6.1.4.1.2011.2.25.3.40.4.5.1.1
    smQuerySeculogEntry OBJECT-TYPE
        SYNTAX SmQuerySeculogEntry
        MAX-ACCESS not-accessible
        STATUS current
        DESCRIPTION
            "Indicates the entry node in the security log table"
        INDEX{ smSeculogLogTime,smSeculogEvtNum }
        ::= { smQuerySeculogTable 1 }

    SmQuerySeculogEntry ::=
        SEQUENCE {
            smSeculogEvtNum
                Unsigned32,
            smSeculogEvtName
                OCTET STRING,
            smSeculogUserName
                OCTET STRING,
            smSeculogLogTime
                DateAndTime,
            smSeculogResName
                OCTET STRING,
            smSeculogTeiType
                OCTET STRING,
            smSeculogIP
                OCTET STRING,
            smSeculogResult
                OCTET STRING
        }

    -- 1.3.6.1.4.1.2011.2.25.3.40.4.5.1.1.1
    smSeculogEvtNum OBJECT-TYPE
        SYNTAX Unsigned32
        MAX-ACCESS not-accessible
        STATUS current
        DESCRIPTION
            "Indicates the event number of the security log"
        ::= { smQuerySeculogEntry 1 }

    -- 1.3.6.1.4.1.2011.2.25.3.40.4.5.1.1.2
    smSeculogEvtName OBJECT-TYPE
        SYNTAX OCTET STRING (SIZE(0..16))
        MAX-ACCESS read-only
        STATUS current
        DESCRIPTION
            "Indicates the event name of the security log"
        ::= { smQuerySeculogEntry 2 }

    -- 1.3.6.1.4.1.2011.2.25.3.40.4.5.1.1.3
    smSeculogUserName OBJECT-TYPE
        SYNTAX OCTET STRING (SIZE(0..16))
        MAX-ACCESS read-only
        STATUS current
        DESCRIPTION
            "Indicates the user name of the security log"
        ::= { smQuerySeculogEntry 3 }

    -- 1.3.6.1.4.1.2011.2.25.3.40.4.5.1.1.4
    smSeculogLogTime OBJECT-TYPE
        SYNTAX DateAndTime
        MAX-ACCESS read-only
        STATUS current
        DESCRIPTION
            "Indicates the record time of the security log"
        ::= { smQuerySeculogEntry 4 }

    -- 1.3.6.1.4.1.2011.2.25.3.40.4.5.1.1.5
    smSeculogResName OBJECT-TYPE
        SYNTAX OCTET STRING (SIZE(0..16))
        MAX-ACCESS read-only
        STATUS current
        DESCRIPTION
            "Indicates the resource name of the security log"
        ::= { smQuerySeculogEntry 5 }

    -- 1.3.6.1.4.1.2011.2.25.3.40.4.5.1.1.6
    smSeculogTeiType OBJECT-TYPE
        SYNTAX OCTET STRING (SIZE(0..6))
        MAX-ACCESS read-only
        STATUS current
        DESCRIPTION
            "Indicates the terminal type of the security log"
        ::= { smQuerySeculogEntry 6 }

    -- 1.3.6.1.4.1.2011.2.25.3.40.4.5.1.1.7
    smSeculogIP OBJECT-TYPE
        SYNTAX OCTET STRING (SIZE(0..16))
        MAX-ACCESS read-only
        STATUS current
        DESCRIPTION
            "Indicates the user IP address of the security log"
        ::= { smQuerySeculogEntry 7 }

    -- 1.3.6.1.4.1.2011.2.25.3.40.4.5.1.1.8
    smSeculogResult OBJECT-TYPE
        SYNTAX OCTET STRING (SIZE(0..1))
        MAX-ACCESS read-only
        STATUS current
        DESCRIPTION
            "Indicates the result of the secure log"
        ::= { smQuerySeculogEntry 8 }

    -- 1.3.6.1.4.1.2011.2.25.3.40.4.6
    smQueryOplog OBJECT IDENTIFIER ::= { optixGlobalSM 6 }

    -- 1.3.6.1.4.1.2011.2.25.3.40.4.6.1
    smQueryOplogTable OBJECT-TYPE
        SYNTAX SEQUENCE OF SmQueryOplogEntry
        MAX-ACCESS not-accessible
        STATUS current
        DESCRIPTION
            "Indicates the operation log table on the NE"
        ::= { smQueryOplog 1 }

    -- 1.3.6.1.4.1.2011.2.25.3.40.4.6.1.1
    smQueryOplogEntry OBJECT-TYPE
        SYNTAX SmQueryOplogEntry
        MAX-ACCESS not-accessible
        STATUS current
        DESCRIPTION
            "Indicates the entry node in the operation log table"
        INDEX{ smOplogOperTime,smOplogSeqNum }
        ::= { smQueryOplogTable 1 }

    SmQueryOplogEntry ::=
        SEQUENCE {
            smOplogSeqNum
                Unsigned32,
            smOplogNMSDescription
                OCTET STRING,
            smOplogNMSMAC
                OCTET STRING,
            smOplogOperTime
                DateAndTime,
            smOplogUserName
                OCTET STRING,
            smOplogCategory
                OCTET STRING,
            smOplogObj
                OCTET STRING,
            smOplogResult
                OCTET STRING,
            smOplogTeiType
                OCTET STRING,
            smOplogTei
                Unsigned32,
            smOplogNMSIP
                OCTET STRING
        }

    -- 1.3.6.1.4.1.2011.2.25.3.40.4.6.1.1.1
    smOplogSeqNum OBJECT-TYPE
        SYNTAX Unsigned32
        MAX-ACCESS not-accessible
        STATUS current
        DESCRIPTION
            "Indicates the sequence number of the operation log"
        ::= { smQueryOplogEntry 1 }

    -- 1.3.6.1.4.1.2011.2.25.3.40.4.6.1.1.2
    smOplogNMSDescription OBJECT-TYPE
        SYNTAX OCTET STRING
        MAX-ACCESS read-only
        STATUS current
        DESCRIPTION
            "Indicates the NMS description of the operation log"
        ::= { smQueryOplogEntry 2 }

    -- 1.3.6.1.4.1.2011.2.25.3.40.4.6.1.1.3
    smOplogNMSMAC OBJECT-TYPE
        SYNTAX OCTET STRING (SIZE(0..17))
        MAX-ACCESS read-only
        STATUS current
        DESCRIPTION
            "Indicates the NMS MAC address of the operation log"
        ::= { smQueryOplogEntry 3 }

    -- 1.3.6.1.4.1.2011.2.25.3.40.4.6.1.1.4
    smOplogOperTime OBJECT-TYPE
        SYNTAX DateAndTime
        MAX-ACCESS read-only
        STATUS current
        DESCRIPTION
            "Indicates the record time of the operation log"
        ::= { smQueryOplogEntry 4 }

    -- 1.3.6.1.4.1.2011.2.25.3.40.4.6.1.1.5
    smOplogUserName OBJECT-TYPE
        SYNTAX OCTET STRING (SIZE(0..16))
        MAX-ACCESS read-only
        STATUS current
        DESCRIPTION
            "Indicates the user name of the operation log"
        ::= { smQueryOplogEntry 5 }

    -- 1.3.6.1.4.1.2011.2.25.3.40.4.6.1.1.6
    smOplogCategory OBJECT-TYPE
        SYNTAX OCTET STRING (SIZE(0..32))
        MAX-ACCESS read-only
        STATUS current
        DESCRIPTION
            "Indicates the category type of the operation log"
        ::= { smQueryOplogEntry 6 }

    -- 1.3.6.1.4.1.2011.2.25.3.40.4.6.1.1.7
    smOplogObj OBJECT-TYPE
        SYNTAX OCTET STRING (SIZE(0..500))
        MAX-ACCESS read-only
        STATUS current
        DESCRIPTION
            "Indicates the object of the operation log"
        ::= { smQueryOplogEntry 7 }

    -- 1.3.6.1.4.1.2011.2.25.3.40.4.6.1.1.8
    smOplogResult OBJECT-TYPE
        SYNTAX OCTET STRING (SIZE(0..7))
        MAX-ACCESS read-only
        STATUS current
        DESCRIPTION
            "Indicates the result of the operation log"
        ::= { smQueryOplogEntry 8 }

    -- 1.3.6.1.4.1.2011.2.25.3.40.4.6.1.1.9
    smOplogTeiType OBJECT-TYPE
        SYNTAX OCTET STRING (SIZE(0..3))
        MAX-ACCESS read-only
        STATUS current
        DESCRIPTION
            "Indicates the terminal type of the operation log"
        ::= { smQueryOplogEntry 9 }

    -- 1.3.6.1.4.1.2011.2.25.3.40.4.6.1.1.10
    smOplogTei OBJECT-TYPE
        SYNTAX Unsigned32
        MAX-ACCESS read-only
        STATUS current
        DESCRIPTION
            "Indicates the TEI of the operation log"
        ::= { smQueryOplogEntry 10 }

    -- 1.3.6.1.4.1.2011.2.25.3.40.4.6.1.1.11
    smOplogNMSIP OBJECT-TYPE
        SYNTAX OCTET STRING (SIZE(0..15))
        MAX-ACCESS read-only
        STATUS current
        DESCRIPTION
            "Indicates the NMS IP address of the operation log"
        ::= { smQueryOplogEntry 11 }

END
