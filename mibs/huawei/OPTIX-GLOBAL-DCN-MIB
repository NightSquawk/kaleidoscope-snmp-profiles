-- OPTIX-GLOBAL-DCN-MIB
-- MIB generated by ExcelToMIB tool 1.0
-- 
-- =================================================================
--  Copyright (C) 2012 by HUAWEI TECHNOLOGIES. All rights reserved
--  Description:
--  Reference:
--  Version: V1.00
--  History:
--  <author>,<date>,<contents>
-- =================================================================
--
OPTIX-GLOBAL-DCN-MIB DEFINITIONS ::= BEGIN
    IMPORTS
        optixCommonGlobal
            FROM OPTIX-OID-MIB
        OBJECT-TYPE,MODULE-IDENTITY,Unsigned32,IpAddress,NOTIFICATION-TYPE
            FROM SNMPv2-SMI
        RowStatus,DateAndTime,DisplayString
            FROM SNMPv2-TC
        ;

    optixGlobalDcn MODULE-IDENTITY
        LAST-UPDATED "201204100940Z"
        ORGANIZATION
            "Huawei Technologies co.,Ltd."
        CONTACT-INFO
            "R&D Building
            Huawei Technologies Co., Ltd.
            Bantian, Longgang District
            Shenzhen, P. R. China
            http://www.huawei.com
            Zip:518129
            E-mail:support@huawei.com"
        DESCRIPTION
            "DCN module"
        REVISION "201204100940Z"
        DESCRIPTION
            "The initial version"
        REVISION "201204100935Z"
        DESCRIPTION
            "The initial version"
        ::={ optixCommonGlobal 2 }

    -- 1.3.6.1.4.1.2011.2.25.3.40.2.1
    optixNeIDManager OBJECT IDENTIFIER ::= { optixGlobalDcn 1 }

    -- 1.3.6.1.4.1.2011.2.25.3.40.2.1.1
    optixNeID OBJECT-TYPE
        SYNTAX Unsigned32
        MAX-ACCESS read-write
        STATUS current
        DESCRIPTION
            "Indicates the NE ID."
        ::= { optixNeIDManager 1 }

    -- 1.3.6.1.4.1.2011.2.25.3.40.2.2
    optixNeIpManager OBJECT IDENTIFIER ::= { optixGlobalDcn 2 }

    -- 1.3.6.1.4.1.2011.2.25.3.40.2.2.1
    optixNeIP OBJECT-TYPE
        SYNTAX IpAddress
        MAX-ACCESS read-write
        STATUS current
        DESCRIPTION
            "Indicates the IP address of an NE."
        ::= { optixNeIpManager 1 }

    -- 1.3.6.1.4.1.2011.2.25.3.40.2.2.2
    optixNeSubMask OBJECT-TYPE
        SYNTAX IpAddress
        MAX-ACCESS read-write
        STATUS current
        DESCRIPTION
            "Indicates the subnet mask of an NE."
        ::= { optixNeIpManager 2 }

    -- 1.3.6.1.4.1.2011.2.25.3.40.2.2.3
    optixNeGateway OBJECT-TYPE
        SYNTAX IpAddress
        MAX-ACCESS read-write
        STATUS current
        DESCRIPTION
            "Indicates the gateway address of an NE."
        ::= { optixNeIpManager 3 }

    -- 1.3.6.1.4.1.2011.2.25.3.40.2.3
    optixOspfAreaManager OBJECT IDENTIFIER ::= { optixGlobalDcn 3 }

    -- 1.3.6.1.4.1.2011.2.25.3.40.2.3.1
    optixOspfArea OBJECT-TYPE
        SYNTAX IpAddress
        MAX-ACCESS read-only
        STATUS current
        DESCRIPTION
            "Indicates the OSPF area ID of an NE."
        ::= { optixOspfAreaManager 1 }

    -- 1.3.6.1.4.1.2011.2.25.3.40.2.4
    optixOspfSwitchManager OBJECT IDENTIFIER ::= { optixGlobalDcn 4 }

    -- 1.3.6.1.4.1.2011.2.25.3.40.2.4.1
    optixOspfSwitch OBJECT-TYPE
        SYNTAX INTEGER
        {
            enable(1),
            disable(0)
        }
        MAX-ACCESS read-only
        STATUS current
        DESCRIPTION
            "Indicates the enable/disable status of the OSPF protocol."
        ::= { optixOspfSwitchManager 1 }

    -- 1.3.6.1.4.1.2011.2.25.3.40.2.5
    optixOspfStubManager OBJECT IDENTIFIER ::= { optixGlobalDcn 5 }

    -- 1.3.6.1.4.1.2011.2.25.3.40.2.5.1
    optixOspfDefaultArea OBJECT-TYPE
        SYNTAX IpAddress
        MAX-ACCESS read-only
        STATUS current
        DESCRIPTION
            "Indicates the default area of an NE."
        ::= { optixOspfStubManager 1 }

    -- 1.3.6.1.4.1.2011.2.25.3.40.2.5.2
    optixOspfStubFlag OBJECT-TYPE
        SYNTAX INTEGER
        {
            enable(1),
            disable(0)
        }
        MAX-ACCESS read-only
        STATUS current
        DESCRIPTION
            "Indicates the enable/disable status of the OSPF stub in the default area of an NE."
        ::= { optixOspfStubManager 2 }

    -- 1.3.6.1.4.1.2011.2.25.3.40.2.6
    optixOspfTimerTable OBJECT-TYPE
        SYNTAX SEQUENCE OF OptixOspfTimerEntry
        MAX-ACCESS not-accessible
        STATUS current
        DESCRIPTION
            "Indicates the OSPF timer table."
        ::= { optixGlobalDcn 6 }

    -- 1.3.6.1.4.1.2011.2.25.3.40.2.6.1
    optixOspfTimerEntry OBJECT-TYPE
        SYNTAX OptixOspfTimerEntry
        MAX-ACCESS not-accessible
        STATUS current
        DESCRIPTION
            "Indicates the entry in the OSPF timer table."
        INDEX{ optixOspfInterface }
        ::= { optixOspfTimerTable 1 }

    OptixOspfTimerEntry ::=
        SEQUENCE {
            optixOspfInterface
                INTEGER,
            optixOspfHellointerval
                Unsigned32,
            optixOspfDeadinterval
                Unsigned32,
            optixOspfRetransmit
                Unsigned32,
            optixOspfTransitDelay
                Unsigned32
        }

    -- 1.3.6.1.4.1.2011.2.25.3.40.2.6.1.1
    optixOspfInterface OBJECT-TYPE
        SYNTAX INTEGER
        {
            lan(1),
            dcc(2)
        }
        MAX-ACCESS read-only
        STATUS current
        DESCRIPTION
            "Indicates the OSPF interface type."
        ::= { optixOspfTimerEntry 1 }

    -- 1.3.6.1.4.1.2011.2.25.3.40.2.6.1.2
    optixOspfHellointerval OBJECT-TYPE
        SYNTAX Unsigned32
        MAX-ACCESS read-only
        STATUS current
        DESCRIPTION
            "Indicates the interval at which Hello packets are sent."
        ::= { optixOspfTimerEntry 2 }

    -- 1.3.6.1.4.1.2011.2.25.3.40.2.6.1.3
    optixOspfDeadinterval OBJECT-TYPE
        SYNTAX Unsigned32
        MAX-ACCESS read-only
        STATUS current
        DESCRIPTION
            "Indicates the OSPF neighbor dead time."
        ::= { optixOspfTimerEntry 3 }

    -- 1.3.6.1.4.1.2011.2.25.3.40.2.6.1.4
    optixOspfRetransmit OBJECT-TYPE
        SYNTAX Unsigned32
        MAX-ACCESS read-only
        STATUS current
        DESCRIPTION
            "Indicates the interval of retransmitting LSAs."
        ::= { optixOspfTimerEntry 4 }

    -- 1.3.6.1.4.1.2011.2.25.3.40.2.6.1.5
    optixOspfTransitDelay OBJECT-TYPE
        SYNTAX Unsigned32
        MAX-ACCESS read-only
        STATUS current
        DESCRIPTION
            "Indicates the delay of trasmitting LSAs."
        ::= { optixOspfTimerEntry 5 }

    -- 1.3.6.1.4.1.2011.2.25.3.40.2.7
    optixAclManager OBJECT IDENTIFIER ::= { optixGlobalDcn 7 }

    -- 1.3.6.1.4.1.2011.2.25.3.40.2.7.1
    optixBasicAclRuleTable OBJECT-TYPE
        SYNTAX SEQUENCE OF OptixBasicAclRuleEntry
        MAX-ACCESS not-accessible
        STATUS current
        DESCRIPTION
            "Indicates the basic ACL rule table."
        ::= { optixAclManager 1 }

    -- 1.3.6.1.4.1.2011.2.25.3.40.2.7.1.1
    optixBasicAclRuleEntry OBJECT-TYPE
        SYNTAX OptixBasicAclRuleEntry
        MAX-ACCESS not-accessible
        STATUS current
        DESCRIPTION
            "Indicates the entry in the basic ACL rule table."
        INDEX{ optixAclRuleID }
        ::= { optixBasicAclRuleTable 1 }

    OptixBasicAclRuleEntry ::=
        SEQUENCE {
            optixAclRuleID
                Unsigned32,
            optixAclRuleOptype
                INTEGER,
            optixAclRuleSrcIp
                IpAddress,
            optixAclRuleWildcard
                IpAddress
        }

    -- 1.3.6.1.4.1.2011.2.25.3.40.2.7.1.1.1
    optixAclRuleID OBJECT-TYPE
        SYNTAX Unsigned32
        MAX-ACCESS read-only
        STATUS current
        DESCRIPTION
            "Indicates the basic ACL rule ID."
        ::= { optixBasicAclRuleEntry 1 }

    -- 1.3.6.1.4.1.2011.2.25.3.40.2.7.1.1.2
    optixAclRuleOptype OBJECT-TYPE
        SYNTAX INTEGER
        {
            deny(0),
            permit(1)
        }
        MAX-ACCESS read-only
        STATUS current
        DESCRIPTION
            "Indicates the adaptable operation type of a basic ACL rule."
        ::= { optixBasicAclRuleEntry 2 }

    -- 1.3.6.1.4.1.2011.2.25.3.40.2.7.1.1.3
    optixAclRuleSrcIp OBJECT-TYPE
        SYNTAX IpAddress
        MAX-ACCESS read-only
        STATUS current
        DESCRIPTION
            "Indicates the adaptable source IP address of a basic ACL rule."
        ::= { optixBasicAclRuleEntry 3 }

    -- 1.3.6.1.4.1.2011.2.25.3.40.2.7.1.1.4
    optixAclRuleWildcard OBJECT-TYPE
        SYNTAX IpAddress
        MAX-ACCESS read-only
        STATUS current
        DESCRIPTION
            "Indicates the adaptable source IP address wildcard of a basic ACL rule."
        ::= { optixBasicAclRuleEntry 4 }

    -- 1.3.6.1.4.1.2011.2.25.3.40.2.7.2
    optixAdvAclRuleTable OBJECT-TYPE
        SYNTAX SEQUENCE OF OptixAdvAclRuleEntry
        MAX-ACCESS not-accessible
        STATUS current
        DESCRIPTION
            "Indicates the advanced ACL rule table."
        ::= { optixAclManager 2 }

    -- 1.3.6.1.4.1.2011.2.25.3.40.2.7.2.1
    optixAdvAclRuleEntry OBJECT-TYPE
        SYNTAX OptixAdvAclRuleEntry
        MAX-ACCESS not-accessible
        STATUS current
        DESCRIPTION
            "Indicates the entry in the advanced ACL rule table."
        INDEX{ optixAdvAclRuleID }
        ::= { optixAdvAclRuleTable 1 }

    OptixAdvAclRuleEntry ::=
        SEQUENCE {
            optixAdvAclRuleID
                Unsigned32,
            optixAdvAclRuleOpType
                INTEGER,
            optixAdvAclRuleSrcIp
                IpAddress,
            optixAdvAclRuleSrcWildCard
                IpAddress,
            optixAdvAclRuleDstIP
                IpAddress,
            optixAdvAclRuleDstWildCard
                IpAddress,
            optixAdvAclRuleProType
                INTEGER,
            optixAdvAclRuleSrcPort
                Unsigned32,
            optixAdvAclRuleDstPort
                Unsigned32,
            optixAdvAclRuleIcmpType
                Unsigned32,
            optixAdvAclRuleIcmpCode
                Unsigned32
        }

    -- 1.3.6.1.4.1.2011.2.25.3.40.2.7.2.1.1
    optixAdvAclRuleID OBJECT-TYPE
        SYNTAX Unsigned32
        MAX-ACCESS read-only
        STATUS current
        DESCRIPTION
            "Indicates the advanced ACL rule ID."
        ::= { optixAdvAclRuleEntry 1 }

    -- 1.3.6.1.4.1.2011.2.25.3.40.2.7.2.1.2
    optixAdvAclRuleOpType OBJECT-TYPE
        SYNTAX INTEGER
        {
            deny(0),
            permit(1)
        }
        MAX-ACCESS read-only
        STATUS current
        DESCRIPTION
            "Indicates the adaptable operation type of an advanced ACL rule."
        ::= { optixAdvAclRuleEntry 2 }

    -- 1.3.6.1.4.1.2011.2.25.3.40.2.7.2.1.3
    optixAdvAclRuleSrcIp OBJECT-TYPE
        SYNTAX IpAddress
        MAX-ACCESS read-only
        STATUS current
        DESCRIPTION
            "Indicates the adaptable source IP address of an advanced ACL rule."
        ::= { optixAdvAclRuleEntry 3 }

    -- 1.3.6.1.4.1.2011.2.25.3.40.2.7.2.1.4
    optixAdvAclRuleSrcWildCard OBJECT-TYPE
        SYNTAX IpAddress
        MAX-ACCESS read-only
        STATUS current
        DESCRIPTION
            "Indicates the adaptable source IP address wildcard of an advanced ACL rule."
        ::= { optixAdvAclRuleEntry 4 }

    -- 1.3.6.1.4.1.2011.2.25.3.40.2.7.2.1.5
    optixAdvAclRuleDstIP OBJECT-TYPE
        SYNTAX IpAddress
        MAX-ACCESS read-only
        STATUS current
        DESCRIPTION
            "Indicates the adaptable destination IP address of an advanced ACL rule."
        ::= { optixAdvAclRuleEntry 5 }

    -- 1.3.6.1.4.1.2011.2.25.3.40.2.7.2.1.6
    optixAdvAclRuleDstWildCard OBJECT-TYPE
        SYNTAX IpAddress
        MAX-ACCESS read-only
        STATUS current
        DESCRIPTION
            "Indicates the adaptable destination IP address wildcard of an advanced ACL rule."
        ::= { optixAdvAclRuleEntry 6 }

    -- 1.3.6.1.4.1.2011.2.25.3.40.2.7.2.1.7
    optixAdvAclRuleProType OBJECT-TYPE
        SYNTAX INTEGER
        {
            ip(0),
            icmp(1),
            tcp(6),
            udp(17)
        }
        MAX-ACCESS read-only
        STATUS current
        DESCRIPTION
            "Indicates the adaptable protocol type of an advanced ACL rule."
        ::= { optixAdvAclRuleEntry 7 }

    -- 1.3.6.1.4.1.2011.2.25.3.40.2.7.2.1.8
    optixAdvAclRuleSrcPort OBJECT-TYPE
        SYNTAX Unsigned32
        MAX-ACCESS read-only
        STATUS current
        DESCRIPTION
            "Indicates the adaptable source port of an advanced ACL rule."
        ::= { optixAdvAclRuleEntry 8 }

    -- 1.3.6.1.4.1.2011.2.25.3.40.2.7.2.1.9
    optixAdvAclRuleDstPort OBJECT-TYPE
        SYNTAX Unsigned32
        MAX-ACCESS read-only
        STATUS current
        DESCRIPTION
            "Indicates the adaptable destination port of an advanced ACL rule."
        ::= { optixAdvAclRuleEntry 9 }

    -- 1.3.6.1.4.1.2011.2.25.3.40.2.7.2.1.10
    optixAdvAclRuleIcmpType OBJECT-TYPE
        SYNTAX Unsigned32
        MAX-ACCESS read-only
        STATUS current
        DESCRIPTION
            "Indicates the ICMP packet type to which an advanced ACL rule is adaptable."
        ::= { optixAdvAclRuleEntry 10 }

    -- 1.3.6.1.4.1.2011.2.25.3.40.2.7.2.1.11
    optixAdvAclRuleIcmpCode OBJECT-TYPE
        SYNTAX Unsigned32
        MAX-ACCESS read-only
        STATUS current
        DESCRIPTION
            "Indicates the ICMP data packet type to which an advanced ACL rule is adaptable."
        ::= { optixAdvAclRuleEntry 11 }

    -- 1.3.6.1.4.1.2011.2.25.3.40.2.8
    optixPortServiceManager OBJECT IDENTIFIER ::= { optixGlobalDcn 8 }

    -- 1.3.6.1.4.1.2011.2.25.3.40.2.8.1
    optixIPPortManagerTable OBJECT-TYPE
        SYNTAX SEQUENCE OF OptixIPPortManagerEntry
        MAX-ACCESS not-accessible
        STATUS current
        DESCRIPTION
            "Indicates the IP PORT INFO table."
        ::= { optixPortServiceManager 1 }

    -- 1.3.6.1.4.1.2011.2.25.3.40.2.8.1.1
    optixIPPortManagerEntry OBJECT-TYPE
        SYNTAX OptixIPPortManagerEntry
        MAX-ACCESS not-accessible
        STATUS current
        DESCRIPTION
            "Indicates the entry in the ip port table."
        INDEX{ optixIPPortID,optixIPPortProtocol }
        ::= { optixIPPortManagerTable 1 }

    OptixIPPortManagerEntry ::=
        SEQUENCE {
            optixIPPortID
                Unsigned32,
            optixIPPortProtocol
                INTEGER,
            optixIPPortStaus
                Unsigned32,
            optixIPPortTaskName
                OCTET STRING
        }

    -- 1.3.6.1.4.1.2011.2.25.3.40.2.8.1.1.1
    optixIPPortID OBJECT-TYPE
        SYNTAX Unsigned32
        MAX-ACCESS not-accessible
        STATUS current
        DESCRIPTION
            "Indicates the IP PORT id."
        ::= { optixIPPortManagerEntry 1 }

    -- 1.3.6.1.4.1.2011.2.25.3.40.2.8.1.1.2
    optixIPPortProtocol OBJECT-TYPE
        SYNTAX INTEGER
        {
            tcp(6),
            udp(17)
        }
        MAX-ACCESS not-accessible
        STATUS current
        DESCRIPTION
            "Indicates the protocol type of the port."
        ::= { optixIPPortManagerEntry 2 }

    -- 1.3.6.1.4.1.2011.2.25.3.40.2.8.1.1.3
    optixIPPortStaus OBJECT-TYPE
        SYNTAX Unsigned32
        MAX-ACCESS read-only
        STATUS current
        DESCRIPTION
            "Indicates status of the PORT."
        ::= { optixIPPortManagerEntry 3 }

    -- 1.3.6.1.4.1.2011.2.25.3.40.2.8.1.1.4
    optixIPPortTaskName OBJECT-TYPE
        SYNTAX OCTET STRING
        MAX-ACCESS read-only
        STATUS current
        DESCRIPTION
            "Indicates the name of the task that creates the port."
        ::= { optixIPPortManagerEntry 4 }

    -- 1.3.6.1.4.1.2011.2.25.3.40.2.8.2
    optixServiceTable OBJECT-TYPE
        SYNTAX SEQUENCE OF OptixServiceEntry
        MAX-ACCESS not-accessible
        STATUS current
        DESCRIPTION
            "Indicates the service type supported by an NE."
        ::= { optixPortServiceManager 2 }

    -- 1.3.6.1.4.1.2011.2.25.3.40.2.8.2.1
    optixServiceEntry OBJECT-TYPE
        SYNTAX OptixServiceEntry
        MAX-ACCESS not-accessible
        STATUS current
        DESCRIPTION
            "IndiIndicates the service type supported by an NE."
        INDEX{ optixServiceName }
        ::= { optixServiceTable 1 }

    OptixServiceEntry ::=
        SEQUENCE {
            optixServiceName
                INTEGER,
            optixServiceState
                INTEGER
        }

    -- 1.3.6.1.4.1.2011.2.25.3.40.2.8.2.1.1
    optixServiceName OBJECT-TYPE
        SYNTAX INTEGER
        {
            ftpclient(1),
            sftpclient(2),
            telserver(3),
            stelserver(4),
            rawtelserver(5),
            rawtl1(6),
            multinetsearch(7),
            omunisearch(8),
            ctrlunisearch(9),
            ipgne(10),
            tl1gneservice(11)
        }
        MAX-ACCESS not-accessible
        STATUS current
        DESCRIPTION
            "Indicates the service name"
        ::= { optixServiceEntry 1 }

    -- 1.3.6.1.4.1.2011.2.25.3.40.2.8.2.1.2
    optixServiceState OBJECT-TYPE
        SYNTAX INTEGER
        {
            open(1),
            close(0)
        }
        MAX-ACCESS read-write
        STATUS current
        DESCRIPTION
            "Indicates the service state"
        ::= { optixServiceEntry 2 }

    -- 1.3.6.1.4.1.2011.2.25.3.40.2.9
    optixARPManager OBJECT IDENTIFIER ::= { optixGlobalDcn 9 }

    -- 1.3.6.1.4.1.2011.2.25.3.40.2.9.1
    optixARPManagerTable OBJECT-TYPE
        SYNTAX SEQUENCE OF OptixARPManagerEntry
        MAX-ACCESS not-accessible
        STATUS current
        DESCRIPTION
            "Indicates the proxy ARP status information of an NE Ethernet port."
        ::= { optixARPManager 1 }

    -- 1.3.6.1.4.1.2011.2.25.3.40.2.9.1.1
    optixARPManagerEntry OBJECT-TYPE
        SYNTAX OptixARPManagerEntry
        MAX-ACCESS not-accessible
        STATUS current
        DESCRIPTION
            "Indicates the eth proxy arp table."
        INDEX{ optixARPNO }
        ::= { optixARPManagerTable 1 }

    OptixARPManagerEntry ::=
        SEQUENCE {
            optixARPNO
                Unsigned32,
            optixARPNOStatus
                INTEGER
        }

    -- 1.3.6.1.4.1.2011.2.25.3.40.2.9.1.1.1
    optixARPNO OBJECT-TYPE
        SYNTAX Unsigned32
        MAX-ACCESS not-accessible
        STATUS current
        DESCRIPTION
            "Indicates the number of the Ethernet proxy ARP."
        ::= { optixARPManagerEntry 1 }

    -- 1.3.6.1.4.1.2011.2.25.3.40.2.9.1.1.2
    optixARPNOStatus OBJECT-TYPE
        SYNTAX INTEGER
        {
            enable(1),
            disable(0)
        }
        MAX-ACCESS read-write
        STATUS current
        DESCRIPTION
            "Indicates the state of the Ethernet proxy ARP."
        ::= { optixARPManagerEntry 2 }

    -- 1.3.6.1.4.1.2011.2.25.3.40.2.10
    optixRouteGlobalManager OBJECT IDENTIFIER ::= { optixGlobalDcn 10 }

    -- 1.3.6.1.4.1.2011.2.25.3.40.2.10.1
    optixOspfGlobalTable OBJECT-TYPE
        SYNTAX SEQUENCE OF OptixOspfGlobalEntry
        MAX-ACCESS not-accessible
        STATUS current
        DESCRIPTION
            "Indicates the static route information table."
        ::= { optixRouteGlobalManager 1 }

    -- 1.3.6.1.4.1.2011.2.25.3.40.2.10.1.1
    optixOspfGlobalEntry OBJECT-TYPE
        SYNTAX OptixOspfGlobalEntry
        MAX-ACCESS not-accessible
        STATUS current
        DESCRIPTION
            "Indicates the static route item."
        INDEX{ optixLanDestIP,optixLanSubMask,optixLanGateWay,optixLanOutBD,optixLanOutPT }
        ::= { optixOspfGlobalTable 1 }

    OptixOspfGlobalEntry ::=
        SEQUENCE {
            optixLanDestIP
                IpAddress,
            optixLanSubMask
                IpAddress,
            optixLanGateWay
                IpAddress,
            optixLanOutBD
                Unsigned32,
            optixLanOutPT
                Unsigned32,
            optixLanPpFlag
                INTEGER,
            optixLanDestRowStatus
                RowStatus
        }

    -- 1.3.6.1.4.1.2011.2.25.3.40.2.10.1.1.1
    optixLanDestIP OBJECT-TYPE
        SYNTAX IpAddress
        MAX-ACCESS not-accessible
        STATUS current
        DESCRIPTION
            "Indicates the destination IP address of the static route."
        ::= { optixOspfGlobalEntry 1 }

    -- 1.3.6.1.4.1.2011.2.25.3.40.2.10.1.1.2
    optixLanSubMask OBJECT-TYPE
        SYNTAX IpAddress
        MAX-ACCESS not-accessible
        STATUS current
        DESCRIPTION
            "Indicates the submask of the static route IP address."
        ::= { optixOspfGlobalEntry 2 }

    -- 1.3.6.1.4.1.2011.2.25.3.40.2.10.1.1.3
    optixLanGateWay OBJECT-TYPE
        SYNTAX IpAddress
        MAX-ACCESS not-accessible
        STATUS current
        DESCRIPTION
            "Indicates the destination gateway IP address of the static route."
        ::= { optixOspfGlobalEntry 3 }

    -- 1.3.6.1.4.1.2011.2.25.3.40.2.10.1.1.4
    optixLanOutBD OBJECT-TYPE
        SYNTAX Unsigned32
        MAX-ACCESS not-accessible
        STATUS current
        DESCRIPTION
            "Indicates the out board of the static route."
        ::= { optixOspfGlobalEntry 4 }

    -- 1.3.6.1.4.1.2011.2.25.3.40.2.10.1.1.5
    optixLanOutPT OBJECT-TYPE
        SYNTAX Unsigned32
        MAX-ACCESS not-accessible
        STATUS current
        DESCRIPTION
            "Indicates the out port of the static route."
        ::= { optixOspfGlobalEntry 5 }

    -- 1.3.6.1.4.1.2011.2.25.3.40.2.10.1.1.6
    optixLanPpFlag OBJECT-TYPE
        SYNTAX INTEGER
        {
            lanRoute(0),
            ppRoute(1)
        }
        MAX-ACCESS read-create
        STATUS current
        DESCRIPTION
            "Indicates the choice of the lanRoute or PpRoute"
        ::= { optixOspfGlobalEntry 6 }

    -- 1.3.6.1.4.1.2011.2.25.3.40.2.10.1.1.255
    optixLanDestRowStatus OBJECT-TYPE
        SYNTAX RowStatus
        MAX-ACCESS read-create
        STATUS current
        DESCRIPTION
            "This object indicates the row status. 1: active 4: createAndGo 6: destroy"
        ::= { optixOspfGlobalEntry 255 }

    -- 1.3.6.1.4.1.2011.2.25.3.40.2.10.2
    optixOspfGlobalDelTable OBJECT-TYPE
        SYNTAX SEQUENCE OF OptixOspfGlobalDelEntry
        MAX-ACCESS not-accessible
        STATUS current
        DESCRIPTION
            "Indicates deleting the information of lanroute."
        ::= { optixRouteGlobalManager 2 }

    -- 1.3.6.1.4.1.2011.2.25.3.40.2.10.2.1
    optixOspfGlobalDelEntry OBJECT-TYPE
        SYNTAX OptixOspfGlobalDelEntry
        MAX-ACCESS not-accessible
        STATUS current
        DESCRIPTION
            "Indicates the static route item."
        INDEX{ optixLanDestIP }
        ::= { optixOspfGlobalDelTable 1 }

    OptixOspfGlobalDelEntry ::=
        SEQUENCE {
            optixLanDestDelRowStatus
                RowStatus
        }

    -- 1.3.6.1.4.1.2011.2.25.3.40.2.10.2.1.255
    optixLanDestDelRowStatus OBJECT-TYPE
        SYNTAX RowStatus
        MAX-ACCESS read-create
        STATUS current
        DESCRIPTION
            "This object indicates the row status.  1: active 6: destroy"
        ::= { optixOspfGlobalDelEntry 255 }

    -- 1.3.6.1.4.1.2011.2.25.3.40.2.10.3
    optixOspfRouteTable OBJECT-TYPE
        SYNTAX SEQUENCE OF OptixOspfRouteEntry
        MAX-ACCESS not-accessible
        STATUS current
        DESCRIPTION
            "Indicates the route info of ne."
        ::= { optixRouteGlobalManager 3 }

    -- 1.3.6.1.4.1.2011.2.25.3.40.2.10.3.1
    optixOspfRouteEntry OBJECT-TYPE
        SYNTAX OptixOspfRouteEntry
        MAX-ACCESS not-accessible
        STATUS current
        DESCRIPTION
            "Indicates the item of the route table."
        INDEX{ optixRouteDestIP,optixRouteMask,optixRouteNextHop,optixRouteInterface,optixRouteProtocol,optixRouteMetric }
        ::= { optixOspfRouteTable 1 }

    OptixOspfRouteEntry ::=
        SEQUENCE {
            optixRouteDestIP
                IpAddress,
            optixRouteMask
                IpAddress,
            optixRouteNextHop
                IpAddress,
            optixRouteInterface
                OCTET STRING,
            optixRouteProtocol
                INTEGER,
            optixRouteMetric
                Unsigned32,
            optixRouteInfo
                OCTET STRING
        }

    -- 1.3.6.1.4.1.2011.2.25.3.40.2.10.3.1.1
    optixRouteDestIP OBJECT-TYPE
        SYNTAX IpAddress
        MAX-ACCESS not-accessible
        STATUS current
        DESCRIPTION
            "Indicates the destination IP address of the route."
        ::= { optixOspfRouteEntry 1 }

    -- 1.3.6.1.4.1.2011.2.25.3.40.2.10.3.1.2
    optixRouteMask OBJECT-TYPE
        SYNTAX IpAddress
        MAX-ACCESS not-accessible
        STATUS current
        DESCRIPTION
            "Indicates the submask of the route IP address."
        ::= { optixOspfRouteEntry 2 }

    -- 1.3.6.1.4.1.2011.2.25.3.40.2.10.3.1.3
    optixRouteNextHop OBJECT-TYPE
        SYNTAX IpAddress
        MAX-ACCESS not-accessible
        STATUS current
        DESCRIPTION
            "Indicates the next hop of route IP address."
        ::= { optixOspfRouteEntry 3 }

    -- 1.3.6.1.4.1.2011.2.25.3.40.2.10.3.1.4
    optixRouteInterface OBJECT-TYPE
        SYNTAX OCTET STRING
        MAX-ACCESS not-accessible
        STATUS current
        DESCRIPTION
            "Indicates the name of the interface which creates the route."
        ::= { optixOspfRouteEntry 4 }

    -- 1.3.6.1.4.1.2011.2.25.3.40.2.10.3.1.5
    optixRouteProtocol OBJECT-TYPE
        SYNTAX INTEGER
        {
            direct(1),
            static(2),
            ospf(6),
            default(17),
            rip(4)
        }
        MAX-ACCESS not-accessible
        STATUS current
        DESCRIPTION
            "Indicates the cause why the route is created."
        ::= { optixOspfRouteEntry 5 }

    -- 1.3.6.1.4.1.2011.2.25.3.40.2.10.3.1.6
    optixRouteMetric OBJECT-TYPE
        SYNTAX Unsigned32
        MAX-ACCESS not-accessible
        STATUS current
        DESCRIPTION
            "Indicates the metirc of the route."
        ::= { optixOspfRouteEntry 6 }

    -- 1.3.6.1.4.1.2011.2.25.3.40.2.10.3.1.7
    optixRouteInfo OBJECT-TYPE
        SYNTAX OCTET STRING
        MAX-ACCESS read-only
        STATUS current
        DESCRIPTION
            "Indicates the destination IP address of the route."
        ::= { optixOspfRouteEntry 7 }

    -- 1.3.6.1.4.1.2011.2.25.3.40.2.10.4
    optixRoutePingTable OBJECT-TYPE
        SYNTAX SEQUENCE OF OptixRoutePingEntry
        MAX-ACCESS not-accessible
        STATUS current
        DESCRIPTION
            "Indicates the table of the operation of ping."
        ::= { optixRouteGlobalManager 4 }

    -- 1.3.6.1.4.1.2011.2.25.3.40.2.10.4.1
    optixRoutePingEntry OBJECT-TYPE
        SYNTAX OptixRoutePingEntry
        MAX-ACCESS not-accessible
        STATUS current
        DESCRIPTION
            "Indicates the item of the ping table"
        INDEX{ optixRoutePingIP,optixPingPacktSize,optixPingPacktNum,optixPingPacktInterval,optixPingPacktTimeOut }
        ::= { optixRoutePingTable 1 }

    OptixRoutePingEntry ::=
        SEQUENCE {
            optixRoutePingIP
                IpAddress,
            optixPingPacktSize
                Unsigned32,
            optixPingPacktNum
                Unsigned32,
            optixPingPacktInterval
                Unsigned32,
            optixPingPacktTimeOut
                Unsigned32,
            optixPingResult
                OCTET STRING
        }

    -- 1.3.6.1.4.1.2011.2.25.3.40.2.10.4.1.1
    optixRoutePingIP OBJECT-TYPE
        SYNTAX IpAddress
        MAX-ACCESS not-accessible
        STATUS current
        DESCRIPTION
            "Destination IP address for ping."
        ::= { optixRoutePingEntry 1 }

    -- 1.3.6.1.4.1.2011.2.25.3.40.2.10.4.1.2
    optixPingPacktSize OBJECT-TYPE
        SYNTAX Unsigned32
        MAX-ACCESS not-accessible
        STATUS current
        DESCRIPTION
            "Indicates the size of a ping packet."
        ::= { optixRoutePingEntry 2 }

    -- 1.3.6.1.4.1.2011.2.25.3.40.2.10.4.1.3
    optixPingPacktNum OBJECT-TYPE
        SYNTAX Unsigned32
        MAX-ACCESS not-accessible
        STATUS current
        DESCRIPTION
            "Indicates the number of ping packets."
        ::= { optixRoutePingEntry 3 }

    -- 1.3.6.1.4.1.2011.2.25.3.40.2.10.4.1.4
    optixPingPacktInterval OBJECT-TYPE
        SYNTAX Unsigned32
        MAX-ACCESS not-accessible
        STATUS current
        DESCRIPTION
            "Indicates the packet sending interval."
        ::= { optixRoutePingEntry 4 }

    -- 1.3.6.1.4.1.2011.2.25.3.40.2.10.4.1.5
    optixPingPacktTimeOut OBJECT-TYPE
        SYNTAX Unsigned32
        MAX-ACCESS not-accessible
        STATUS current
        DESCRIPTION
            "Indicates the timeout of a Replay packet."
        ::= { optixRoutePingEntry 5 }

    -- 1.3.6.1.4.1.2011.2.25.3.40.2.10.4.1.6
    optixPingResult OBJECT-TYPE
        SYNTAX OCTET STRING
        MAX-ACCESS read-only
        STATUS current
        DESCRIPTION
            "Indicates the operation result."
        ::= { optixRoutePingEntry 6 }

    -- 1.3.6.1.4.1.2011.2.25.3.40.2.10.5
    optixRouteTracertTable OBJECT-TYPE
        SYNTAX SEQUENCE OF OptixRouteTracertEntry
        MAX-ACCESS not-accessible
        STATUS current
        DESCRIPTION
            "Indicates the eth proxy arp table."
        ::= { optixRouteGlobalManager 5 }

    -- 1.3.6.1.4.1.2011.2.25.3.40.2.10.5.1
    optixRouteTracertEntry OBJECT-TYPE
        SYNTAX OptixRouteTracertEntry
        MAX-ACCESS not-accessible
        STATUS current
        DESCRIPTION
            "Indicates the item of the operation of the tracert."
        INDEX{ optixRouteTracertIP,optixRouteTracertTTL }
        ::= { optixRouteTracertTable 1 }

    OptixRouteTracertEntry ::=
        SEQUENCE {
            optixRouteTracertIP
                IpAddress,
            optixRouteTracertTTL
                Unsigned32,
            optixRouteTracertResult
                OCTET STRING
        }

    -- 1.3.6.1.4.1.2011.2.25.3.40.2.10.5.1.1
    optixRouteTracertIP OBJECT-TYPE
        SYNTAX IpAddress
        MAX-ACCESS not-accessible
        STATUS current
        DESCRIPTION
            "Indicates the destination IP address."
        ::= { optixRouteTracertEntry 1 }

    -- 1.3.6.1.4.1.2011.2.25.3.40.2.10.5.1.2
    optixRouteTracertTTL OBJECT-TYPE
        SYNTAX Unsigned32
        MAX-ACCESS not-accessible
        STATUS current
        DESCRIPTION
            "The TTL of the tracert"
        ::= { optixRouteTracertEntry 2 }

    -- 1.3.6.1.4.1.2011.2.25.3.40.2.10.5.1.3
    optixRouteTracertResult OBJECT-TYPE
        SYNTAX OCTET STRING
        MAX-ACCESS read-only
        STATUS current
        DESCRIPTION
            "The Result of the tracert operation."
        ::= { optixRouteTracertEntry 3 }

    -- 1.3.6.1.4.1.2011.2.25.3.40.2.10.6
    optixTrapsRoutePingCommon OBJECT IDENTIFIER ::= { optixRouteGlobalManager 6 }

    -- 1.3.6.1.4.1.2011.2.25.3.40.2.10.6.1
    rptEvtPingIP OBJECT-TYPE
        SYNTAX IpAddress
        MAX-ACCESS accessible-for-notify
        STATUS current
        DESCRIPTION
            "Indicates the destionation IP address of Ping."
        ::= { optixTrapsRoutePingCommon 1 }

    -- 1.3.6.1.4.1.2011.2.25.3.40.2.10.6.2
    rptEvtPingResult OBJECT-TYPE
        SYNTAX DisplayString
        MAX-ACCESS accessible-for-notify
        STATUS current
        DESCRIPTION
            "Indicates the result of Ping."
        ::= { optixTrapsRoutePingCommon 2 }

    -- 1.3.6.1.4.1.2011.2.25.3.40.2.10.7
    optixTrapsRoutePing OBJECT IDENTIFIER ::= { optixRouteGlobalManager 7 }

    -- 1.3.6.1.4.1.2011.2.25.3.40.2.10.7.1
    routePing NOTIFICATION-TYPE
        OBJECTS{ rptEvtPingIP,rptEvtPingResult }
        STATUS current
        DESCRIPTION
            "Trap of route: Ping."
        ::= { optixTrapsRoutePing 1 }

    -- 1.3.6.1.4.1.2011.2.25.3.40.2.10.7.2
    routeTracert NOTIFICATION-TYPE
        OBJECTS{ rptEvtPingIP,rptEvtPingResult }
        STATUS current
        DESCRIPTION
            "Trap of route: Tracert."
        ::= { optixTrapsRoutePing 2 }

    -- 1.3.6.1.4.1.2011.2.25.3.40.2.11
    optixRouteGroupManager OBJECT IDENTIFIER ::= { optixGlobalDcn 11 }

    -- 1.3.6.1.4.1.2011.2.25.3.40.2.11.1
    optixPingStop OBJECT-TYPE
        SYNTAX INTEGER
        {
            stop(0)
        }
        MAX-ACCESS read-write
        STATUS current
        DESCRIPTION
            "The action of stopping."
        ::= { optixRouteGroupManager 1 }

    -- 1.3.6.1.4.1.2011.2.25.3.40.2.11.2
    optixTracertStop OBJECT-TYPE
        SYNTAX INTEGER
        {
            stop(0)
        }
        MAX-ACCESS read-write
        STATUS current
        DESCRIPTION
            "The action of stopping."
        ::= { optixRouteGroupManager 2 }

    -- 1.3.6.1.4.1.2011.2.25.3.40.2.14
    optixOspfConfManager OBJECT IDENTIFIER ::= { optixGlobalDcn 14 }

    -- 1.3.6.1.4.1.2011.2.25.3.40.2.14.1
    optixInterfaceTable OBJECT-TYPE
        SYNTAX SEQUENCE OF OptixInterfaceEntry
        MAX-ACCESS not-accessible
        STATUS current
        DESCRIPTION
            "Indicates the IP address of an OSPF interface."
        ::= { optixOspfConfManager 1 }

    -- 1.3.6.1.4.1.2011.2.25.3.40.2.14.1.1
    optixInterfaceEntry OBJECT-TYPE
        SYNTAX OptixInterfaceEntry
        MAX-ACCESS not-accessible
        STATUS current
        DESCRIPTION
            "Indicates the item for configuring the wifi"
        INDEX{ optixNEShelf,optixNESlot,optixNESubCard,optixNEPort,optixNEChan,optixNEDcnType,optixNELogicif }
        ::= { optixInterfaceTable 1 }

    OptixInterfaceEntry ::=
        SEQUENCE {
            optixNEShelf
                Unsigned32,
            optixNESlot
                Unsigned32,
            optixNESubCard
                Unsigned32,
            optixNEPort
                Unsigned32,
            optixNEChan
                Unsigned32,
            optixNEDcnType
                INTEGER,
            optixNELogicif
                Unsigned32,
            optixNEIP
                IpAddress,
            optixNESubMask
                IpAddress
        }

    -- 1.3.6.1.4.1.2011.2.25.3.40.2.14.1.1.1
    optixNEShelf OBJECT-TYPE
        SYNTAX Unsigned32
        MAX-ACCESS not-accessible
        STATUS current
        DESCRIPTION
            "Indicates the shelf."
        ::= { optixInterfaceEntry 1 }

    -- 1.3.6.1.4.1.2011.2.25.3.40.2.14.1.1.2
    optixNESlot OBJECT-TYPE
        SYNTAX Unsigned32
        MAX-ACCESS not-accessible
        STATUS current
        DESCRIPTION
            "Indicates the slot."
        ::= { optixInterfaceEntry 2 }

    -- 1.3.6.1.4.1.2011.2.25.3.40.2.14.1.1.3
    optixNESubCard OBJECT-TYPE
        SYNTAX Unsigned32
        MAX-ACCESS not-accessible
        STATUS current
        DESCRIPTION
            "Indicates the subcard."
        ::= { optixInterfaceEntry 3 }

    -- 1.3.6.1.4.1.2011.2.25.3.40.2.14.1.1.4
    optixNEPort OBJECT-TYPE
        SYNTAX Unsigned32
        MAX-ACCESS not-accessible
        STATUS current
        DESCRIPTION
            "Indicates the port."
        ::= { optixInterfaceEntry 4 }

    -- 1.3.6.1.4.1.2011.2.25.3.40.2.14.1.1.5
    optixNEChan OBJECT-TYPE
        SYNTAX Unsigned32
        MAX-ACCESS not-accessible
        STATUS current
        DESCRIPTION
            "Indicates the channel."
        ::= { optixInterfaceEntry 5 }

    -- 1.3.6.1.4.1.2011.2.25.3.40.2.14.1.1.6
    optixNEDcnType OBJECT-TYPE
        SYNTAX INTEGER
        {
            outband(0),
            inband(1)
        }
        MAX-ACCESS not-accessible
        STATUS current
        DESCRIPTION
            "Indicates the dcntype."
        ::= { optixInterfaceEntry 6 }

    -- 1.3.6.1.4.1.2011.2.25.3.40.2.14.1.1.7
    optixNELogicif OBJECT-TYPE
        SYNTAX Unsigned32
        MAX-ACCESS not-accessible
        STATUS current
        DESCRIPTION
            "Indicates the logical interface."
        ::= { optixInterfaceEntry 7 }

    -- 1.3.6.1.4.1.2011.2.25.3.40.2.14.1.1.8
    optixNEIP OBJECT-TYPE
        SYNTAX IpAddress
        MAX-ACCESS read-write
        STATUS current
        DESCRIPTION
            "Indicates the IP."
        ::= { optixInterfaceEntry 8 }

    -- 1.3.6.1.4.1.2011.2.25.3.40.2.14.1.1.9
    optixNESubMask OBJECT-TYPE
        SYNTAX IpAddress
        MAX-ACCESS read-write
        STATUS current
        DESCRIPTION
            "Indicates the submask"
        ::= { optixInterfaceEntry 9 }

    -- 1.3.6.1.4.1.2011.2.25.3.40.2.14.2
    optixInterfaceEnTable OBJECT-TYPE
        SYNTAX SEQUENCE OF OptixInterfaceEnEntry
        MAX-ACCESS not-accessible
        STATUS current
        DESCRIPTION
            "Indicates the table of ospf interface for enable flag."
        ::= { optixOspfConfManager 2 }

    -- 1.3.6.1.4.1.2011.2.25.3.40.2.14.2.1
    optixInterfaceEnEntry OBJECT-TYPE
        SYNTAX OptixInterfaceEnEntry
        MAX-ACCESS not-accessible
        STATUS current
        DESCRIPTION
            "Indicates the item for the flag of ospf enable flag."
        INDEX{ optixNEInterface }
        ::= { optixInterfaceEnTable 1 }

    OptixInterfaceEnEntry ::=
        SEQUENCE {
            optixNEInterface
                INTEGER,
            optixNEInterfaceFlag
                INTEGER
        }

    -- 1.3.6.1.4.1.2011.2.25.3.40.2.14.2.1.1
    optixNEInterface OBJECT-TYPE
        SYNTAX INTEGER
        {
            lan(1),
            dcc(2)
        }
        MAX-ACCESS not-accessible
        STATUS current
        DESCRIPTION
            "Indicates the interface of the ospf."
        ::= { optixInterfaceEnEntry 1 }

    -- 1.3.6.1.4.1.2011.2.25.3.40.2.14.2.1.2
    optixNEInterfaceFlag OBJECT-TYPE
        SYNTAX INTEGER
        {
            enable(1),
            disable(0)
        }
        MAX-ACCESS read-write
        STATUS current
        DESCRIPTION
            "Indicates the priority of the OSPF DR."
        ::= { optixInterfaceEnEntry 2 }

    -- 1.3.6.1.4.1.2011.2.25.3.40.2.14.3
    optixInterfaceDRTable OBJECT-TYPE
        SYNTAX SEQUENCE OF OptixInterfaceDREntry
        MAX-ACCESS not-accessible
        STATUS current
        DESCRIPTION
            "Indicates the table of ospf DR priority"
        ::= { optixOspfConfManager 3 }

    -- 1.3.6.1.4.1.2011.2.25.3.40.2.14.3.1
    optixInterfaceDREntry OBJECT-TYPE
        SYNTAX OptixInterfaceDREntry
        MAX-ACCESS not-accessible
        STATUS current
        DESCRIPTION
            "Indicates the item for the priority of ospf interface."
        INDEX{ optixDRInterface }
        ::= { optixInterfaceDRTable 1 }

    OptixInterfaceDREntry ::=
        SEQUENCE {
            optixDRInterface
                INTEGER,
            optixDRInterfacePri
                Unsigned32
        }

    -- 1.3.6.1.4.1.2011.2.25.3.40.2.14.3.1.1
    optixDRInterface OBJECT-TYPE
        SYNTAX INTEGER
        {
            lan(1)
        }
        MAX-ACCESS not-accessible
        STATUS current
        DESCRIPTION
            "Indicates the interface of the ospf."
        ::= { optixInterfaceDREntry 1 }

    -- 1.3.6.1.4.1.2011.2.25.3.40.2.14.3.1.2
    optixDRInterfacePri OBJECT-TYPE
        SYNTAX Unsigned32
        MAX-ACCESS read-write
        STATUS current
        DESCRIPTION
            "Indicates the priority of the OSPF DR."
        ::= { optixInterfaceDREntry 2 }

    -- 1.3.6.1.4.1.2011.2.25.3.40.2.14.4
    optixCROspfImportTable OBJECT-TYPE
        SYNTAX SEQUENCE OF OptixCROspfImportEntry
        MAX-ACCESS not-accessible
        STATUS current
        DESCRIPTION
            "Indicates the table to which OSPF can be imported."
        ::= { optixOspfConfManager 4 }

    -- 1.3.6.1.4.1.2011.2.25.3.40.2.14.4.1
    optixCROspfImportEntry OBJECT-TYPE
        SYNTAX OptixCROspfImportEntry
        MAX-ACCESS not-accessible
        STATUS current
        DESCRIPTION
            "Indicates the item entry which ospf can import."
        INDEX{ optixCRImportFrom }
        ::= { optixCROspfImportTable 1 }

    OptixCROspfImportEntry ::=
        SEQUENCE {
            optixCRImportFrom
                INTEGER,
            optixCRImportEnFlag
                INTEGER
        }

    -- 1.3.6.1.4.1.2011.2.25.3.40.2.14.4.1.1
    optixCRImportFrom OBJECT-TYPE
        SYNTAX INTEGER
        {
            direct(1),
            static(2),
            rip(4),
            default(17)
        }
        MAX-ACCESS not-accessible
        STATUS current
        DESCRIPTION
            "Indicates the item which ospf can import."
        ::= { optixCROspfImportEntry 1 }

    -- 1.3.6.1.4.1.2011.2.25.3.40.2.14.4.1.2
    optixCRImportEnFlag OBJECT-TYPE
        SYNTAX INTEGER
        {
            enable(1),
            disable(0)
        }
        MAX-ACCESS read-write
        STATUS current
        DESCRIPTION
            "Indicates flag of the ospf item."
        ::= { optixCROspfImportEntry 2 }

    -- 1.3.6.1.4.1.2011.2.25.3.40.2.14.5
    optixOspfAreaTable OBJECT-TYPE
        SYNTAX SEQUENCE OF OptixOspfAreaEntry
        MAX-ACCESS not-accessible
        STATUS current
        DESCRIPTION
            "Indicates the information of ospf multi-area."
        ::= { optixOspfConfManager 5 }

    -- 1.3.6.1.4.1.2011.2.25.3.40.2.14.5.1
    optixOspfAreaEntry OBJECT-TYPE
        SYNTAX OptixOspfAreaEntry
        MAX-ACCESS not-accessible
        STATUS current
        DESCRIPTION
            "Indicates the item for ospf multi-area"
        INDEX{ optixAreaID }
        ::= { optixOspfAreaTable 1 }

    OptixOspfAreaEntry ::=
        SEQUENCE {
            optixAreaID
                IpAddress,
            optixAreaFlag
                INTEGER,
            optixAreaType
                INTEGER,
            optixAutoRange
                INTEGER,
            optixStubType
                INTEGER
        }

    -- 1.3.6.1.4.1.2011.2.25.3.40.2.14.5.1.1
    optixAreaID OBJECT-TYPE
        SYNTAX IpAddress
        MAX-ACCESS not-accessible
        STATUS current
        DESCRIPTION
            "Indicates the area-id."
        ::= { optixOspfAreaEntry 1 }

    -- 1.3.6.1.4.1.2011.2.25.3.40.2.14.5.1.2
    optixAreaFlag OBJECT-TYPE
        SYNTAX INTEGER
        {
            default(0),
            nondefault(1)
        }
        MAX-ACCESS read-only
        STATUS current
        DESCRIPTION
            "Indicates the default-area."
        ::= { optixOspfAreaEntry 2 }

    -- 1.3.6.1.4.1.2011.2.25.3.40.2.14.5.1.3
    optixAreaType OBJECT-TYPE
        SYNTAX INTEGER
        {
            none(0),
            simple(1),
            md5(2),
            hamcsha256256(3)
        }
        MAX-ACCESS read-write
        STATUS current
        DESCRIPTION
            "Indicates the authtype."
        ::= { optixOspfAreaEntry 3 }

    -- 1.3.6.1.4.1.2011.2.25.3.40.2.14.5.1.4
    optixAutoRange OBJECT-TYPE
        SYNTAX INTEGER
        {
            enable(1),
            disable(0)
        }
        MAX-ACCESS read-only
        STATUS current
        DESCRIPTION
            "Indicates the state of autorange."
        ::= { optixOspfAreaEntry 4 }

    -- 1.3.6.1.4.1.2011.2.25.3.40.2.14.5.1.5
    optixStubType OBJECT-TYPE
        SYNTAX INTEGER
        {
            nonstub(0),
            stub(1),
            nssa(2)
        }
        MAX-ACCESS read-only
        STATUS current
        DESCRIPTION
            "Indicates the type of the area stub."
        ::= { optixOspfAreaEntry 5 }

    -- 1.3.6.1.4.1.2011.2.25.3.40.2.14.6
    optixOspfAuthTable OBJECT-TYPE
        SYNTAX SEQUENCE OF OptixOspfAuthEntry
        MAX-ACCESS not-accessible
        STATUS current
        DESCRIPTION
            "Indicates the authtype-table for ospf."
        ::= { optixOspfConfManager 6 }

    -- 1.3.6.1.4.1.2011.2.25.3.40.2.14.6.1
    optixOspfAuthEntry OBJECT-TYPE
        SYNTAX OptixOspfAuthEntry
        MAX-ACCESS not-accessible
        STATUS current
        DESCRIPTION
            "Indicates the item for ospf authtype."
        INDEX{ optixOspfAuthInterface,optixOspfAuthType }
        ::= { optixOspfAuthTable 1 }

    OptixOspfAuthEntry ::=
        SEQUENCE {
            optixOspfAuthInterface
                INTEGER,
            optixOspfAuthType
                INTEGER,
            optixOspfAuthPW
                OCTET STRING,
            optixOspfKeyID
                Unsigned32
        }

    -- 1.3.6.1.4.1.2011.2.25.3.40.2.14.6.1.1
    optixOspfAuthInterface OBJECT-TYPE
        SYNTAX INTEGER
        {
            lan(1),
            dcc(2)
        }
        MAX-ACCESS not-accessible
        STATUS current
        DESCRIPTION
            "Indicates the name of interface."
        ::= { optixOspfAuthEntry 1 }

    -- 1.3.6.1.4.1.2011.2.25.3.40.2.14.6.1.2
    optixOspfAuthType OBJECT-TYPE
        SYNTAX INTEGER
        {
            none(0),
            simple(1),
            md5(2),
            hamcsha256256(3)
        }
        MAX-ACCESS not-accessible
        STATUS current
        DESCRIPTION
            "Indicates the type of authentication."
        ::= { optixOspfAuthEntry 2 }

    -- 1.3.6.1.4.1.2011.2.25.3.40.2.14.6.1.3
    optixOspfAuthPW OBJECT-TYPE
        SYNTAX OCTET STRING
        MAX-ACCESS read-write
        STATUS current
        DESCRIPTION
            "Indicates the password of authentication."
        ::= { optixOspfAuthEntry 3 }

    -- 1.3.6.1.4.1.2011.2.25.3.40.2.14.6.1.4
    optixOspfKeyID OBJECT-TYPE
        SYNTAX Unsigned32
        MAX-ACCESS read-write
        STATUS current
        DESCRIPTION
            "Indicates the key of authentication."
        ::= { optixOspfAuthEntry 4 }

    -- 1.3.6.1.4.1.2011.2.25.3.40.2.14.7
    optixOspfNBRInfoTable OBJECT-TYPE
        SYNTAX SEQUENCE OF OptixOspfNBRInfoEntry
        MAX-ACCESS not-accessible
        STATUS current
        DESCRIPTION
            "Indicates the table of ospf info."
        ::= { optixOspfConfManager 7 }

    -- 1.3.6.1.4.1.2011.2.25.3.40.2.14.7.1
    optixOspfNBRInfoEntry OBJECT-TYPE
        SYNTAX OptixOspfNBRInfoEntry
        MAX-ACCESS not-accessible
        STATUS current
        DESCRIPTION
            "Indicates the item for OSPF neighbors."
        INDEX{ optixNBRLocalRouteID,optixNBRProcessID,optixNBRAreaID,optixInterfaceName,optixBoardID,optixSubcardID,optixPortID,optixChannelID,optixNBRRouterID,optixNBRIP,optixNBRState,optixNBRMode,optixPriority,optixDRIP,optixBDRIP,optixBDMtu,optixLsaDeadTime,optixRtransInterVal,optixNBRUPTime,optixNBRSequence }
        ::= { optixOspfNBRInfoTable 1 }

    OptixOspfNBRInfoEntry ::=
        SEQUENCE {
            optixNBRLocalRouteID
                IpAddress,
            optixNBRProcessID
                Unsigned32,
            optixNBRAreaID
                IpAddress,
            optixInterfaceName
                OCTET STRING,
            optixBoardID
                Unsigned32,
            optixSubcardID
                Unsigned32,
            optixPortID
                Unsigned32,
            optixChannelID
                Unsigned32,
            optixNBRRouterID
                IpAddress,
            optixNBRIP
                IpAddress,
            optixNBRState
                INTEGER,
            optixNBRMode
                INTEGER,
            optixPriority
                Unsigned32,
            optixDRIP
                IpAddress,
            optixBDRIP
                IpAddress,
            optixBDMtu
                Unsigned32,
            optixLsaDeadTime
                Unsigned32,
            optixRtransInterVal
                Unsigned32,
            optixNBRUPTime
                Unsigned32,
            optixNBRSequence
                Unsigned32,
            optixOspfNBRInfo
                OCTET STRING
        }

    -- 1.3.6.1.4.1.2011.2.25.3.40.2.14.7.1.1
    optixNBRLocalRouteID OBJECT-TYPE
        SYNTAX IpAddress
        MAX-ACCESS not-accessible
        STATUS current
        DESCRIPTION
            "Indicates the Locale router ID."
        ::= { optixOspfNBRInfoEntry 1 }

    -- 1.3.6.1.4.1.2011.2.25.3.40.2.14.7.1.2
    optixNBRProcessID OBJECT-TYPE
        SYNTAX Unsigned32
        MAX-ACCESS not-accessible
        STATUS current
        DESCRIPTION
            "Indicates the process ID."
        ::= { optixOspfNBRInfoEntry 2 }

    -- 1.3.6.1.4.1.2011.2.25.3.40.2.14.7.1.3
    optixNBRAreaID OBJECT-TYPE
        SYNTAX IpAddress
        MAX-ACCESS not-accessible
        STATUS current
        DESCRIPTION
            "Indicates the area id."
        ::= { optixOspfNBRInfoEntry 3 }

    -- 1.3.6.1.4.1.2011.2.25.3.40.2.14.7.1.4
    optixInterfaceName OBJECT-TYPE
        SYNTAX OCTET STRING
        MAX-ACCESS not-accessible
        STATUS current
        DESCRIPTION
            "Indicates the Interface name."
        ::= { optixOspfNBRInfoEntry 4 }

    -- 1.3.6.1.4.1.2011.2.25.3.40.2.14.7.1.5
    optixBoardID OBJECT-TYPE
        SYNTAX Unsigned32
        MAX-ACCESS not-accessible
        STATUS current
        DESCRIPTION
            "Indicates the board ID."
        ::= { optixOspfNBRInfoEntry 5 }

    -- 1.3.6.1.4.1.2011.2.25.3.40.2.14.7.1.6
    optixSubcardID OBJECT-TYPE
        SYNTAX Unsigned32
        MAX-ACCESS not-accessible
        STATUS current
        DESCRIPTION
            "Indicates the subcard."
        ::= { optixOspfNBRInfoEntry 6 }

    -- 1.3.6.1.4.1.2011.2.25.3.40.2.14.7.1.7
    optixPortID OBJECT-TYPE
        SYNTAX Unsigned32
        MAX-ACCESS not-accessible
        STATUS current
        DESCRIPTION
            "Indicates the port."
        ::= { optixOspfNBRInfoEntry 7 }

    -- 1.3.6.1.4.1.2011.2.25.3.40.2.14.7.1.8
    optixChannelID OBJECT-TYPE
        SYNTAX Unsigned32
        MAX-ACCESS not-accessible
        STATUS current
        DESCRIPTION
            "Indicates the channel."
        ::= { optixOspfNBRInfoEntry 8 }

    -- 1.3.6.1.4.1.2011.2.25.3.40.2.14.7.1.9
    optixNBRRouterID OBJECT-TYPE
        SYNTAX IpAddress
        MAX-ACCESS not-accessible
        STATUS current
        DESCRIPTION
            "Indicates the NBR RouterID."
        ::= { optixOspfNBRInfoEntry 9 }

    -- 1.3.6.1.4.1.2011.2.25.3.40.2.14.7.1.10
    optixNBRIP OBJECT-TYPE
        SYNTAX IpAddress
        MAX-ACCESS not-accessible
        STATUS current
        DESCRIPTION
            "Indicates the NBR IP."
        ::= { optixOspfNBRInfoEntry 10 }

    -- 1.3.6.1.4.1.2011.2.25.3.40.2.14.7.1.11
    optixNBRState OBJECT-TYPE
        SYNTAX INTEGER
        {
            down(0),
            init(1),
            attempt(2),
            twoway(3),
            exstart(4),
            exchange(5),
            loading(6),
            full(7)
        }
        MAX-ACCESS not-accessible
        STATUS current
        DESCRIPTION
            "Indicates the NBR State."
        ::= { optixOspfNBRInfoEntry 11 }

    -- 1.3.6.1.4.1.2011.2.25.3.40.2.14.7.1.12
    optixNBRMode OBJECT-TYPE
        SYNTAX INTEGER
        {
            master(0),
            slave(1)
        }
        MAX-ACCESS not-accessible
        STATUS current
        DESCRIPTION
            "Indicates the mode of route."
        ::= { optixOspfNBRInfoEntry 12 }

    -- 1.3.6.1.4.1.2011.2.25.3.40.2.14.7.1.13
    optixPriority OBJECT-TYPE
        SYNTAX Unsigned32
        MAX-ACCESS not-accessible
        STATUS current
        DESCRIPTION
            "Indicates the priority."
        ::= { optixOspfNBRInfoEntry 13 }

    -- 1.3.6.1.4.1.2011.2.25.3.40.2.14.7.1.14
    optixDRIP OBJECT-TYPE
        SYNTAX IpAddress
        MAX-ACCESS not-accessible
        STATUS current
        DESCRIPTION
            "Indicates the DR IP."
        ::= { optixOspfNBRInfoEntry 14 }

    -- 1.3.6.1.4.1.2011.2.25.3.40.2.14.7.1.15
    optixBDRIP OBJECT-TYPE
        SYNTAX IpAddress
        MAX-ACCESS not-accessible
        STATUS current
        DESCRIPTION
            "Indicates the BDR IP."
        ::= { optixOspfNBRInfoEntry 15 }

    -- 1.3.6.1.4.1.2011.2.25.3.40.2.14.7.1.16
    optixBDMtu OBJECT-TYPE
        SYNTAX Unsigned32
        MAX-ACCESS not-accessible
        STATUS current
        DESCRIPTION
            "Indicates the mtu."
        ::= { optixOspfNBRInfoEntry 16 }

    -- 1.3.6.1.4.1.2011.2.25.3.40.2.14.7.1.17
    optixLsaDeadTime OBJECT-TYPE
        SYNTAX Unsigned32
        MAX-ACCESS not-accessible
        STATUS current
        DESCRIPTION
            "Indicates the lsa-dead-time."
        ::= { optixOspfNBRInfoEntry 17 }

    -- 1.3.6.1.4.1.2011.2.25.3.40.2.14.7.1.18
    optixRtransInterVal OBJECT-TYPE
        SYNTAX Unsigned32
        MAX-ACCESS not-accessible
        STATUS current
        DESCRIPTION
            "Indicates the retransmission interval."
        ::= { optixOspfNBRInfoEntry 18 }

    -- 1.3.6.1.4.1.2011.2.25.3.40.2.14.7.1.19
    optixNBRUPTime OBJECT-TYPE
        SYNTAX Unsigned32
        MAX-ACCESS not-accessible
        STATUS current
        DESCRIPTION
            "Indicates the time when the NE neighbor relationship is established."
        ::= { optixOspfNBRInfoEntry 19 }

    -- 1.3.6.1.4.1.2011.2.25.3.40.2.14.7.1.20
    optixNBRSequence OBJECT-TYPE
        SYNTAX Unsigned32
        MAX-ACCESS not-accessible
        STATUS current
        DESCRIPTION
            "Indicates the sequence."
        ::= { optixOspfNBRInfoEntry 20 }

    -- 1.3.6.1.4.1.2011.2.25.3.40.2.14.7.1.21
    optixOspfNBRInfo OBJECT-TYPE
        SYNTAX OCTET STRING
        MAX-ACCESS read-only
        STATUS current
        DESCRIPTION
            "Indicates the sequence."
        ::= { optixOspfNBRInfoEntry 21 }

    -- 1.3.6.1.4.1.2011.2.25.3.40.2.15
    optixOspfGroupManager OBJECT IDENTIFIER ::= { optixGlobalDcn 15 }

    -- 1.3.6.1.4.1.2011.2.25.3.40.2.15.1
    optixOPQState OBJECT-TYPE
        SYNTAX INTEGER
        {
            enable(1),
            disable(0)
        }
        MAX-ACCESS read-write
        STATUS current
        DESCRIPTION
            "Indicates the state of 10# lsa opq."
        ::= { optixOspfGroupManager 1 }

    -- 1.3.6.1.4.1.2011.2.25.3.40.2.15.2
    optixLanAuthType OBJECT-TYPE
        SYNTAX INTEGER
        {
            none(0),
            simple(1),
            md5(2),
            hamcsha256(3)
        }
        MAX-ACCESS read-write
        STATUS current
        DESCRIPTION
            "Indicates the authtype of lan."
        ::= { optixOspfGroupManager 2 }

    -- 1.3.6.1.4.1.2011.2.25.3.40.2.18
    optixPPPOEManager OBJECT IDENTIFIER ::= { optixGlobalDcn 18 }

    -- 1.3.6.1.4.1.2011.2.25.3.40.2.18.1
    optixDcnOption OBJECT-TYPE
        SYNTAX INTEGER
        {
            enable(1),
            disable(0)
        }
        MAX-ACCESS read-write
        STATUS current
        DESCRIPTION
            "Indicate the state of dcn pppoe"
        ::= { optixPPPOEManager 1 }

    -- 1.3.6.1.4.1.2011.2.25.3.40.2.18.2
    optixDcnProto OBJECT-TYPE
        SYNTAX INTEGER
        {
            nulll(0),
            ip(1),
            hwecc(3)
        }
        MAX-ACCESS read-write
        STATUS current
        DESCRIPTION
            "Indicate the protocol type of dcn pppoe"
        ::= { optixPPPOEManager 2 }

    -- 1.3.6.1.4.1.2011.2.25.3.40.2.18.3
    optixGcpOption OBJECT-TYPE
        SYNTAX INTEGER
        {
            enable(1),
            disable(0)
        }
        MAX-ACCESS read-write
        STATUS current
        DESCRIPTION
            "Indicate the state of gcp pppoe"
        ::= { optixPPPOEManager 3 }

    -- 1.3.6.1.4.1.2011.2.25.3.40.2.18.4
    optixGcpProto OBJECT-TYPE
        SYNTAX INTEGER
        {
            null(0),
            ip(1),
            hwecc(3)
        }
        MAX-ACCESS read-write
        STATUS current
        DESCRIPTION
            "Indicate the protocol type of gcp pppoe"
        ::= { optixPPPOEManager 4 }

    -- 1.3.6.1.4.1.2011.2.25.3.40.2.19
    optixDcnConModeManager OBJECT IDENTIFIER ::= { optixGlobalDcn 19 }

    -- 1.3.6.1.4.1.2011.2.25.3.40.2.19.1
    optixConMode OBJECT-TYPE
        SYNTAX INTEGER
        {
            ssl(0),
            nossl(1),
            all(2),
            none(3)
        }
        MAX-ACCESS read-write
        STATUS current
        DESCRIPTION
            "Indicates the NE connection mode."
        ::= { optixDcnConModeManager 1 }

    -- 1.3.6.1.4.1.2011.2.25.3.40.2.20
    optixNtpManager OBJECT IDENTIFIER ::= { optixGlobalDcn 20 }

    -- 1.3.6.1.4.1.2011.2.25.3.40.2.20.1
    optixNtpAclTable OBJECT-TYPE
        SYNTAX SEQUENCE OF OptixNtpAclEntry
        MAX-ACCESS not-accessible
        STATUS current
        DESCRIPTION
            "Indicates the NTP ACL rule table."
        ::= { optixNtpManager 1 }

    -- 1.3.6.1.4.1.2011.2.25.3.40.2.20.1.1
    optixNtpAclEntry OBJECT-TYPE
        SYNTAX OptixNtpAclEntry
        MAX-ACCESS not-accessible
        STATUS current
        DESCRIPTION
            "Indicates the entry to NTP ACL rules."
        INDEX{ optixNtpAclNo }
        ::= { optixNtpAclTable 1 }

    OptixNtpAclEntry ::=
        SEQUENCE {
            optixNtpAclNo
                Unsigned32,
            optixNtpAclNeID
                Unsigned32,
            optixNtpAclIP
                IpAddress,
            optixNtpAclNsap
                OCTET STRING,
            optixNtpAclPermission
                INTEGER,
            optixNtpAclRight
                INTEGER,
            optixNtpAclRowStatus
                RowStatus
        }

    -- 1.3.6.1.4.1.2011.2.25.3.40.2.20.1.1.1
    optixNtpAclNo OBJECT-TYPE
        SYNTAX Unsigned32
        MAX-ACCESS not-accessible
        STATUS current
        DESCRIPTION
            "Indicates the number of an NTP ACL rule."
        ::= { optixNtpAclEntry 1 }

    -- 1.3.6.1.4.1.2011.2.25.3.40.2.20.1.1.2
    optixNtpAclNeID OBJECT-TYPE
        SYNTAX Unsigned32
        MAX-ACCESS read-create
        STATUS current
        DESCRIPTION
            "Indicates the NE ID of an NTP ACL rule."
        ::= { optixNtpAclEntry 2 }

    -- 1.3.6.1.4.1.2011.2.25.3.40.2.20.1.1.3
    optixNtpAclIP OBJECT-TYPE
        SYNTAX IpAddress
        MAX-ACCESS read-create
        STATUS current
        DESCRIPTION
            "Indicates the NE IP address of an NTP ACL rule."
        ::= { optixNtpAclEntry 3 }

    -- 1.3.6.1.4.1.2011.2.25.3.40.2.20.1.1.4
    optixNtpAclNsap OBJECT-TYPE
        SYNTAX OCTET STRING
        MAX-ACCESS read-create
        STATUS current
        DESCRIPTION
            "Indicates the NTP NSAP."
        ::= { optixNtpAclEntry 4 }

    -- 1.3.6.1.4.1.2011.2.25.3.40.2.20.1.1.5
    optixNtpAclPermission OBJECT-TYPE
        SYNTAX INTEGER
        {
            accept(0),
            deny(1)
        }
        MAX-ACCESS read-create
        STATUS current
        DESCRIPTION
            "Indicates the NTP ACL operation enable status."
        ::= { optixNtpAclEntry 5 }

    -- 1.3.6.1.4.1.2011.2.25.3.40.2.20.1.1.6
    optixNtpAclRight OBJECT-TYPE
        SYNTAX INTEGER
        {
            query(0),
            synchronization(1),
            server(2),
            peer(3)
        }
        MAX-ACCESS read-create
        STATUS current
        DESCRIPTION
            "Indicates the NTP ACL operation rights."
        ::= { optixNtpAclEntry 6 }

    -- 1.3.6.1.4.1.2011.2.25.3.40.2.20.1.1.255
    optixNtpAclRowStatus OBJECT-TYPE
        SYNTAX RowStatus
        MAX-ACCESS read-create
        STATUS current
        DESCRIPTION
            "This object indicates the row status. 1: active 4: createAndGo 6: destroy"
        ::= { optixNtpAclEntry 255 }

    -- 1.3.6.1.4.1.2011.2.25.3.40.2.20.2
    optixNtpSrvTable OBJECT-TYPE
        SYNTAX SEQUENCE OF OptixNtpSrvEntry
        MAX-ACCESS not-accessible
        STATUS current
        DESCRIPTION
            "Indicates the NTP server configuraion table."
        ::= { optixNtpManager 2 }

    -- 1.3.6.1.4.1.2011.2.25.3.40.2.20.2.1
    optixNtpSrvEntry OBJECT-TYPE
        SYNTAX OptixNtpSrvEntry
        MAX-ACCESS not-accessible
        STATUS current
        DESCRIPTION
            "Indicates the entry to the NTP server table."
        INDEX{ optixNtpSrvNeid,optixNtpSrvIP,optixNtpSrvNSAP }
        ::= { optixNtpSrvTable 1 }

    OptixNtpSrvEntry ::=
        SEQUENCE {
            optixNtpSrvNeid
                Unsigned32,
            optixNtpSrvIP
                IpAddress,
            optixNtpSrvNSAP
                OCTET STRING,
            optixNtpSrvVer
                Unsigned32,
            optixNtpSrvKeyID
                Unsigned32,
            optixNtpSrvPri
                INTEGER,
            optixNtpSrvStatus
                RowStatus
        }

    -- 1.3.6.1.4.1.2011.2.25.3.40.2.20.2.1.1
    optixNtpSrvNeid OBJECT-TYPE
        SYNTAX Unsigned32
        MAX-ACCESS not-accessible
        STATUS current
        DESCRIPTION
            "Indicates the NE ID of the NTP server."
        ::= { optixNtpSrvEntry 1 }

    -- 1.3.6.1.4.1.2011.2.25.3.40.2.20.2.1.2
    optixNtpSrvIP OBJECT-TYPE
        SYNTAX IpAddress
        MAX-ACCESS not-accessible
        STATUS current
        DESCRIPTION
            "Indicates the IP address of the NTP server."
        ::= { optixNtpSrvEntry 2 }

    -- 1.3.6.1.4.1.2011.2.25.3.40.2.20.2.1.3
    optixNtpSrvNSAP OBJECT-TYPE
        SYNTAX OCTET STRING
        MAX-ACCESS not-accessible
        STATUS current
        DESCRIPTION
            "Indicates the NSAP of the NTP server."
        ::= { optixNtpSrvEntry 3 }

    -- 1.3.6.1.4.1.2011.2.25.3.40.2.20.2.1.4
    optixNtpSrvVer OBJECT-TYPE
        SYNTAX Unsigned32
        MAX-ACCESS read-create
        STATUS current
        DESCRIPTION
            "Indicates the NTP version of the NTP server."
        ::= { optixNtpSrvEntry 4 }

    -- 1.3.6.1.4.1.2011.2.25.3.40.2.20.2.1.5
    optixNtpSrvKeyID OBJECT-TYPE
        SYNTAX Unsigned32
        MAX-ACCESS read-create
        STATUS current
        DESCRIPTION
            "Indicates the key ID of the authentication for the NTP server."
        ::= { optixNtpSrvEntry 5 }

    -- 1.3.6.1.4.1.2011.2.25.3.40.2.20.2.1.6
    optixNtpSrvPri OBJECT-TYPE
        SYNTAX INTEGER
        {
            false(0),
            true(1)
        }
        MAX-ACCESS read-create
        STATUS current
        DESCRIPTION
            "Indicates the priority of the NTP server"
        ::= { optixNtpSrvEntry 6 }

    -- 1.3.6.1.4.1.2011.2.25.3.40.2.20.2.1.255
    optixNtpSrvStatus OBJECT-TYPE
        SYNTAX RowStatus
        MAX-ACCESS read-create
        STATUS current
        DESCRIPTION
            "This object indicates the row status. 1: active 4: createAndGo 6: destroy"
        ::= { optixNtpSrvEntry 255 }

    -- 1.3.6.1.4.1.2011.2.25.3.40.2.20.3
    optixNtpSrvAuthTable OBJECT-TYPE
        SYNTAX SEQUENCE OF OptixNtpSrvAuthEntry
        MAX-ACCESS not-accessible
        STATUS current
        DESCRIPTION
            "Indicates the PW authentication table of the NTP server."
        ::= { optixNtpManager 3 }

    -- 1.3.6.1.4.1.2011.2.25.3.40.2.20.3.1
    optixNtpSrvAuthEntry OBJECT-TYPE
        SYNTAX OptixNtpSrvAuthEntry
        MAX-ACCESS not-accessible
        STATUS current
        DESCRIPTION
            "Indicates the entry to the PW authentication table."
        INDEX{ optixNtpSrvAuthKeyID }
        ::= { optixNtpSrvAuthTable 1 }

    OptixNtpSrvAuthEntry ::=
        SEQUENCE {
            optixNtpSrvAuthKeyID
                Unsigned32,
            optixNtpSrvAuthType
                INTEGER,
            optixNtpSrvAuthPw
                OCTET STRING,
            optixNtpSrvAuthStatus
                RowStatus
        }

    -- 1.3.6.1.4.1.2011.2.25.3.40.2.20.3.1.1
    optixNtpSrvAuthKeyID OBJECT-TYPE
        SYNTAX Unsigned32
        MAX-ACCESS not-accessible
        STATUS current
        DESCRIPTION
            "Indicates the authentication key ID of the NTP server."
        ::= { optixNtpSrvAuthEntry 1 }

    -- 1.3.6.1.4.1.2011.2.25.3.40.2.20.3.1.2
    optixNtpSrvAuthType OBJECT-TYPE
        SYNTAX INTEGER
        {
            md5(0)
        }
        MAX-ACCESS read-create
        STATUS current
        DESCRIPTION
            "Indicates the authentication key type of the NTP server."
        ::= { optixNtpSrvAuthEntry 2 }

    -- 1.3.6.1.4.1.2011.2.25.3.40.2.20.3.1.3
    optixNtpSrvAuthPw OBJECT-TYPE
        SYNTAX OCTET STRING
        MAX-ACCESS read-create
        STATUS current
        DESCRIPTION
            "Indicates the authentication password of the NTP server."
        ::= { optixNtpSrvAuthEntry 3 }

    -- 1.3.6.1.4.1.2011.2.25.3.40.2.20.3.1.4
    optixNtpSrvAuthStatus OBJECT-TYPE
        SYNTAX RowStatus
        MAX-ACCESS read-create
        STATUS current
        DESCRIPTION
            "This object indicates the row status. 1: active 4: createAndGo 6: destroy"
        ::= { optixNtpSrvAuthEntry 4 }

    -- 1.3.6.1.4.1.2011.2.25.3.40.2.20.4
    optixNtpTrustKeyTable OBJECT-TYPE
        SYNTAX SEQUENCE OF OptixNtpTrustKeyEntry
        MAX-ACCESS not-accessible
        STATUS current
        DESCRIPTION
            "Indicates the trusty status table."
        ::= { optixNtpManager 4 }

    -- 1.3.6.1.4.1.2011.2.25.3.40.2.20.4.1
    optixNtpTrustKeyEntry OBJECT-TYPE
        SYNTAX OptixNtpTrustKeyEntry
        MAX-ACCESS not-accessible
        STATUS current
        DESCRIPTION
            "Indicates the entry to the trusty status table."
        INDEX{ optixNtpTrustKeyID }
        ::= { optixNtpTrustKeyTable 1 }

    OptixNtpTrustKeyEntry ::=
        SEQUENCE {
            optixNtpTrustKeyID
                Unsigned32,
            optixNtpTustKeyState
                INTEGER
        }

    -- 1.3.6.1.4.1.2011.2.25.3.40.2.20.4.1.1
    optixNtpTrustKeyID OBJECT-TYPE
        SYNTAX Unsigned32
        MAX-ACCESS not-accessible
        STATUS current
        DESCRIPTION
            "Indicates the key ID of the trusty status.."
        ::= { optixNtpTrustKeyEntry 1 }

    -- 1.3.6.1.4.1.2011.2.25.3.40.2.20.4.1.2
    optixNtpTustKeyState OBJECT-TYPE
        SYNTAX INTEGER
        {
            no(0),
            yes(1)
        }
        MAX-ACCESS read-write
        STATUS current
        DESCRIPTION
            "Indicates the trusty status of the NTP server."
        ::= { optixNtpTrustKeyEntry 2 }

    -- 1.3.6.1.4.1.2011.2.25.3.40.2.21
    optixNtpGloableManager OBJECT IDENTIFIER ::= { optixGlobalDcn 21 }

    -- 1.3.6.1.4.1.2011.2.25.3.40.2.21.1
    optixNtpSrvstate OBJECT-TYPE
        SYNTAX INTEGER
        {
            disable(0),
            enable(1)
        }
        MAX-ACCESS read-write
        STATUS current
        DESCRIPTION
            "Indicates the service status of the NTP server."
        ::= { optixNtpGloableManager 1 }

    -- 1.3.6.1.4.1.2011.2.25.3.40.2.21.2
    optixNtpState OBJECT-TYPE
        SYNTAX INTEGER
        {
            disable(0),
            enable(1)
        }
        MAX-ACCESS read-write
        STATUS current
        DESCRIPTION
            "Indicates the enable status of the NTP server."
        ::= { optixNtpGloableManager 2 }

    -- 1.3.6.1.4.1.2011.2.25.3.40.2.21.3
    optixNtpAuthState OBJECT-TYPE
        SYNTAX INTEGER
        {
            disable(0),
            enable(1)
        }
        MAX-ACCESS read-write
        STATUS current
        DESCRIPTION
            "Indicates the authentication status of the NTP server."
        ::= { optixNtpGloableManager 3 }

    -- 1.3.6.1.4.1.2011.2.25.3.40.2.21.4
    optixNtpStatusInfo OBJECT-TYPE
        SYNTAX INTEGER
        {
            unsynchronized(0),
            synchronized(1)
        }
        MAX-ACCESS read-only
        STATUS current
        DESCRIPTION
            "Indicates the running status of the NTP server."
        ::= { optixNtpGloableManager 4 }

    -- 1.3.6.1.4.1.2011.2.25.3.40.2.21.5
    optixNtpSynNEID OBJECT-TYPE
        SYNTAX Unsigned32
        MAX-ACCESS read-only
        STATUS current
        DESCRIPTION
            "Indicates the NEID of NTP synchronization."
        ::= { optixNtpGloableManager 5 }

    -- 1.3.6.1.4.1.2011.2.25.3.40.2.21.6
    optixNtpSynNEIP OBJECT-TYPE
        SYNTAX IpAddress
        MAX-ACCESS read-only
        STATUS current
        DESCRIPTION
            "Indicates the IP of NTP synchronization."
        ::= { optixNtpGloableManager 6 }

    -- 1.3.6.1.4.1.2011.2.25.3.40.2.21.7
    optixNtpSynNSAP OBJECT-TYPE
        SYNTAX OCTET STRING
        MAX-ACCESS read-only
        STATUS current
        DESCRIPTION
            "Indicates the NSAP of NTP synchronization"
        ::= { optixNtpGloableManager 7 }

    -- 1.3.6.1.4.1.2011.2.25.3.40.2.22
    optixSftpFingerprintManager OBJECT IDENTIFIER ::= { optixGlobalDcn 22 }

    -- 1.3.6.1.4.1.2011.2.25.3.40.2.22.1
    optixSftpFingerBaseTable OBJECT-TYPE
        SYNTAX SEQUENCE OF OptixSftpFingerBaseEntry
        MAX-ACCESS not-accessible
        STATUS current
        DESCRIPTION
            "Indicates the SFTP Fingerprint server configuraion table."
        ::= { optixSftpFingerprintManager 1 }

    -- 1.3.6.1.4.1.2011.2.25.3.40.2.22.1.1
    optixSftpFingerBaseEntry OBJECT-TYPE
        SYNTAX OptixSftpFingerBaseEntry
        MAX-ACCESS not-accessible
        STATUS current
        DESCRIPTION
            "Indicates the entry to the SFTP Fingerprint server table."
        INDEX{ optixSftpFingerBaseIP,optixSftpFingerBasePort }
        ::= { optixSftpFingerBaseTable 1 }

    OptixSftpFingerBaseEntry ::=
        SEQUENCE {
            optixSftpFingerBaseIP
                IpAddress,
            optixSftpFingerBasePort
                Unsigned32,
            optixSftpFingerBaseAlg
                INTEGER,
            optixSftpFingerBaseFingerprint
                OCTET STRING,
            optixSftpFingerBaseStatus
                RowStatus
        }

    -- 1.3.6.1.4.1.2011.2.25.3.40.2.22.1.1.1
    optixSftpFingerBaseIP OBJECT-TYPE
        SYNTAX IpAddress
        MAX-ACCESS not-accessible
        STATUS current
        DESCRIPTION
            "Indicates the IP address of the SFTP server."
        ::= { optixSftpFingerBaseEntry 1 }

    -- 1.3.6.1.4.1.2011.2.25.3.40.2.22.1.1.2
    optixSftpFingerBasePort OBJECT-TYPE
        SYNTAX Unsigned32
        MAX-ACCESS not-accessible
        STATUS current
        DESCRIPTION
            "Indicates the port of the SFTP server."
        ::= { optixSftpFingerBaseEntry 2 }

    -- 1.3.6.1.4.1.2011.2.25.3.40.2.22.1.1.3
    optixSftpFingerBaseAlg OBJECT-TYPE
        SYNTAX INTEGER
        {
            md5(0),
            sha256(3)
        }
        MAX-ACCESS read-create
        STATUS current
        DESCRIPTION
            "Indicates the algorithm type of the SFTP server."
        ::= { optixSftpFingerBaseEntry 3 }

    -- 1.3.6.1.4.1.2011.2.25.3.40.2.22.1.1.4
    optixSftpFingerBaseFingerprint OBJECT-TYPE
        SYNTAX OCTET STRING
        MAX-ACCESS read-create
        STATUS current
        DESCRIPTION
            "Indicates the fingerprint of the SFTP server."
        ::= { optixSftpFingerBaseEntry 4 }

    -- 1.3.6.1.4.1.2011.2.25.3.40.2.22.1.1.5
    optixSftpFingerBaseStatus OBJECT-TYPE
        SYNTAX RowStatus
        MAX-ACCESS read-create
        STATUS current
        DESCRIPTION
            "This object indicates the row status. 1: active 4: createAndGo 6: destroy"
        ::= { optixSftpFingerBaseEntry 5 }

    -- 1.3.6.1.4.1.2011.2.25.3.40.2.23
    optixSftpFingerprintSwitchManager OBJECT IDENTIFIER ::= { optixGlobalDcn 23 }

    -- 1.3.6.1.4.1.2011.2.25.3.40.2.23.1
    optixSftpFingerprintSwitch OBJECT-TYPE
        SYNTAX INTEGER
        {
            close(0),
            open(1),
            unknown(2)
        }
        MAX-ACCESS read-write
        STATUS current
        DESCRIPTION
            "Indicates the open/close status of the sftp server fingerprint authentication."
        ::= { optixSftpFingerprintSwitchManager 1 }

END
