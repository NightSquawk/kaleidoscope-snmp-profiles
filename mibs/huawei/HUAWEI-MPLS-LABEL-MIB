-- =================================================================
-- Copyright (C) 2011 by  HUAWEI TECHNOLOGIES. All rights reserved.
-- Description: The MIB is used for configuring and querying the  
--              range of MPLS label and MPLS default ttl.
-- Reference:
-- Version: V1.01
-- =================================================================
    HUAWEI-MPLS-LABEL-MIB DEFINITIONS ::= BEGIN
 
        IMPORTS 
            hwMpls            
                FROM HUAWEI-MIB 
            ifIndex, InterfaceIndex            
                FROM IF-MIB            
            InetAddressType            
                FROM INET-ADDRESS-MIB
            IpAddress, Integer32, Unsigned32, Counter32, Counter64, 
            OBJECT-TYPE, MODULE-IDENTITY, NOTIFICATION-TYPE 
                FROM SNMPv2-SMI             
            TruthValue, TimeStamp, RowStatus, TEXTUAL-CONVENTION      
                FROM SNMPv2-TC 
            OBJECT-GROUP, NOTIFICATION-GROUP            
                FROM SNMPv2-CONF;
        
        hwMplsLabel MODULE-IDENTITY 
            LAST-UPDATED "201107211111Z"        
            ORGANIZATION 
                "Huawei Technologies Co.,Ltd."
            CONTACT-INFO                                       
                "Huawei Industrial Base
                 Bantian, Longgang
                 Shenzhen 518129
                 People's Republic of China
                 Website: http://www.huawei.com
                 Email: support@huawei.com
                "                                                
            DESCRIPTION                        
                "The MIB is used for configuring and querying the range of MPLS label and MPLS default ttl."
          
            --  Revision history   
            REVISION    "201107211111Z"
            DESCRIPTION "V1.01, added hwMplsDefaultTtl,this object indicates the mpls default ttl,the node of hwMplsDefaultTtl's value range to 1-255."                    
                                 
            REVISION "201007031000Z"                    
            DESCRIPTION "V1.00, initial revision."      
      
            ::= { hwMpls 9 }
            
        hwMplsLabelStartValue OBJECT-TYPE
            SYNTAX Integer32 (16|8192)
            MAX-ACCESS read-write
            STATUS current
            DESCRIPTION
                "This object indicates the start value of MPLS label.
                 After this object is modified successfully, the system will automatically reset after saving the configuration. 
                 Therefore, exercise caution when modifying this object.
                 Default: 8192
                " 
            ::= { hwMplsLabel 1 }

        hwMplsStaticLspLabelStart OBJECT-TYPE
            SYNTAX Integer32
            MAX-ACCESS read-only
            STATUS current
            DESCRIPTION
                "This object indicates the start value of static LSP.
                " 
            ::= { hwMplsLabel 2 }

        hwMplsStaticLspLabelEnd OBJECT-TYPE
            SYNTAX Integer32
            MAX-ACCESS read-only
            STATUS current
            DESCRIPTION
                "This object indicates the end value of static LSP.
                " 
            ::= { hwMplsLabel 3 }

        hwMplsStaticPwLabelStart OBJECT-TYPE
            SYNTAX Integer32
            MAX-ACCESS read-only
            STATUS current
            DESCRIPTION
                "This object indicates the start value of static PW.
                " 
            ::= { hwMplsLabel 4 }

        hwMplsStaticPwLabelEnd OBJECT-TYPE
            SYNTAX Integer32
            MAX-ACCESS read-only
            STATUS current
            DESCRIPTION
                "This object indicates the end value of static PW.
                " 
            ::= { hwMplsLabel 5 }    
            
        hwMplsDefaultTtl OBJECT-TYPE
            SYNTAX Integer32 (1..255) 
            MAX-ACCESS read-write
            STATUS current
            DESCRIPTION
                "This object indicates the mpls ttl default. 
                Range: 1-255.  
                Default: 64.
                " 
            ::= { hwMpls 10 }


    END
