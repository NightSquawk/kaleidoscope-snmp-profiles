GUDEADS-ETS8801-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200705231244Z"	-- May 23, 2007 12:44:00 PM
	ORGANIZATION "Gude Analog- und Digitalsysteme GmbH"
	CONTACT-INFO
		"http://www.gudeads.com/"
	DESCRIPTION
		""
	REVISION "200705231244Z"	-- May 23, 2007 12:44:00 PM
	DESCRIPTION
		"Initial version."
	-- 1.3.6.1.4.1.28507
	::= { enterprises 28507 }


gadsETS8801 OBJECT IDENTIFIER 
	-- 1.3.6.1.4.1.28507.41
	::= { gudeads 41 }

-- Notification Types
--

ets8801Events OBJECT IDENTIFIER 
	-- 1.3.6.1.4.1.28507.41.3
	::= { gadsETS8801 3 }

-- Scalars and Tables
--

ets8801Objects OBJECT IDENTIFIER 
	-- 1.3.6.1.4.1.28507.41.1
	::= { gadsETS8801 1 }

ets8801CommonConfig OBJECT IDENTIFIER 
	-- 1.3.6.1.4.1.28507.41.1.1
	::= { ets8801Objects 1 }

ets8801SNMPaccess OBJECT IDENTIFIER 
	-- 1.3.6.1.4.1.28507.41.1.1.1
	::= { ets8801CommonConfig 1 }

ets8801TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.41.1.1.1.1
	::= { ets8801SNMPaccess 1 }


ets8801TrapIPTable OBJECT-TYPE
	SYNTAX  SEQUENCE OF Ets8801TrapIPEntry
	MAX-ACCESS not-accessible
	STATUS  current
	DESCRIPTION
		"list of all Trap receiver"
	-- 1.3.6.1.4.1.28507.41.1.1.1.2
	::= { ets8801SNMPaccess 2 }


ets8801TrapIPEntry OBJECT-TYPE
	SYNTAX  Ets8801TrapIPEntry
	MAX-ACCESS not-accessible
	STATUS  current
	DESCRIPTION
		"an entry containing management
		informations regarding the list of trap
		receivers"
	INDEX {
		ets8801TrapIPIndex }
	-- 1.3.6.1.4.1.28507.41.1.1.1.2.1
	::= { ets8801TrapIPTable 1 }


Ets8801TrapIPEntry ::= SEQUENCE {

	ets8801TrapIPIndex Integer32,
	ets8801TrapAddr    OCTET STRING }


ets8801TrapIPIndex OBJECT-TYPE
	SYNTAX  Integer32 (1..8)
	MAX-ACCESS read-only
	STATUS  current
	DESCRIPTION
		"A unique value, greater than zero, for each receiver slot."
	-- 1.3.6.1.4.1.28507.41.1.1.1.2.1.1
	::= { ets8801TrapIPEntry 1 }


ets8801TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.41.1.1.1.2.1.2
	::= { ets8801TrapIPEntry 2 }


ets8801IntActors OBJECT IDENTIFIER 
	-- 1.3.6.1.4.1.28507.41.1.3
	::= { ets8801Objects 3 }

ets8801Buzzer OBJECT-TYPE
	SYNTAX  Integer32 (0..1)
	UNITS	"0 = Off, 1 = On"
	MAX-ACCESS read-write
	STATUS  current
	DESCRIPTION
		"turn Buzzer on and off"
	-- 1.3.6.1.4.1.28507.41.1.3.10
	::= { ets8801IntActors 10 }


ets8801IntSensors OBJECT IDENTIFIER 
	-- 1.3.6.1.4.1.28507.41.1.5
	::= { ets8801Objects 5 }

ets8801PowerChan OBJECT IDENTIFIER 
	-- 1.3.6.1.4.1.28507.41.1.5.1
	::= { ets8801IntSensors 1 }

ets8801ActivePowerChan OBJECT-TYPE
	SYNTAX  Unsigned32 (1)
	MAX-ACCESS read-only
	STATUS  current
	DESCRIPTION
		"Number of suppported Power Channels."
	-- 1.3.6.1.4.1.28507.41.1.5.1.1
	::= { ets8801PowerChan 1 }


ets8801PowerTable OBJECT-TYPE
	SYNTAX  SEQUENCE OF Ets8801PowerEntry
	MAX-ACCESS not-accessible
	STATUS  current
	DESCRIPTION
		"All available Channel Interfaces."
	-- 1.3.6.1.4.1.28507.41.1.5.1.2
	::= { ets8801PowerChan 2 }


ets8801PowerEntry OBJECT-TYPE
	SYNTAX  Ets8801PowerEntry
	MAX-ACCESS not-accessible
	STATUS  current
	DESCRIPTION
		"An entry containing management information
		applicable to a particular Power Channel."
	INDEX {
		ets8801PowerIndex }
	-- 1.3.6.1.4.1.28507.41.1.5.1.2.1
	::= { ets8801PowerTable 1 }


Ets8801PowerEntry ::= SEQUENCE {

	ets8801PowerIndex                   Integer32,
	ets8801ChanStatus                   Integer32,
	ets8801AbsEnergyActive              Unsigned32,
	ets8801PowerActive                  Integer32,
	ets8801Current                      Unsigned32,
	ets8801Voltage                      Unsigned32,
	ets8801Frequency                    Unsigned32,
	ets8801PowerFactor                  Integer32,
	ets8801Pangle                       Integer32,
	ets8801PowerApparent                Integer32,
	ets8801PowerReactive                Integer32,
	ets8801AbsEnergyReactive            Unsigned32,
	ets8801AbsEnergyActiveResettable    Unsigned32,
	ets8801AbsEnergyReactiveResettable  Unsigned32,
	ets8801ResetTime                    Unsigned32,
	ets8801ForwEnergyActive             Unsigned32,
	ets8801ForwEnergyReactive           Unsigned32,
	ets8801ForwEnergyActiveResettable   Unsigned32,
	ets8801ForwEnergyReactiveResettable Unsigned32,
	ets8801RevEnergyActive              Unsigned32,
	ets8801RevEnergyReactive            Unsigned32,
	ets8801RevEnergyActiveResettable    Unsigned32,
	ets8801RevEnergyReactiveResettable  Unsigned32,
	ets8801ResidualCurrent              Unsigned32 }


ets8801PowerIndex OBJECT-TYPE
	SYNTAX  Integer32 (1)
	MAX-ACCESS read-only
	STATUS  current
	DESCRIPTION
		"Index of Power Channel entries"
	-- 1.3.6.1.4.1.28507.41.1.5.1.2.1.1
	::= { ets8801PowerEntry 1 }


ets8801ChanStatus OBJECT-TYPE
	SYNTAX  Integer32 (0..1)
	MAX-ACCESS read-only
	STATUS  current
	DESCRIPTION
		"0 = data not active, 1 = data valid"
	-- 1.3.6.1.4.1.28507.41.1.5.1.2.1.2
	::= { ets8801PowerEntry 2 }


ets8801AbsEnergyActive OBJECT-TYPE
	SYNTAX  Unsigned32
	UNITS	"Wh"
	MAX-ACCESS read-only
	STATUS  current
	DESCRIPTION
		"Absolute Active Energy counter."
	-- 1.3.6.1.4.1.28507.41.1.5.1.2.1.3
	::= { ets8801PowerEntry 3 }


ets8801PowerActive OBJECT-TYPE
	SYNTAX  Integer32
	UNITS	"W"
	MAX-ACCESS read-only
	STATUS  current
	DESCRIPTION
		"Active Power"
	-- 1.3.6.1.4.1.28507.41.1.5.1.2.1.4
	::= { ets8801PowerEntry 4 }


ets8801Current OBJECT-TYPE
	SYNTAX  Unsigned32
	UNITS	"mA"
	MAX-ACCESS read-only
	STATUS  current
	DESCRIPTION
		"Actual Curent on Power Channel."
	-- 1.3.6.1.4.1.28507.41.1.5.1.2.1.5
	::= { ets8801PowerEntry 5 }


ets8801Voltage OBJECT-TYPE
	SYNTAX  Unsigned32
	UNITS	"V"
	MAX-ACCESS read-only
	STATUS  current
	DESCRIPTION
		"Actual Voltage on Power Channel"
	-- 1.3.6.1.4.1.28507.41.1.5.1.2.1.6
	::= { ets8801PowerEntry 6 }


ets8801Frequency OBJECT-TYPE
	SYNTAX  Unsigned32
	UNITS	"0.01 hz"
	MAX-ACCESS read-only
	STATUS  current
	DESCRIPTION
		"Frequency of Power Channel"
	-- 1.3.6.1.4.1.28507.41.1.5.1.2.1.7
	::= { ets8801PowerEntry 7 }


ets8801PowerFactor OBJECT-TYPE
	SYNTAX  Integer32
	UNITS	"0.001"
	MAX-ACCESS read-only
	STATUS  current
	DESCRIPTION
		"Power Factor of Channel between
		-1.0 and 1.00"
	-- 1.3.6.1.4.1.28507.41.1.5.1.2.1.8
	::= { ets8801PowerEntry 8 }


ets8801Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.41.1.5.1.2.1.9
	::= { ets8801PowerEntry 9 }


ets8801PowerApparent OBJECT-TYPE
	SYNTAX  Integer32
	UNITS	"VA"
	MAX-ACCESS read-only
	STATUS  current
	DESCRIPTION
		"L Line Mean Apparent Power"
	-- 1.3.6.1.4.1.28507.41.1.5.1.2.1.10
	::= { ets8801PowerEntry 10 }


ets8801PowerReactive OBJECT-TYPE
	SYNTAX  Integer32
	UNITS	"VAR"
	MAX-ACCESS read-only
	STATUS  current
	DESCRIPTION
		"L Line Mean Reactive Power"
	-- 1.3.6.1.4.1.28507.41.1.5.1.2.1.11
	::= { ets8801PowerEntry 11 }


ets8801AbsEnergyReactive OBJECT-TYPE
	SYNTAX  Unsigned32
	UNITS	"VARh"
	MAX-ACCESS read-only
	STATUS  current
	DESCRIPTION
		"Absolute Reactive Energy counter."
	-- 1.3.6.1.4.1.28507.41.1.5.1.2.1.12
	::= { ets8801PowerEntry 12 }


ets8801AbsEnergyActiveResettable OBJECT-TYPE
	SYNTAX  Unsigned32
	UNITS	"Wh"
	MAX-ACCESS read-write
	STATUS  current
	DESCRIPTION
		"Resettable Absolute Active Energy counter.
		Writing '0' resets all resettable counter."
	-- 1.3.6.1.4.1.28507.41.1.5.1.2.1.13
	::= { ets8801PowerEntry 13 }


ets8801AbsEnergyReactiveResettable OBJECT-TYPE
	SYNTAX  Unsigned32
	UNITS	"VARh"
	MAX-ACCESS read-only
	STATUS  current
	DESCRIPTION
		"Resettable Absolute Reactive Energy counter."
	-- 1.3.6.1.4.1.28507.41.1.5.1.2.1.14
	::= { ets8801PowerEntry 14 }


ets8801ResetTime OBJECT-TYPE
	SYNTAX  Unsigned32
	UNITS	"s"
	MAX-ACCESS read-only
	STATUS  current
	DESCRIPTION
		"Time in seconds since last Energy
		Counter reset."
	-- 1.3.6.1.4.1.28507.41.1.5.1.2.1.15
	::= { ets8801PowerEntry 15 }


ets8801ForwEnergyActive OBJECT-TYPE
	SYNTAX  Unsigned32
	UNITS	"Wh"
	MAX-ACCESS read-only
	STATUS  current
	DESCRIPTION
		"Forward Active Energy counter."
	-- 1.3.6.1.4.1.28507.41.1.5.1.2.1.16
	::= { ets8801PowerEntry 16 }


ets8801ForwEnergyReactive OBJECT-TYPE
	SYNTAX  Unsigned32
	UNITS	"VARh"
	MAX-ACCESS read-only
	STATUS  current
	DESCRIPTION
		"Forward Reactive Energy counter."
	-- 1.3.6.1.4.1.28507.41.1.5.1.2.1.17
	::= { ets8801PowerEntry 17 }


ets8801ForwEnergyActiveResettable OBJECT-TYPE
	SYNTAX  Unsigned32
	UNITS	"Wh"
	MAX-ACCESS read-only
	STATUS  current
	DESCRIPTION
		"Resettable Forward Active Energy counter."
	-- 1.3.6.1.4.1.28507.41.1.5.1.2.1.18
	::= { ets8801PowerEntry 18 }


ets8801ForwEnergyReactiveResettable OBJECT-TYPE
	SYNTAX  Unsigned32
	UNITS	"VARh"
	MAX-ACCESS read-only
	STATUS  current
	DESCRIPTION
		"Resettable Forward Reactive Energy counter."
	-- 1.3.6.1.4.1.28507.41.1.5.1.2.1.19
	::= { ets8801PowerEntry 19 }


ets8801RevEnergyActive OBJECT-TYPE
	SYNTAX  Unsigned32
	UNITS	"Wh"
	MAX-ACCESS read-only
	STATUS  current
	DESCRIPTION
		"Reverse Active Energy counter."
	-- 1.3.6.1.4.1.28507.41.1.5.1.2.1.20
	::= { ets8801PowerEntry 20 }


ets8801RevEnergyReactive OBJECT-TYPE
	SYNTAX  Unsigned32
	UNITS	"VARh"
	MAX-ACCESS read-only
	STATUS  current
	DESCRIPTION
		"Reverse Reactive Energy counter."
	-- 1.3.6.1.4.1.28507.41.1.5.1.2.1.21
	::= { ets8801PowerEntry 21 }


ets8801RevEnergyActiveResettable OBJECT-TYPE
	SYNTAX  Unsigned32
	UNITS	"Wh"
	MAX-ACCESS read-only
	STATUS  current
	DESCRIPTION
		"Resettable Reverse Active Energy counter."
	-- 1.3.6.1.4.1.28507.41.1.5.1.2.1.22
	::= { ets8801PowerEntry 22 }


ets8801RevEnergyReactiveResettable OBJECT-TYPE
	SYNTAX  Unsigned32
	UNITS	"VARh"
	MAX-ACCESS read-only
	STATUS  current
	DESCRIPTION
		"Resettable Reverse Reactive Energy counter."
	-- 1.3.6.1.4.1.28507.41.1.5.1.2.1.23
	::= { ets8801PowerEntry 23 }


ets8801ETSPowerInfo OBJECT IDENTIFIER 
	-- 1.3.6.1.4.1.28507.41.1.5.11
	::= { ets8801IntSensors 11 }

ets8801PrimaryPowerAvail OBJECT-TYPE
	SYNTAX  INTEGER {
			void(0),
			power(1) }
	MAX-ACCESS read-only
	STATUS  current
	DESCRIPTION
		"not zero if primary Power available"
	-- 1.3.6.1.4.1.28507.41.1.5.11.1
	::= { ets8801ETSPowerInfo 1 }


ets8801ExtSensors OBJECT IDENTIFIER 
	-- 1.3.6.1.4.1.28507.41.1.6
	::= { ets8801Objects 6 }

ets8801SensorTable OBJECT-TYPE
	SYNTAX  SEQUENCE OF Ets8801SensorEntry
	MAX-ACCESS not-accessible
	STATUS  current
	DESCRIPTION ""
	-- 1.3.6.1.4.1.28507.41.1.6.1
	::= { ets8801ExtSensors 1 }


ets8801SensorEntry OBJECT-TYPE
	SYNTAX  Ets8801SensorEntry
	MAX-ACCESS not-accessible
	STATUS  current
	DESCRIPTION ""
	INDEX {
		ets8801SensorIndex }
	-- 1.3.6.1.4.1.28507.41.1.6.1.1
	::= { ets8801SensorTable 1 }


Ets8801SensorEntry ::= SEQUENCE {

	ets8801SensorIndex  Integer32,
	ets8801TempSensor   Integer32,
	ets8801HygroSensor  Integer32,
	ets8801InputSensor  INTEGER,
	ets8801AirPressure  Integer32,
	ets8801DewPoint     Integer32,
	ets8801DewPointDiff Integer32 }


ets8801SensorIndex OBJECT-TYPE
	SYNTAX  Integer32 (1..2)
	MAX-ACCESS read-only
	STATUS  current
	DESCRIPTION ""
	-- 1.3.6.1.4.1.28507.41.1.6.1.1.1
	::= { ets8801SensorEntry 1 }


ets8801TempSensor OBJECT-TYPE
	SYNTAX  Integer32
	UNITS	"0.1 degree Celsius"
	MAX-ACCESS read-only
	STATUS  current
	DESCRIPTION
		"actual temperature"
	-- 1.3.6.1.4.1.28507.41.1.6.1.1.2
	::= { ets8801SensorEntry 2 }


ets8801HygroSensor OBJECT-TYPE
	SYNTAX  Integer32
	UNITS	"0.1 percent humidity"
	MAX-ACCESS read-only
	STATUS  current
	DESCRIPTION
		"actual humidity"
	-- 1.3.6.1.4.1.28507.41.1.6.1.1.3
	::= { ets8801SensorEntry 3 }


ets8801InputSensor OBJECT-TYPE
	SYNTAX  INTEGER {
			off(0),
			on(1) }
	MAX-ACCESS read-only
	STATUS  current
	DESCRIPTION
		"logical state of input sensor"
	-- 1.3.6.1.4.1.28507.41.1.6.1.1.4
	::= { ets8801SensorEntry 4 }


-- Conformance
--

ets8801Conf OBJECT IDENTIFIER 
	-- 1.3.6.1.4.1.28507.41.2
	::= { gadsETS8801 2 }

ets8801AirPressure OBJECT-TYPE
	SYNTAX  Integer32
	UNITS	"1 hPA (hectopascal) ~ 1 milibar"
	MAX-ACCESS read-only
	STATUS  current
	DESCRIPTION
		"actual air pressure"
	-- 1.3.6.1.4.1.28507.41.1.6.1.1.5
	::= { ets8801SensorEntry 5 }


ets8801DewPoint OBJECT-TYPE
	SYNTAX  Integer32
	UNITS	"0.1 degree Celsius"
	MAX-ACCESS read-only
	STATUS  current
	DESCRIPTION
		"dew point for actual temperature and humidity"
	-- 1.3.6.1.4.1.28507.41.1.6.1.1.6
	::= { ets8801SensorEntry 6 }


ets8801DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.41.1.6.1.1.7
	::= { ets8801SensorEntry 7 }


-- Groups
--

ets8801Groups OBJECT IDENTIFIER 
	-- 1.3.6.1.4.1.28507.41.2.1
	::= { ets8801Conf 1 }

-- Compliance
--

ets8801Compls OBJECT IDENTIFIER 
	-- 1.3.6.1.4.1.28507.41.2.2
	::= { ets8801Conf 2 }


ets8801PrimaryPowerChangeEvt NOTIFICATION-TYPE
	OBJECTS {
		ets8801PrimaryPowerAvail,
		ets8801SecondaryPowerAvail}
	STATUS  current
	DESCRIPTION
		"Event is triggered when primary power
		changes"
	-- 1.3.6.1.4.1.28507.41.3.1
	::= { ets8801Events 1 }


ets8801SecondaryPowerChangeEvt NOTIFICATION-TYPE
	OBJECTS {
		ets8801PrimaryPowerAvail,
		ets8801SecondaryPowerAvail}
	STATUS  current
	DESCRIPTION
		"Event is triggered when secondary power
		changes"
	-- 1.3.6.1.4.1.28507.41.3.2
	::= { ets8801Events 2 }


ets8801PowerSelectEvt NOTIFICATION-TYPE
	OBJECTS {
		ets8801PowerLineSelected}
	STATUS  current
	DESCRIPTION
		"Event is triggered when power changes
		between primary and secondary"
	-- 1.3.6.1.4.1.28507.41.3.3
	::= { ets8801Events 3 }


ets8801TempEvtSen NOTIFICATION-TYPE
	OBJECTS {
		ets8801SensorIndex,
		ets8801TempSensor}
	STATUS  current
	DESCRIPTION
		"temperature limits exceeded"
	-- 1.3.6.1.4.1.28507.41.3.4
	::= { ets8801Events 4 }


ets8801HygroEvtSen NOTIFICATION-TYPE
	OBJECTS {
		ets8801SensorIndex,
		ets8801HygroSensor}
	STATUS  current
	DESCRIPTION
		"hygro limits exceeded"
	-- 1.3.6.1.4.1.28507.41.3.5
	::= { ets8801Events 5 }


ets8801InputEvtSen NOTIFICATION-TYPE
	OBJECTS {
		ets8801SensorIndex,
		ets8801InputSensor}
	STATUS  current
	DESCRIPTION
		"change of logical input sensor state"
	-- 1.3.6.1.4.1.28507.41.3.6
	::= { ets8801Events 6 }


ets8801LineAmperageEvt NOTIFICATION-TYPE
	OBJECTS {
		ets8801PowerIndex,
		ets8801PowerActive,
		ets8801Current,
		ets8801Voltage,
		ets8801Frequency,
		ets8801PowerApparent,
		ets8801PowerReactive}
	STATUS  current
	DESCRIPTION
		"Event is triggered when a measured
		current is crossing the entered limits"
	-- 1.3.6.1.4.1.28507.41.3.9
	::= { ets8801Events 9 }

ets8801BasicGroup OBJECT-GROUP
	OBJECTS {
		ets8801TrapCtrl,
		ets8801TrapIPIndex,
		ets8801TrapAddr,
		ets8801Buzzer,
		ets8801ActivePowerChan,
		ets8801PowerIndex,
		ets8801ChanStatus,
		ets8801AbsEnergyActive,
		ets8801PowerActive,
		ets8801Current,
		ets8801Voltage,
		ets8801Frequency,
		ets8801PowerFactor,
		ets8801Pangle,
		ets8801PowerApparent,
		ets8801PowerReactive,
		ets8801AbsEnergyReactive,
		ets8801AbsEnergyActiveResettable,
		ets8801AbsEnergyReactiveResettable,
		ets8801ResetTime,
		ets8801ForwEnergyActive,
		ets8801ForwEnergyReactive,
		ets8801ForwEnergyActiveResettable,
		ets8801ForwEnergyReactiveResettable,
		ets8801RevEnergyActive,
		ets8801RevEnergyReactive,
		ets8801RevEnergyActiveResettable,
		ets8801RevEnergyReactiveResettable,
		ets8801ResidualCurrent,
		ets8801PrimaryPowerAvail,
		ets8801SecondaryPowerAvail,
		ets8801LineSelectRequest,
		ets8801PowerLineSelected,
		ets8801SensorIndex,
		ets8801TempSensor,
		ets8801HygroSensor,
		ets8801InputSensor,
		ets8801AirPressure,
		ets8801DewPoint,
		ets8801DewPointDiff }
	STATUS  current
	DESCRIPTION
		"Basic objects."
	-- 1.3.6.1.4.1.28507.41.2.1.1
	::= { ets8801Groups 1 }

ets8801NotificationGroup NOTIFICATION-GROUP
	NOTIFICATIONS {
		ets8801PrimaryPowerChangeEvt,
		ets8801SecondaryPowerChangeEvt,
		ets8801PowerSelectEvt,
		ets8801LineAmperageEvt,
		ets8801TempEvtSen,
		ets8801HygroEvtSen,
		ets8801InputEvtSen,
		ets8801AirPressureEvtSen,
		ets8801DewPtDiffEvtSen }
	STATUS  current
	DESCRIPTION ""
	-- 1.3.6.1.4.1.28507.41.2.1.2
	::= { ets8801Groups 2 }

ets8801SecondaryPowerAvail OBJECT-TYPE
	SYNTAX  INTEGER {
			void(0),
			power(1) }
	MAX-ACCESS read-only
	STATUS  current
	DESCRIPTION
		"not zero if secondary Power available"
	-- 1.3.6.1.4.1.28507.41.1.5.11.2
	::= { ets8801ETSPowerInfo 2 }


ets8801LineSelectRequest OBJECT-TYPE
	SYNTAX  INTEGER {
			norequest(0),
			primary(1),
			secondary(2) }
	MAX-ACCESS read-write
	STATUS  current
	DESCRIPTION
		"sends change request to select line 1 (A) or 2 (B)"
	-- 1.3.6.1.4.1.28507.41.1.5.11.3
	::= { ets8801ETSPowerInfo 3 }


ets8801ResidualCurrent OBJECT-TYPE
	SYNTAX  Unsigned32
	UNITS	"mA"
	MAX-ACCESS read-only
	STATUS  current
	DESCRIPTION
		"Actual Residual Current on Power Channel.
		According Typ A IEC 60755. Only visible on
		models that support this feature."
	-- 1.3.6.1.4.1.28507.41.1.5.1.2.1.24
	::= { ets8801PowerEntry 24 }


ets8801PowerLineSelected OBJECT-TYPE
	SYNTAX  INTEGER {
			primary(1),
			secondary(2) }
	MAX-ACCESS read-only
	STATUS  current
	DESCRIPTION ""
	REFERENCE
		"primary (A) or secondary (B) line selected"
	-- 1.3.6.1.4.1.28507.41.1.5.11.4
	::= { ets8801ETSPowerInfo 4 }



ets8801AirPressureEvtSen NOTIFICATION-TYPE
	OBJECTS {
		ets8801SensorIndex,
		ets8801AirPressure}
	STATUS  current
	DESCRIPTION
		"Air Pressure limits exceeded

		"
	-- 1.3.6.1.4.1.28507.41.3.7
	::= { ets8801Events 7 }


ets8801DewPtDiffEvtSen NOTIFICATION-TYPE
	OBJECTS {
		ets8801SensorIndex,
		ets8801DewPointDiff}
	STATUS  current
	DESCRIPTION
		"Dew Point Difference limits exceeded"
	-- 1.3.6.1.4.1.28507.41.3.8
	::= { ets8801Events 8 }

END
