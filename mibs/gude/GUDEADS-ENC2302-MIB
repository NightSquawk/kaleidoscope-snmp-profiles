GUDEADS-ENC2302-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id: GUDEADS-ENC2302-MIB.txt 4232 2011-07-26 09:45:52Z petes1 $"
	-- 1.3.6.1.4.1.28507
	::= { enterprises 28507 }


enc2302SensorTable OBJECT-TYPE
	SYNTAX  SEQUENCE OF Enc2302SensorEntry
	MAX-ACCESS not-accessible
	STATUS  current
	DESCRIPTION ""
	-- 1.3.6.1.4.1.28507.70.1.6.1
	::= { enc2302ExtSensors 1 }


enc2302SensorEntry OBJECT-TYPE
	SYNTAX  Enc2302SensorEntry
	MAX-ACCESS not-accessible
	STATUS  current
	DESCRIPTION ""
	INDEX {
		enc2302SensorIndex }
	-- 1.3.6.1.4.1.28507.70.1.6.1.1
	::= { enc2302SensorTable 1 }


Enc2302SensorEntry ::= SEQUENCE {

	enc2302SensorIndex  Integer32,
	enc2302TempSensor   Integer32,
	enc2302HygroSensor  Integer32,
	enc2302InputSensor  INTEGER,
	enc2302AirPressure  Integer32,
	enc2302DewPoint     Integer32,
	enc2302DewPointDiff Integer32 }


enc2302SensorIndex OBJECT-TYPE
	SYNTAX  Integer32 (1..4)
	MAX-ACCESS read-only
	STATUS  current
	DESCRIPTION ""
	-- 1.3.6.1.4.1.28507.70.1.6.1.1.1
	::= { enc2302SensorEntry 1 }


enc2302TempSensor OBJECT-TYPE
	SYNTAX  Integer32
	UNITS	"0.1 degree Celsius"
	MAX-ACCESS read-only
	STATUS  current
	DESCRIPTION
		"actual temperature"
	-- 1.3.6.1.4.1.28507.70.1.6.1.1.2
	::= { enc2302SensorEntry 2 }


enc2302HygroSensor OBJECT-TYPE
	SYNTAX  Integer32
	UNITS	"0.1 percent humidity"
	MAX-ACCESS read-only
	STATUS  current
	DESCRIPTION
		"actual humidity"
	-- 1.3.6.1.4.1.28507.70.1.6.1.1.3
	::= { enc2302SensorEntry 3 }


enc2302InputSensor OBJECT-TYPE
	SYNTAX  INTEGER {
			off(0),
			on(1) }
	MAX-ACCESS read-only
	STATUS  current
	DESCRIPTION
		"logical state of input sensor"
	-- 1.3.6.1.4.1.28507.70.1.6.1.1.4
	::= { enc2302SensorEntry 4 }


enc2302AirPressure OBJECT-TYPE
	SYNTAX  Integer32
	UNITS	"1 hPA (hectopascal) ~ 1 milibar"
	MAX-ACCESS read-only
	STATUS  current
	DESCRIPTION
		"actual air pressure"
	-- 1.3.6.1.4.1.28507.70.1.6.1.1.5
	::= { enc2302SensorEntry 5 }


enc2302DewPoint OBJECT-TYPE
	SYNTAX  Integer32
	UNITS	"0.1 degree Celsius"
	MAX-ACCESS read-only
	STATUS  current
	DESCRIPTION
		"dew point for actual temperature and humidity"
	-- 1.3.6.1.4.1.28507.70.1.6.1.1.6
	::= { enc2302SensorEntry 6 }


enc2302DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.70.1.6.1.1.7
	::= { enc2302SensorEntry 7 }


gadsENC2302 OBJECT IDENTIFIER 
	-- 1.3.6.1.4.1.28507.70
	::= { gudeads 70 }

-- Scalars and Tables
--

enc2302Objects OBJECT IDENTIFIER 
	-- 1.3.6.1.4.1.28507.70.1
	::= { gadsENC2302 1 }

enc2302CommonConfig OBJECT IDENTIFIER 
	-- 1.3.6.1.4.1.28507.70.1.1
	::= { enc2302Objects 1 }

enc2302SNMPaccess OBJECT IDENTIFIER 
	-- 1.3.6.1.4.1.28507.70.1.1.1
	::= { enc2302CommonConfig 1 }

enc2302TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.70.1.1.1.1
	::= { enc2302SNMPaccess 1 }


enc2302TrapIPTable OBJECT-TYPE
	SYNTAX  SEQUENCE OF Enc2302TrapIPEntry
	MAX-ACCESS not-accessible
	STATUS  current
	DESCRIPTION
		"list of all Trap receiver"
	-- 1.3.6.1.4.1.28507.70.1.1.1.2
	::= { enc2302SNMPaccess 2 }


enc2302TrapIPEntry OBJECT-TYPE
	SYNTAX  Enc2302TrapIPEntry
	MAX-ACCESS not-accessible
	STATUS  current
	DESCRIPTION
		"an entry containing management
		informations regarding the list of trap
		receivers"
	INDEX {
		enc2302TrapIPIndex }
	-- 1.3.6.1.4.1.28507.70.1.1.1.2.1
	::= { enc2302TrapIPTable 1 }


Enc2302TrapIPEntry ::= SEQUENCE {

	enc2302TrapIPIndex Integer32,
	enc2302TrapAddr    OCTET STRING }


enc2302TrapIPIndex OBJECT-TYPE
	SYNTAX  Integer32 (1..8)
	MAX-ACCESS read-only
	STATUS  current
	DESCRIPTION
		"A unique value, greater than zero, for each receiver slot."
	-- 1.3.6.1.4.1.28507.70.1.1.1.2.1.1
	::= { enc2302TrapIPEntry 1 }


enc2302TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.70.1.1.1.2.1.2
	::= { enc2302TrapIPEntry 2 }


enc2302DeviceConfig OBJECT IDENTIFIER 
	-- 1.3.6.1.4.1.28507.70.1.2
	::= { enc2302Objects 2 }

enc2302IntActors OBJECT IDENTIFIER 
	-- 1.3.6.1.4.1.28507.70.1.3
	::= { enc2302Objects 3 }

enc2302relayports OBJECT IDENTIFIER 
	-- 1.3.6.1.4.1.28507.70.1.3.1
	::= { enc2302IntActors 1 }

enc2302portNumber OBJECT-TYPE
	SYNTAX  Integer32 (1..4)
	MAX-ACCESS read-only
	STATUS  current
	DESCRIPTION
		"The number of Relay Ports"
	-- 1.3.6.1.4.1.28507.70.1.3.1.1
	::= { enc2302relayports 1 }


-- the Interfaces table
-- The Interfaces table contains information on the entity's
-- interfaces.  Each sub-layer below the internetwork-layer
-- of a network interface is considered to be an interface.

enc2302portTable OBJECT-TYPE
	SYNTAX  SEQUENCE OF Enc2302portEntry
	MAX-ACCESS not-accessible
	STATUS  current
	DESCRIPTION
		"list of all EPC Relay Ports"
	-- 1.3.6.1.4.1.28507.70.1.3.1.2
	::= { enc2302relayports 2 }


enc2302portEntry OBJECT-TYPE
	SYNTAX  Enc2302portEntry
	MAX-ACCESS not-accessible
	STATUS  current
	DESCRIPTION
		"An entry containing management information applicable to a
		particular relay port."
	INDEX {
		enc2302PortIndex }
	-- 1.3.6.1.4.1.28507.70.1.3.1.2.1
	::= { enc2302portTable 1 }


Enc2302portEntry ::= SEQUENCE {

	enc2302PortIndex        Integer32,
	enc2302PortName         OCTET STRING,
	enc2302PortState        INTEGER,
	enc2302PortSwitchCount  Integer32,
	enc2302PortStartupMode  INTEGER,
	enc2302PortStartupDelay Integer32,
	enc2302PortRepowerTime  Integer32 }


enc2302PortIndex OBJECT-TYPE
	SYNTAX  Integer32 (1..4)
	MAX-ACCESS read-only
	STATUS  current
	DESCRIPTION
		"A unique value, greater than zero, for each Relay Port."
	-- 1.3.6.1.4.1.28507.70.1.3.1.2.1.1
	::= { enc2302portEntry 1 }


enc2302PortName OBJECT-TYPE
	SYNTAX  OCTET STRING (SIZE (0..15))
	MAX-ACCESS read-write
	STATUS  current
	DESCRIPTION
		"A textual string containing name of a Relay Port."
	-- 1.3.6.1.4.1.28507.70.1.3.1.2.1.2
	::= { enc2302portEntry 2 }


enc2302PortState OBJECT-TYPE
	SYNTAX  INTEGER {
			off(0),
			on(1) }
	MAX-ACCESS read-write
	STATUS  current
	DESCRIPTION
		"current state a Relay Port"
	-- 1.3.6.1.4.1.28507.70.1.3.1.2.1.3
	::= { enc2302portEntry 3 }


enc2302PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.70.1.3.1.2.1.4
	::= { enc2302portEntry 4 }


enc2302PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.70.1.3.1.2.1.5
	::= { enc2302portEntry 5 }


enc2302PortStartupDelay OBJECT-TYPE
	SYNTAX  Integer32
	UNITS	"seconds"
	MAX-ACCESS read-write
	STATUS  current
	DESCRIPTION
		"Delay in sec for startup action"
	DEFVAL { 0 }
	-- 1.3.6.1.4.1.28507.70.1.3.1.2.1.6
	::= { enc2302portEntry 6 }


enc2302PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.70.1.3.1.2.1.7
	::= { enc2302portEntry 7 }


enc2302ExtActors OBJECT IDENTIFIER 
	-- 1.3.6.1.4.1.28507.70.1.4
	::= { enc2302Objects 4 }

enc2302IntSensors OBJECT IDENTIFIER 
	-- 1.3.6.1.4.1.28507.70.1.5
	::= { enc2302Objects 5 }

enc2302ExtSensors OBJECT IDENTIFIER 
	-- 1.3.6.1.4.1.28507.70.1.6
	::= { enc2302Objects 6 }

enc2302Inputs OBJECT IDENTIFIER 
	-- 1.3.6.1.4.1.28507.70.1.5.6
	::= { enc2302IntSensors 6 }

enc2302ActiveInputs OBJECT-TYPE
	SYNTAX  Unsigned32 (1)
	MAX-ACCESS read-only
	STATUS  current
	DESCRIPTION
		"Number of suppported Input Channels."
	-- 1.3.6.1.4.1.28507.70.1.5.6.1
	::= { enc2302Inputs 1 }


enc2302InputTable OBJECT-TYPE
	SYNTAX  SEQUENCE OF Enc2302InputEntry
	MAX-ACCESS not-accessible
	STATUS  current
	DESCRIPTION ""
	-- 1.3.6.1.4.1.28507.70.1.5.6.2
	::= { enc2302Inputs 2 }


enc2302InputEntry OBJECT-TYPE
	SYNTAX  Enc2302InputEntry
	MAX-ACCESS not-accessible
	STATUS  current
	DESCRIPTION ""
	INDEX {
		enc2302InputIndex }
	-- 1.3.6.1.4.1.28507.70.1.5.6.2.1
	::= { enc2302InputTable 1 }


Enc2302InputEntry ::= SEQUENCE {

	enc2302InputIndex Integer32,
	enc2302Input      INTEGER }


enc2302InputIndex OBJECT-TYPE
	SYNTAX  Integer32 (1..8)
	MAX-ACCESS read-only
	STATUS  current
	DESCRIPTION ""
	-- 1.3.6.1.4.1.28507.70.1.5.6.2.1.1
	::= { enc2302InputEntry 1 }


enc2302Input OBJECT-TYPE
	SYNTAX  INTEGER {
			lo(0),
			hi(1) }
	MAX-ACCESS read-only
	STATUS  current
	DESCRIPTION
		"Input state of device"
	-- 1.3.6.1.4.1.28507.70.1.5.6.2.1.2
	::= { enc2302InputEntry 2 }


-- Conformance
--

enc2302Conf OBJECT IDENTIFIER 
	-- 1.3.6.1.4.1.28507.70.2
	::= { gadsENC2302 2 }

-- Groups
--

enc2302Groups OBJECT IDENTIFIER 
	-- 1.3.6.1.4.1.28507.70.2.1
	::= { enc2302Conf 1 }

-- Compliance
--

enc2302Compls OBJECT IDENTIFIER 
	-- 1.3.6.1.4.1.28507.70.2.2
	::= { enc2302Conf 2 }

enc2302BasicGroup OBJECT-GROUP
	OBJECTS {
		enc2302TrapCtrl,
		enc2302TrapIPIndex,
		enc2302TrapAddr,
		enc2302portNumber,
		enc2302PortIndex,
		enc2302PortName,
		enc2302PortState,
		enc2302PortSwitchCount,
		enc2302PortStartupMode,
		enc2302PortStartupDelay,
		enc2302PortRepowerTime,
		enc2302ActiveInputs,
		enc2302InputIndex,
		enc2302Input,
		enc2302SensorIndex,
		enc2302TempSensor,
		enc2302HygroSensor,
		enc2302InputSensor,
		enc2302AirPressure,
		enc2302DewPoint,
		enc2302DewPointDiff }
	STATUS  current
	DESCRIPTION
		"Basic objects."
	-- 1.3.6.1.4.1.28507.70.2.1.1
	::= { enc2302Groups 1 }

enc2302NotificationGroup NOTIFICATION-GROUP
	NOTIFICATIONS {
		enc2302SwitchEvtPort,
		enc2302InputEvt,
		enc2302TempEvtSen,
		enc2302HygroEvtSen,
		enc2302InputEvtSen,
		enc2302AirPressureEvtSen,
		enc2302DewPtDiffEvtSen }
	STATUS  current
	DESCRIPTION ""
	-- 1.3.6.1.4.1.28507.70.2.1.2
	::= { enc2302Groups 2 }

-- Notification Types
--

events OBJECT IDENTIFIER 
	-- 1.3.6.1.4.1.28507.70.3
	::= { gadsENC2302 3 }


enc2302InputEvt NOTIFICATION-TYPE
	OBJECTS {
		enc2302InputIndex,
		enc2302Input}
	STATUS  current
	DESCRIPTION
		"Change of device input."
	-- 1.3.6.1.4.1.28507.70.3.2
	::= { events 2 }


enc2302HygroEvtSen NOTIFICATION-TYPE
	OBJECTS {
		enc2302SensorIndex,
		enc2302HygroSensor}
	STATUS  current
	DESCRIPTION
		"hygro limits exceeded"
	-- 1.3.6.1.4.1.28507.70.3.4
	::= { events 4 }


enc2302InputEvtSen NOTIFICATION-TYPE
	OBJECTS {
		enc2302SensorIndex,
		enc2302InputSensor}
	STATUS  current
	DESCRIPTION
		"change of logical input sensor state"
	-- 1.3.6.1.4.1.28507.70.3.5
	::= { events 5 }


enc2302AirPressureEvtSen NOTIFICATION-TYPE
	OBJECTS {
		enc2302SensorIndex,
		enc2302AirPressure}
	STATUS  current
	DESCRIPTION
		"Air Pressure limits exceeded

		"
	-- 1.3.6.1.4.1.28507.70.3.6
	::= { events 6 }


enc2302DewPtDiffEvtSen NOTIFICATION-TYPE
	OBJECTS {
		enc2302SensorIndex,
		enc2302DewPointDiff}
	STATUS  current
	DESCRIPTION
		"Dew Point Difference limits exceeded"
	-- 1.3.6.1.4.1.28507.70.3.7
	::= { events 7 }


enc2302TempEvtSen NOTIFICATION-TYPE
	OBJECTS {
		enc2302SensorIndex,
		enc2302TempSensor}
	STATUS  current
	DESCRIPTION
		"temperature limits exceeded"
	-- 1.3.6.1.4.1.28507.70.3.3
	::= { events 3 }


enc2302SwitchEvtPort NOTIFICATION-TYPE
	OBJECTS {
		enc2302PortIndex,
		enc2302PortName,
		enc2302PortState,
		enc2302PortSwitchCount}
	STATUS  current
	DESCRIPTION
		"Event is triggered when a port is switched"
	-- 1.3.6.1.4.1.28507.70.3.1
	::= { events 1 }

END
