GUDEADS-ENC2111-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


enc2111POE OBJECT-TYPE
	SYNTAX  Integer32 (0..1)
	UNITS	"0 = no POE, 1 = POE available"
	MAX-ACCESS read-only
	STATUS  current
	DESCRIPTION
		"signals POE availability"
	-- 1.3.6.1.4.1.28507.60.1.5.10
	::= { enc2111IntSensors 10 }


gadsENC2111 OBJECT IDENTIFIER 
	-- 1.3.6.1.4.1.28507.60
	::= { gudeads 60 }

-- Notification Types
--

events OBJECT IDENTIFIER 
	-- 1.3.6.1.4.1.28507.60.3
	::= { gadsENC2111 3 }

-- Scalars and Tables
--

enc2111Objects OBJECT IDENTIFIER 
	-- 1.3.6.1.4.1.28507.60.1
	::= { gadsENC2111 1 }

enc2111CommonConfig OBJECT IDENTIFIER 
	-- 1.3.6.1.4.1.28507.60.1.1
	::= { enc2111Objects 1 }

enc2111SNMPaccess OBJECT IDENTIFIER 
	-- 1.3.6.1.4.1.28507.60.1.1.1
	::= { enc2111CommonConfig 1 }

enc2111TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.60.1.1.1.1
	::= { enc2111SNMPaccess 1 }


enc2111TrapIPTable OBJECT-TYPE
	SYNTAX  SEQUENCE OF Enc2111TrapIPEntry
	MAX-ACCESS not-accessible
	STATUS  current
	DESCRIPTION
		"list of all Trap receiver"
	-- 1.3.6.1.4.1.28507.60.1.1.1.2
	::= { enc2111SNMPaccess 2 }


enc2111TrapIPEntry OBJECT-TYPE
	SYNTAX  Enc2111TrapIPEntry
	MAX-ACCESS not-accessible
	STATUS  current
	DESCRIPTION
		"an entry containing management
		informations regarding the list of trap
		receivers"
	INDEX {
		enc2111TrapIPIndex }
	-- 1.3.6.1.4.1.28507.60.1.1.1.2.1
	::= { enc2111TrapIPTable 1 }


Enc2111TrapIPEntry ::= SEQUENCE {

	enc2111TrapIPIndex Integer32,
	enc2111TrapAddr    OCTET STRING }


enc2111TrapIPIndex OBJECT-TYPE
	SYNTAX  Integer32 (1..8)
	MAX-ACCESS read-only
	STATUS  current
	DESCRIPTION
		"A unique value, greater than zero, for each receiver slot."
	-- 1.3.6.1.4.1.28507.60.1.1.1.2.1.1
	::= { enc2111TrapIPEntry 1 }


enc2111TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.60.1.1.1.2.1.2
	::= { enc2111TrapIPEntry 2 }


enc2111DeviceConfig OBJECT IDENTIFIER 
	-- 1.3.6.1.4.1.28507.60.1.2
	::= { enc2111Objects 2 }

enc2111IntActors OBJECT IDENTIFIER 
	-- 1.3.6.1.4.1.28507.60.1.3
	::= { enc2111Objects 3 }

enc2111relayports OBJECT IDENTIFIER 
	-- 1.3.6.1.4.1.28507.60.1.3.1
	::= { enc2111IntActors 1 }

enc2111portNumber OBJECT-TYPE
	SYNTAX  Integer32 (1..12)
	MAX-ACCESS read-only
	STATUS  current
	DESCRIPTION
		"The number of Relay Ports"
	-- 1.3.6.1.4.1.28507.60.1.3.1.1
	::= { enc2111relayports 1 }


-- the Interfaces table
-- The Interfaces table contains information on the entity's
-- interfaces.  Each sub-layer below the internetwork-layer
-- of a network interface is considered to be an interface.

enc2111portTable OBJECT-TYPE
	SYNTAX  SEQUENCE OF Enc2111portEntry
	MAX-ACCESS not-accessible
	STATUS  current
	DESCRIPTION
		"list of all EPC Relay Ports"
	-- 1.3.6.1.4.1.28507.60.1.3.1.2
	::= { enc2111relayports 2 }


enc2111portEntry OBJECT-TYPE
	SYNTAX  Enc2111portEntry
	MAX-ACCESS not-accessible
	STATUS  current
	DESCRIPTION
		"An entry containing management information applicable to a
		particular relay port."
	INDEX {
		enc2111PortIndex }
	-- 1.3.6.1.4.1.28507.60.1.3.1.2.1
	::= { enc2111portTable 1 }


Enc2111portEntry ::= SEQUENCE {

	enc2111PortIndex        Integer32,
	enc2111PortName         OCTET STRING,
	enc2111PortState        INTEGER,
	enc2111PortSwitchCount  Integer32,
	enc2111PortStartupMode  INTEGER,
	enc2111PortStartupDelay Integer32,
	enc2111PortRepowerTime  Integer32 }


enc2111PortIndex OBJECT-TYPE
	SYNTAX  Integer32 (1..4)
	MAX-ACCESS read-only
	STATUS  current
	DESCRIPTION
		"A unique value, greater than zero, for each Relay Port."
	-- 1.3.6.1.4.1.28507.60.1.3.1.2.1.1
	::= { enc2111portEntry 1 }


enc2111PortName OBJECT-TYPE
	SYNTAX  OCTET STRING (SIZE (0..15))
	MAX-ACCESS read-write
	STATUS  current
	DESCRIPTION
		"A textual string containing name of a Relay Port."
	-- 1.3.6.1.4.1.28507.60.1.3.1.2.1.2
	::= { enc2111portEntry 2 }


enc2111PortState OBJECT-TYPE
	SYNTAX  INTEGER {
			off(0),
			on(1) }
	MAX-ACCESS read-write
	STATUS  current
	DESCRIPTION
		"current state of a Relay Port"
	-- 1.3.6.1.4.1.28507.60.1.3.1.2.1.3
	::= { enc2111portEntry 3 }


enc2111PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.60.1.3.1.2.1.4
	::= { enc2111portEntry 4 }


enc2111PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.60.1.3.1.2.1.5
	::= { enc2111portEntry 5 }


enc2111PortStartupDelay OBJECT-TYPE
	SYNTAX  Integer32
	UNITS	"seconds"
	MAX-ACCESS read-write
	STATUS  current
	DESCRIPTION
		"Delay in sec for startup action"
	DEFVAL { 0 }
	-- 1.3.6.1.4.1.28507.60.1.3.1.2.1.6
	::= { enc2111portEntry 6 }


enc2111PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.60.1.3.1.2.1.7
	::= { enc2111portEntry 7 }


enc2111ExtActors OBJECT IDENTIFIER 
	-- 1.3.6.1.4.1.28507.60.1.4
	::= { enc2111Objects 4 }

enc2111IntSensors OBJECT IDENTIFIER 
	-- 1.3.6.1.4.1.28507.60.1.5
	::= { enc2111Objects 5 }

enc2111VoltageInfo OBJECT IDENTIFIER 
	-- 1.3.6.1.4.1.28507.60.1.5.7
	::= { enc2111IntSensors 7 }

enc2111ExtSensors OBJECT IDENTIFIER 
	-- 1.3.6.1.4.1.28507.60.1.6
	::= { enc2111Objects 6 }

enc2111SensorTable OBJECT-TYPE
	SYNTAX  SEQUENCE OF Enc2111SensorEntry
	MAX-ACCESS not-accessible
	STATUS  current
	DESCRIPTION ""
	-- 1.3.6.1.4.1.28507.60.1.6.1
	::= { enc2111ExtSensors 1 }


enc2111SensorEntry OBJECT-TYPE
	SYNTAX  Enc2111SensorEntry
	MAX-ACCESS not-accessible
	STATUS  current
	DESCRIPTION ""
	INDEX {
		enc2111SensorIndex }
	-- 1.3.6.1.4.1.28507.60.1.6.1.1
	::= { enc2111SensorTable 1 }


Enc2111SensorEntry ::= SEQUENCE {

	enc2111SensorIndex  Integer32,
	enc2111TempSensor   Integer32,
	enc2111HygroSensor  Integer32,
	enc2111InputSensor  INTEGER,
	enc2111AirPressure  Integer32,
	enc2111DewPoint     Integer32,
	enc2111DewPointDiff Integer32 }


enc2111SensorIndex OBJECT-TYPE
	SYNTAX  Integer32 (1..4)
	MAX-ACCESS read-only
	STATUS  current
	DESCRIPTION ""
	-- 1.3.6.1.4.1.28507.60.1.6.1.1.1
	::= { enc2111SensorEntry 1 }


enc2111State3V OBJECT-TYPE
	SYNTAX  INTEGER {
			on(1),
			error(3) }
	MAX-ACCESS read-only
	STATUS  current
	DESCRIPTION
		"Show state of internal 3.3V"
	-- 1.3.6.1.4.1.28507.60.1.5.7.2
	::= { enc2111VoltageInfo 2 }


enc2111TempSensor OBJECT-TYPE
	SYNTAX  Integer32
	UNITS	"0.1 degree Celsius"
	MAX-ACCESS read-only
	STATUS  current
	DESCRIPTION
		"actual temperature"
	-- 1.3.6.1.4.1.28507.60.1.6.1.1.2
	::= { enc2111SensorEntry 2 }


enc2111HygroSensor OBJECT-TYPE
	SYNTAX  Integer32
	UNITS	"0.1 percent humidity"
	MAX-ACCESS read-only
	STATUS  current
	DESCRIPTION
		"actual humidity"
	-- 1.3.6.1.4.1.28507.60.1.6.1.1.3
	::= { enc2111SensorEntry 3 }


enc2111InputSensor OBJECT-TYPE
	SYNTAX  INTEGER {
			off(0),
			on(1) }
	MAX-ACCESS read-only
	STATUS  current
	DESCRIPTION
		"logical state of input sensor"
	-- 1.3.6.1.4.1.28507.60.1.6.1.1.4
	::= { enc2111SensorEntry 4 }


-- Conformance
--

enc2111Conf OBJECT IDENTIFIER 
	-- 1.3.6.1.4.1.28507.60.2
	::= { gadsENC2111 2 }

-- Groups
--

enc2111Groups OBJECT IDENTIFIER 
	-- 1.3.6.1.4.1.28507.60.2.1
	::= { enc2111Conf 1 }

-- Compliance
--

enc2111Compls OBJECT IDENTIFIER 
	-- 1.3.6.1.4.1.28507.60.2.2
	::= { enc2111Conf 2 }

enc2111BasicGroup OBJECT-GROUP
	OBJECTS {
		enc2111TrapCtrl,
		enc2111TrapIPIndex,
		enc2111TrapAddr,
		enc2111portNumber,
		enc2111PortIndex,
		enc2111PortName,
		enc2111PortState,
		enc2111PortSwitchCount,
		enc2111PortStartupMode,
		enc2111PortStartupDelay,
		enc2111PortRepowerTime,
		enc2111ActiveInputs,
		enc2111InputIndex,
		enc2111Input,
		enc2111State12V,
		enc2111State3V,
		enc2111POE,
		enc2111SensorIndex,
		enc2111TempSensor,
		enc2111HygroSensor,
		enc2111InputSensor,
		enc2111AirPressure,
		enc2111DewPoint,
		enc2111DewPointDiff }
	STATUS  current
	DESCRIPTION
		"Basic objects."
	-- 1.3.6.1.4.1.28507.60.2.1.1
	::= { enc2111Groups 1 }

enc2111NotificationGroup NOTIFICATION-GROUP
	NOTIFICATIONS {
		enc2111SwitchEvtPort,
		enc2111InputEvt,
		enc2111TempEvtSen,
		enc2111HygroEvtSen,
		enc2111InputEvtSen,
		enc2111AirPressureEvtSen,
		enc2111DewPtDiffEvtSen,
		enc2111POEEvt }
	STATUS  current
	DESCRIPTION ""
	-- 1.3.6.1.4.1.28507.60.2.1.2
	::= { enc2111Groups 2 }

enc2111Inputs OBJECT IDENTIFIER 
	-- 1.3.6.1.4.1.28507.60.1.5.6
	::= { enc2111IntSensors 6 }

enc2111InputEntry OBJECT-TYPE
	SYNTAX  Enc2111InputEntry
	MAX-ACCESS not-accessible
	STATUS  current
	DESCRIPTION ""
	INDEX {
		enc2111InputIndex }
	-- 1.3.6.1.4.1.28507.60.1.5.6.2.1
	::= { enc2111InputTable 1 }


Enc2111InputEntry ::= SEQUENCE {

	enc2111InputIndex Integer32,
	enc2111Input      INTEGER }


enc2111Input OBJECT-TYPE
	SYNTAX  INTEGER {
			lo(0),
			hi(1) }
	MAX-ACCESS read-only
	STATUS  current
	DESCRIPTION
		"Input state of device"
	-- 1.3.6.1.4.1.28507.60.1.5.6.2.1.2
	::= { enc2111InputEntry 2 }


enc2111ActiveInputs OBJECT-TYPE
	SYNTAX  Unsigned32 (1..12)
	MAX-ACCESS read-only
	STATUS  current
	DESCRIPTION
		"Number of suppported Input Channels."
	-- 1.3.6.1.4.1.28507.60.1.5.6.1
	::= { enc2111Inputs 1 }


enc2111InputTable OBJECT-TYPE
	SYNTAX  SEQUENCE OF Enc2111InputEntry
	MAX-ACCESS not-accessible
	STATUS  current
	DESCRIPTION ""
	-- 1.3.6.1.4.1.28507.60.1.5.6.2
	::= { enc2111Inputs 2 }


enc2111InputIndex OBJECT-TYPE
	SYNTAX  Integer32 (1..12)
	MAX-ACCESS read-only
	STATUS  current
	DESCRIPTION ""
	-- 1.3.6.1.4.1.28507.60.1.5.6.2.1.1
	::= { enc2111InputEntry 1 }


enc2111State12V OBJECT-TYPE
	SYNTAX  INTEGER {
			off(0),
			low(1),
			high(2),
			error(3) }
	MAX-ACCESS read-only
	STATUS  current
	DESCRIPTION
		"Show state of internal 12V"
	-- 1.3.6.1.4.1.28507.60.1.5.7.1
	::= { enc2111VoltageInfo 1 }


enc2111AirPressure OBJECT-TYPE
	SYNTAX  Integer32
	UNITS	"1 hPA (hectopascal) ~ 1 milibar"
	MAX-ACCESS read-only
	STATUS  current
	DESCRIPTION
		"actual air pressure"
	-- 1.3.6.1.4.1.28507.60.1.6.1.1.5
	::= { enc2111SensorEntry 5 }


enc2111DewPoint OBJECT-TYPE
	SYNTAX  Integer32
	UNITS	"0.1 degree Celsius"
	MAX-ACCESS read-only
	STATUS  current
	DESCRIPTION
		"dew point for actual temperature and humidity"
	-- 1.3.6.1.4.1.28507.60.1.6.1.1.6
	::= { enc2111SensorEntry 6 }


enc2111DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.60.1.6.1.1.7
	::= { enc2111SensorEntry 7 }



enc2111POEEvt NOTIFICATION-TYPE
	OBJECTS {
		enc2111POE}
	STATUS  current
	DESCRIPTION
		"Power over Ethernet changed"
	-- 1.3.6.1.4.1.28507.60.3.8
	::= { events 8 }


enc2111InputEvt NOTIFICATION-TYPE
	OBJECTS {
		enc2111InputIndex,
		enc2111Input}
	STATUS  current
	DESCRIPTION
		"Change of device input."
	-- 1.3.6.1.4.1.28507.60.3.2
	::= { events 2 }


enc2111HygroEvtSen NOTIFICATION-TYPE
	OBJECTS {
		enc2111SensorIndex,
		enc2111HygroSensor}
	STATUS  current
	DESCRIPTION
		"hygro limits exceeded"
	-- 1.3.6.1.4.1.28507.60.3.4
	::= { events 4 }


enc2111InputEvtSen NOTIFICATION-TYPE
	OBJECTS {
		enc2111SensorIndex,
		enc2111InputSensor}
	STATUS  current
	DESCRIPTION
		"change of logical input sensor state"
	-- 1.3.6.1.4.1.28507.60.3.5
	::= { events 5 }


enc2111AirPressureEvtSen NOTIFICATION-TYPE
	OBJECTS {
		enc2111SensorIndex,
		enc2111AirPressure}
	STATUS  current
	DESCRIPTION
		"Air Pressure limits exceeded

		"
	-- 1.3.6.1.4.1.28507.60.3.6
	::= { events 6 }


enc2111DewPtDiffEvtSen NOTIFICATION-TYPE
	OBJECTS {
		enc2111SensorIndex,
		enc2111DewPointDiff}
	STATUS  current
	DESCRIPTION
		"Dew Point Difference limits exceeded"
	-- 1.3.6.1.4.1.28507.60.3.7
	::= { events 7 }


enc2111TempEvtSen NOTIFICATION-TYPE
	OBJECTS {
		enc2111SensorIndex,
		enc2111TempSensor}
	STATUS  current
	DESCRIPTION
		"temperature limits exceeded"
	-- 1.3.6.1.4.1.28507.60.3.3
	::= { events 3 }


enc2111SwitchEvtPort NOTIFICATION-TYPE
	OBJECTS {
		enc2111PortIndex,
		enc2111PortName,
		enc2111PortState,
		enc2111PortSwitchCount}
	STATUS  current
	DESCRIPTION
		"Event is triggered when a port is switched"
	-- 1.3.6.1.4.1.28507.60.3.1
	::= { events 1 }

END
