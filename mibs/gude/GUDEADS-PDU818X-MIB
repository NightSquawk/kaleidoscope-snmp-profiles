GUDEADS-PDU818X-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


-- Notification Types
--

events OBJECT IDENTIFIER 
	-- 1.3.6.1.4.1.28507.35.0
	::= { gadsPDU818X 0 }

pdu818XPowerIndex OBJECT-TYPE
	SYNTAX  Integer32 (1..4)
	MAX-ACCESS not-accessible
	STATUS  current
	DESCRIPTION
		"Index of Power Channel entries"
	-- 1.3.6.1.4.1.28507.35.1.5.1.2.1.1
	::= { pdu818XPowerEntry 1 }


pdu818XTrapIPTable OBJECT-TYPE
	SYNTAX  SEQUENCE OF Epc8TrapIPEntry
	MAX-ACCESS not-accessible
	STATUS  current
	DESCRIPTION
		"list of all Trap receiver"
	-- 1.3.6.1.4.1.28507.35.1.1.1.2
	::= { pdu818XSNMPaccess 2 }


pdu818XCurrent OBJECT-TYPE
	SYNTAX  Unsigned32
	UNITS
		"mA"
	MAX-ACCESS read-only
	STATUS  current
	DESCRIPTION
		"Actual Curent on Power Channel."
	-- 1.3.6.1.4.1.28507.35.1.5.1.2.1.5
	::= { pdu818XPowerEntry 5 }


gadsPDU818X OBJECT IDENTIFIER 
	-- 1.3.6.1.4.1.28507.35
	::= { gudeads 35 }

pdu818XVoltage OBJECT-TYPE
	SYNTAX  Unsigned32
	UNITS
		"V"
	MAX-ACCESS read-only
	STATUS  current
	DESCRIPTION
		"Actual Voltage on Power Channel"
	-- 1.3.6.1.4.1.28507.35.1.5.1.2.1.6
	::= { pdu818XPowerEntry 6 }


pdu818XTrapIPEntry OBJECT-TYPE
	SYNTAX  Epc8TrapIPEntry
	MAX-ACCESS not-accessible
	STATUS  current
	DESCRIPTION
		"an entry containing management
		informations regarding the list of trap
		receivers"
	INDEX {
		pdu818XTrapIPIndex }
	-- 1.3.6.1.4.1.28507.35.1.1.1.2.1
	::= { pdu818XTrapIPTable 1 }


Epc8TrapIPEntry ::= SEQUENCE {

	pdu818XTrapIPIndex Integer32,
	pdu818XTrapAddr    OCTET STRING }


pdu818XPowerTable OBJECT-TYPE
	SYNTAX  SEQUENCE OF Pdu818XPowerEntry
	MAX-ACCESS not-accessible
	STATUS  current
	DESCRIPTION
		"All available Channel Interfaces."
	-- 1.3.6.1.4.1.28507.35.1.5.1.2
	::= { pdu818XPowerChan 2 }


pdu818XPowerEntry OBJECT-TYPE
	SYNTAX  Pdu818XPowerEntry
	MAX-ACCESS not-accessible
	STATUS  current
	DESCRIPTION
		"An entry containing management information
		applicable to a particular Power Channel."
	INDEX {
		pdu818XPowerIndex }
	-- 1.3.6.1.4.1.28507.35.1.5.1.2.1
	::= { pdu818XPowerTable 1 }


Pdu818XPowerEntry ::= SEQUENCE {

	pdu818XPowerIndex   Integer32,
	pdu818XChanStatus   Integer32,
	pdu818XEnergyActive Unsigned32,
	pdu818XPowerActive  Unsigned32,
	pdu818XCurrent      Unsigned32,
	pdu818XVoltage      Unsigned32 }


pdu818XTrapIPIndex OBJECT-TYPE
	SYNTAX  Integer32 (1..8)
	MAX-ACCESS not-accessible
	STATUS  current
	DESCRIPTION
		"A unique value, greater than zero, for each receiver slot."
	-- 1.3.6.1.4.1.28507.35.1.1.1.2.1.1
	::= { pdu818XTrapIPEntry 1 }


pdu818XDeviceConfig OBJECT IDENTIFIER 
	-- 1.3.6.1.4.1.28507.35.1.2
	::= { pdu818XObjects 2 }

pdu818XExtActors OBJECT IDENTIFIER 
	-- 1.3.6.1.4.1.28507.35.1.4
	::= { pdu818XObjects 4 }

pdu818XExtSensors OBJECT IDENTIFIER 
	-- 1.3.6.1.4.1.28507.35.1.6
	::= { pdu818XObjects 6 }

pdu818XSensorTable OBJECT-TYPE
	SYNTAX  SEQUENCE OF Pdu818XSensorEntry
	MAX-ACCESS not-accessible
	STATUS  current
	DESCRIPTION ""
	-- 1.3.6.1.4.1.28507.35.1.6.1
	::= { pdu818XExtSensors 1 }


pdu818XSensorEntry OBJECT-TYPE
	SYNTAX  Pdu818XSensorEntry
	MAX-ACCESS not-accessible
	STATUS  current
	DESCRIPTION ""
	INDEX {
		pdu818XSensorIndex }
	-- 1.3.6.1.4.1.28507.35.1.6.1.1
	::= { pdu818XSensorTable 1 }


Pdu818XSensorEntry ::= SEQUENCE {

	pdu818XSensorIndex Integer32,
	pdu818XTempSensor  Integer32,
	pdu818XHygroSensor Integer32 }



pdu818XPowerDataEvt1 NOTIFICATION-TYPE
	OBJECTS {
		pdu818XEnergyActive,
		pdu818XPowerActive,
		pdu818XCurrent,
		pdu818XVoltage}
	STATUS  current
	DESCRIPTION
		"Event is triggered when a data
		for a Power Channel is incoming"
	-- 1.3.6.1.4.1.28507.35.0.1
	::= { events 1 }


pdu818XPowerDataEvt2 NOTIFICATION-TYPE
	OBJECTS {
		pdu818XEnergyActive,
		pdu818XPowerActive,
		pdu818XCurrent,
		pdu818XVoltage}
	STATUS  current
	DESCRIPTION
		"Event is triggered when a data
		for a Power Channel is incoming"
	-- 1.3.6.1.4.1.28507.35.0.2
	::= { events 2 }


pdu818XPowerDataEvt3 NOTIFICATION-TYPE
	OBJECTS {
		pdu818XEnergyActive,
		pdu818XPowerActive,
		pdu818XCurrent,
		pdu818XVoltage}
	STATUS  current
	DESCRIPTION
		"Event is triggered when a data
		for a Power Channel is incoming"
	-- 1.3.6.1.4.1.28507.35.0.3
	::= { events 3 }


pdu818XPowerDataEvt4 NOTIFICATION-TYPE
	OBJECTS {
		pdu818XEnergyActive,
		pdu818XPowerActive,
		pdu818XCurrent,
		pdu818XVoltage}
	STATUS  current
	DESCRIPTION
		"Event is triggered when a data
		for a Power Channel is incoming"
	-- 1.3.6.1.4.1.28507.35.0.4
	::= { events 4 }

pdu818XSensorIndex OBJECT-TYPE
	SYNTAX  Integer32 (1)
	MAX-ACCESS not-accessible
	STATUS  current
	DESCRIPTION ""
	-- 1.3.6.1.4.1.28507.35.1.6.1.1.1
	::= { pdu818XSensorEntry 1 }


pdu818XTempSensor OBJECT-TYPE
	SYNTAX  Integer32
	UNITS
		"10th of degree Celsius"
	MAX-ACCESS read-only
	STATUS  current
	DESCRIPTION
		"actual temperature,  a value of -9999 indicates
		that data is not available"
	-- 1.3.6.1.4.1.28507.35.1.6.1.1.2
	::= { pdu818XSensorEntry 2 }


pdu818XHygroSensor OBJECT-TYPE
	SYNTAX  Integer32
	UNITS
		"10th of percentage humidity"
	MAX-ACCESS read-only
	STATUS  current
	DESCRIPTION
		"actual humidity,  a value of -9999 indicates
		that data is not available"
	-- 1.3.6.1.4.1.28507.35.1.6.1.1.3
	::= { pdu818XSensorEntry 3 }


pdu818XSNMPaccess OBJECT IDENTIFIER 
	-- 1.3.6.1.4.1.28507.35.1.1.1
	::= { pdu818XCommonConfig 1 }

pdu818XTrapCtrl OBJECT-TYPE
	SYNTAX  Integer32 (0..2)
	MAX-ACCESS read-write
	STATUS  current
	DESCRIPTION
		"0 = off
		1 = Ver. 1
		2 = Ver. 2c"
	-- 1.3.6.1.4.1.28507.35.1.1.1.1
	::= { pdu818XSNMPaccess 1 }


-- Scalars and Tables
--

pdu818XObjects OBJECT IDENTIFIER 
	-- 1.3.6.1.4.1.28507.35.1
	::= { gadsPDU818X 1 }

pdu818XCommonConfig OBJECT IDENTIFIER 
	-- 1.3.6.1.4.1.28507.35.1.1
	::= { pdu818XObjects 1 }

pdu818XPowerChan OBJECT IDENTIFIER 
	-- 1.3.6.1.4.1.28507.35.1.5.1
	::= { pdu818XIntSensors 1 }

pdu818XIntActors OBJECT IDENTIFIER 
	-- 1.3.6.1.4.1.28507.35.1.3
	::= { pdu818XObjects 3 }

pdu818XChanStatus OBJECT-TYPE
	SYNTAX  Integer32 (0..1)
	MAX-ACCESS read-only
	STATUS  current
	DESCRIPTION
		"0 = data not active, 1 = data valid"
	-- 1.3.6.1.4.1.28507.35.1.5.1.2.1.2
	::= { pdu818XPowerEntry 2 }


pdu818XActivePowerChan OBJECT-TYPE
	SYNTAX  Unsigned32 (1..2)
	MAX-ACCESS read-only
	STATUS  current
	DESCRIPTION
		"Number of suppported Power Channels."
	-- 1.3.6.1.4.1.28507.35.1.5.1.1
	::= { pdu818XPowerChan 1 }


pdu818XEnergyActive OBJECT-TYPE
	SYNTAX  Unsigned32
	UNITS
		"Wh"
	MAX-ACCESS read-only
	STATUS  current
	DESCRIPTION
		"Total accumulated Active Energy of Power Channel."
	-- 1.3.6.1.4.1.28507.35.1.5.1.2.1.3
	::= { pdu818XPowerEntry 3 }


pdu818XTrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.35.1.1.1.2.1.2
	::= { pdu818XTrapIPEntry 2 }


pdu818XPowerActive OBJECT-TYPE
	SYNTAX  Unsigned32
	UNITS
		"W"
	MAX-ACCESS read-only
	STATUS  current
	DESCRIPTION
		"Active Power"
	-- 1.3.6.1.4.1.28507.35.1.5.1.2.1.4
	::= { pdu818XPowerEntry 4 }


pdu818XIntSensors OBJECT IDENTIFIER 
	-- 1.3.6.1.4.1.28507.35.1.5
	::= { pdu818XObjects 5 }

-- Conformance
--

pdu818XConf OBJECT IDENTIFIER 
	-- 1.3.6.1.4.1.28507.35.2
	::= { gadsPDU818X 2 }

-- Groups
--

pdu818XGroups OBJECT IDENTIFIER 
	-- 1.3.6.1.4.1.28507.35.2.1
	::= { pdu818XConf 1 }

-- Compliance
--

pdu818XCompls OBJECT IDENTIFIER 
	-- 1.3.6.1.4.1.28507.35.2.2
	::= { pdu818XConf 2 }


pdu818XTempEvtSen1 NOTIFICATION-TYPE
	OBJECTS {
		pdu818XTempSensor}
	STATUS  current
	DESCRIPTION
		"temperature limits exceeded"
	-- 1.3.6.1.4.1.28507.35.0.6
	::= { events 6 }


pdu818XHygroEvtSen1 NOTIFICATION-TYPE
	OBJECTS {
		pdu818XHygroSensor}
	STATUS  current
	DESCRIPTION
		"hygro limits exceeded"
	-- 1.3.6.1.4.1.28507.35.0.7
	::= { events 7 }

pdu818XBasicGroup OBJECT-GROUP
	OBJECTS {
		pdu818XTrapCtrl,
		pdu818XTrapAddr,
		pdu818XTempSensor,
		pdu818XHygroSensor,
		pdu818XActivePowerChan,
		pdu818XChanStatus,
		pdu818XEnergyActive,
		pdu818XPowerActive,
		pdu818XCurrent,
		pdu818XVoltage }
	STATUS  current
	DESCRIPTION
		"Basic objects."
	-- 1.3.6.1.4.1.28507.35.2.1.1
	::= { pdu818XGroups 1 }

pdu818XNotificationGroup NOTIFICATION-GROUP
	NOTIFICATIONS {
		pdu818XTempEvtSen1,
		pdu818XHygroEvtSen1,
		pdu818XPowerDataEvt1,
		pdu818XPowerDataEvt2,
		pdu818XPowerDataEvt3,
		pdu818XPowerDataEvt4 }
	STATUS  current
	DESCRIPTION
		""
	-- 1.3.6.1.4.1.28507.35.2.1.2
	::= { pdu818XGroups 2 }

END
