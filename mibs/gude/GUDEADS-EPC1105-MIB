GUDEADS-EPC1105-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


gadsEPC1105 OBJECT IDENTIFIER 
	-- 1.3.6.1.4.1.28507.69
	::= { gudeads 69 }

-- Scalars and Tables
--

epc1105Objects OBJECT IDENTIFIER 
	-- 1.3.6.1.4.1.28507.69.1
	::= { gadsEPC1105 1 }

epc1105CommonConfig OBJECT IDENTIFIER 
	-- 1.3.6.1.4.1.28507.69.1.1
	::= { epc1105Objects 1 }

epc1105SNMPaccess OBJECT IDENTIFIER 
	-- 1.3.6.1.4.1.28507.69.1.1.1
	::= { epc1105CommonConfig 1 }

epc1105TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.69.1.1.1.1
	::= { epc1105SNMPaccess 1 }


epc1105TrapIPTable OBJECT-TYPE
	SYNTAX  SEQUENCE OF Epc8TrapIPEntry
	MAX-ACCESS not-accessible
	STATUS  current
	DESCRIPTION
		"list of all Trap receiver"
	-- 1.3.6.1.4.1.28507.69.1.1.1.2
	::= { epc1105SNMPaccess 2 }


epc1105TrapIPEntry OBJECT-TYPE
	SYNTAX  Epc8TrapIPEntry
	MAX-ACCESS not-accessible
	STATUS  current
	DESCRIPTION
		"an entry containing management
		informations regarding the list of trap
		receivers"
	INDEX {
		epc1105TrapIPIndex }
	-- 1.3.6.1.4.1.28507.69.1.1.1.2.1
	::= { epc1105TrapIPTable 1 }


Epc8TrapIPEntry ::= SEQUENCE {

	epc1105TrapIPIndex Integer32,
	epc1105TrapAddr    OCTET STRING }


epc1105TrapIPIndex OBJECT-TYPE
	SYNTAX  Integer32 (1..8)
	MAX-ACCESS read-only
	STATUS  current
	DESCRIPTION
		"A unique value, greater than zero, for each receiver slot."
	-- 1.3.6.1.4.1.28507.69.1.1.1.2.1.1
	::= { epc1105TrapIPEntry 1 }


epc1105TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.69.1.1.1.2.1.2
	::= { epc1105TrapIPEntry 2 }


epc1105DeviceConfig OBJECT IDENTIFIER 
	-- 1.3.6.1.4.1.28507.69.1.2
	::= { epc1105Objects 2 }

epc1105IntActors OBJECT IDENTIFIER 
	-- 1.3.6.1.4.1.28507.69.1.3
	::= { epc1105Objects 3 }

epc1105relayports OBJECT IDENTIFIER 
	-- 1.3.6.1.4.1.28507.69.1.3.1
	::= { epc1105IntActors 1 }

epc1105portNumber OBJECT-TYPE
	SYNTAX  Integer32 (1)
	MAX-ACCESS read-only
	STATUS  current
	DESCRIPTION
		"The number of Relay Ports"
	-- 1.3.6.1.4.1.28507.69.1.3.1.1
	::= { epc1105relayports 1 }


-- the Interfaces table
-- The Interfaces table contains information on the entity's
-- interfaces.  Each sub-layer below the internetwork-layer
-- of a network interface is considered to be an interface.

epc1105portTable OBJECT-TYPE
	SYNTAX  SEQUENCE OF Epc1105portEntry
	MAX-ACCESS not-accessible
	STATUS  current
	DESCRIPTION
		"list of all EPC Relay Ports"
	-- 1.3.6.1.4.1.28507.69.1.3.1.2
	::= { epc1105relayports 2 }


epc1105portEntry OBJECT-TYPE
	SYNTAX  Epc1105portEntry
	MAX-ACCESS not-accessible
	STATUS  current
	DESCRIPTION
		"An entry containing management information applicable to a
		particular relay port."
	INDEX {
		epc1105PortIndex }
	-- 1.3.6.1.4.1.28507.69.1.3.1.2.1
	::= { epc1105portTable 1 }


Epc1105portEntry ::= SEQUENCE {

	epc1105PortIndex        Integer32,
	epc1105PortName         OCTET STRING,
	epc1105PortState        INTEGER,
	epc1105PortSwitchCount  Integer32,
	epc1105PortStartupMode  INTEGER,
	epc1105PortStartupDelay Integer32,
	epc1105PortRepowerTime  Integer32 }


epc1105PortIndex OBJECT-TYPE
	SYNTAX  Integer32 (1)
	MAX-ACCESS read-only
	STATUS  current
	DESCRIPTION
		"A unique value, greater than zero, for each Relay Port."
	-- 1.3.6.1.4.1.28507.69.1.3.1.2.1.1
	::= { epc1105portEntry 1 }


epc1105PortName OBJECT-TYPE
	SYNTAX  OCTET STRING (SIZE (0..15))
	MAX-ACCESS read-write
	STATUS  current
	DESCRIPTION
		"A textual string containing name of a Relay Port."
	-- 1.3.6.1.4.1.28507.69.1.3.1.2.1.2
	::= { epc1105portEntry 2 }


epc1105PortState OBJECT-TYPE
	SYNTAX  INTEGER {
			off(0),
			on(1) }
	MAX-ACCESS read-write
	STATUS  current
	DESCRIPTION
		"current state a Relay Port"
	-- 1.3.6.1.4.1.28507.69.1.3.1.2.1.3
	::= { epc1105portEntry 3 }


epc1105PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.69.1.3.1.2.1.4
	::= { epc1105portEntry 4 }


epc1105PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.69.1.3.1.2.1.5
	::= { epc1105portEntry 5 }


epc1105PortStartupDelay OBJECT-TYPE
	SYNTAX  Integer32
	UNITS	"seconds"
	MAX-ACCESS read-write
	STATUS  current
	DESCRIPTION
		"Delay in sec for startup action"
	DEFVAL { 0 }
	-- 1.3.6.1.4.1.28507.69.1.3.1.2.1.6
	::= { epc1105portEntry 6 }


epc1105PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.69.1.3.1.2.1.7
	::= { epc1105portEntry 7 }


epc1105ExtActors OBJECT IDENTIFIER 
	-- 1.3.6.1.4.1.28507.69.1.4
	::= { epc1105Objects 4 }

epc1105IntSensors OBJECT IDENTIFIER 
	-- 1.3.6.1.4.1.28507.69.1.5
	::= { epc1105Objects 5 }

epc1105PowerChan OBJECT IDENTIFIER 
	-- 1.3.6.1.4.1.28507.69.1.5.1
	::= { epc1105IntSensors 1 }

epc1105ActivePowerChan OBJECT-TYPE
	SYNTAX  Unsigned32 (1)
	MAX-ACCESS read-only
	STATUS  current
	DESCRIPTION
		"Number of suppported Power Channels."
	-- 1.3.6.1.4.1.28507.69.1.5.1.1
	::= { epc1105PowerChan 1 }


epc1105PowerTable OBJECT-TYPE
	SYNTAX  SEQUENCE OF Epc1105PowerEntry
	MAX-ACCESS not-accessible
	STATUS  current
	DESCRIPTION
		"All available Channel Interfaces."
	-- 1.3.6.1.4.1.28507.69.1.5.1.2
	::= { epc1105PowerChan 2 }


epc1105PowerEntry OBJECT-TYPE
	SYNTAX  Epc1105PowerEntry
	MAX-ACCESS not-accessible
	STATUS  current
	DESCRIPTION
		"An entry containing management information
		applicable to a particular Power Channel."
	INDEX {
		epc1105PowerIndex }
	-- 1.3.6.1.4.1.28507.69.1.5.1.2.1
	::= { epc1105PowerTable 1 }


Epc1105PowerEntry ::= SEQUENCE {

	epc1105PowerIndex                   Integer32,
	epc1105ChanStatus                   Integer32,
	epc1105AbsEnergyActive              Unsigned32,
	epc1105PowerActive                  Integer32,
	epc1105Current                      Unsigned32,
	epc1105Voltage                      Unsigned32,
	epc1105Frequency                    Unsigned32,
	epc1105PowerFactor                  Integer32,
	epc1105Pangle                       Integer32,
	epc1105PowerApparent                Integer32,
	epc1105PowerReactive                Integer32,
	epc1105AbsEnergyReactive            Unsigned32,
	epc1105AbsEnergyActiveResettable    Unsigned32,
	epc1105AbsEnergyReactiveResettable  Unsigned32,
	epc1105ResetTime                    Unsigned32,
	epc1105ForwEnergyActive             Unsigned32,
	epc1105ForwEnergyReactive           Unsigned32,
	epc1105ForwEnergyActiveResettable   Unsigned32,
	epc1105ForwEnergyReactiveResettable Unsigned32,
	epc1105RevEnergyActive              Unsigned32,
	epc1105RevEnergyReactive            Unsigned32,
	epc1105RevEnergyActiveResettable    Unsigned32,
	epc1105RevEnergyReactiveResettable  Unsigned32 }


epc1105PowerIndex OBJECT-TYPE
	SYNTAX  Integer32 (1)
	MAX-ACCESS read-only
	STATUS  current
	DESCRIPTION
		"Index of Power Channel entries"
	-- 1.3.6.1.4.1.28507.69.1.5.1.2.1.1
	::= { epc1105PowerEntry 1 }


epc1105ChanStatus OBJECT-TYPE
	SYNTAX  Integer32 (0..1)
	MAX-ACCESS read-only
	STATUS  current
	DESCRIPTION
		"0 = data not active, 1 = data valid"
	-- 1.3.6.1.4.1.28507.69.1.5.1.2.1.2
	::= { epc1105PowerEntry 2 }


epc1105AbsEnergyActive OBJECT-TYPE
	SYNTAX  Unsigned32
	UNITS	"Wh"
	MAX-ACCESS read-only
	STATUS  current
	DESCRIPTION
		"Absolute Active Energy counter."
	-- 1.3.6.1.4.1.28507.69.1.5.1.2.1.3
	::= { epc1105PowerEntry 3 }


epc1105PowerActive OBJECT-TYPE
	SYNTAX  Integer32
	UNITS	"W"
	MAX-ACCESS read-only
	STATUS  current
	DESCRIPTION
		"Active Power"
	-- 1.3.6.1.4.1.28507.69.1.5.1.2.1.4
	::= { epc1105PowerEntry 4 }


epc1105Current OBJECT-TYPE
	SYNTAX  Unsigned32
	UNITS	"mA"
	MAX-ACCESS read-only
	STATUS  current
	DESCRIPTION
		"Actual Curent on Power Channel."
	-- 1.3.6.1.4.1.28507.69.1.5.1.2.1.5
	::= { epc1105PowerEntry 5 }


epc1105Voltage OBJECT-TYPE
	SYNTAX  Unsigned32
	UNITS	"V"
	MAX-ACCESS read-only
	STATUS  current
	DESCRIPTION
		"Actual Voltage on Power Channel"
	-- 1.3.6.1.4.1.28507.69.1.5.1.2.1.6
	::= { epc1105PowerEntry 6 }


epc1105Frequency OBJECT-TYPE
	SYNTAX  Unsigned32
	UNITS	"0.01 hz"
	MAX-ACCESS read-only
	STATUS  current
	DESCRIPTION
		"Frequency of Power Channel"
	-- 1.3.6.1.4.1.28507.69.1.5.1.2.1.7
	::= { epc1105PowerEntry 7 }


epc1105PowerFactor OBJECT-TYPE
	SYNTAX  Integer32
	UNITS	"0.001"
	MAX-ACCESS read-only
	STATUS  current
	DESCRIPTION
		"Power Factor of Channel between
		-1.0 and 1.00"
	-- 1.3.6.1.4.1.28507.69.1.5.1.2.1.8
	::= { epc1105PowerEntry 8 }


epc1105Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.69.1.5.1.2.1.9
	::= { epc1105PowerEntry 9 }


epc1105PowerApparent OBJECT-TYPE
	SYNTAX  Integer32
	UNITS	"VA"
	MAX-ACCESS read-only
	STATUS  current
	DESCRIPTION
		"L Line Mean Apparent Power"
	-- 1.3.6.1.4.1.28507.69.1.5.1.2.1.10
	::= { epc1105PowerEntry 10 }


epc1105PowerReactive OBJECT-TYPE
	SYNTAX  Integer32
	UNITS	"VAR"
	MAX-ACCESS read-only
	STATUS  current
	DESCRIPTION
		"L Line Mean Reactive Power"
	-- 1.3.6.1.4.1.28507.69.1.5.1.2.1.11
	::= { epc1105PowerEntry 11 }


epc1105AbsEnergyReactive OBJECT-TYPE
	SYNTAX  Unsigned32
	UNITS	"VARh"
	MAX-ACCESS read-only
	STATUS  current
	DESCRIPTION
		"Absolute Reactive Energy counter."
	-- 1.3.6.1.4.1.28507.69.1.5.1.2.1.12
	::= { epc1105PowerEntry 12 }


epc1105AbsEnergyActiveResettable OBJECT-TYPE
	SYNTAX  Unsigned32
	UNITS	"Wh"
	MAX-ACCESS read-write
	STATUS  current
	DESCRIPTION
		"Resettable Absolute Active Energy counter.
		Writing '0' resets all resettable counter.r."
	-- 1.3.6.1.4.1.28507.69.1.5.1.2.1.13
	::= { epc1105PowerEntry 13 }


epc1105AbsEnergyReactiveResettable OBJECT-TYPE
	SYNTAX  Unsigned32
	UNITS	"VARh"
	MAX-ACCESS read-only
	STATUS  current
	DESCRIPTION
		"Resettable Absolute Reactive Energy counter."
	-- 1.3.6.1.4.1.28507.69.1.5.1.2.1.14
	::= { epc1105PowerEntry 14 }


epc1105ResetTime OBJECT-TYPE
	SYNTAX  Unsigned32
	UNITS	"s"
	MAX-ACCESS read-only
	STATUS  current
	DESCRIPTION
		"Time in seconds since last Energy
		Counter reset."
	-- 1.3.6.1.4.1.28507.69.1.5.1.2.1.15
	::= { epc1105PowerEntry 15 }


epc1105ForwEnergyActive OBJECT-TYPE
	SYNTAX  Unsigned32
	UNITS	"Wh"
	MAX-ACCESS read-only
	STATUS  current
	DESCRIPTION
		"Forward Active Energy counter."
	-- 1.3.6.1.4.1.28507.69.1.5.1.2.1.16
	::= { epc1105PowerEntry 16 }


epc1105ForwEnergyReactive OBJECT-TYPE
	SYNTAX  Unsigned32
	UNITS	"VARh"
	MAX-ACCESS read-only
	STATUS  current
	DESCRIPTION
		"Forward Reactive Energy counter."
	-- 1.3.6.1.4.1.28507.69.1.5.1.2.1.17
	::= { epc1105PowerEntry 17 }


epc1105ForwEnergyActiveResettable OBJECT-TYPE
	SYNTAX  Unsigned32
	UNITS	"Wh"
	MAX-ACCESS read-only
	STATUS  current
	DESCRIPTION
		"Resettable Forward Active Energy counter."
	-- 1.3.6.1.4.1.28507.69.1.5.1.2.1.18
	::= { epc1105PowerEntry 18 }


epc1105ForwEnergyReactiveResettable OBJECT-TYPE
	SYNTAX  Unsigned32
	UNITS	"VARh"
	MAX-ACCESS read-only
	STATUS  current
	DESCRIPTION
		"Resettable Forward Reactive Energy counter."
	-- 1.3.6.1.4.1.28507.69.1.5.1.2.1.19
	::= { epc1105PowerEntry 19 }


epc1105RevEnergyActive OBJECT-TYPE
	SYNTAX  Unsigned32
	UNITS	"Wh"
	MAX-ACCESS read-only
	STATUS  current
	DESCRIPTION
		"Reverse Active Energy counter."
	-- 1.3.6.1.4.1.28507.69.1.5.1.2.1.20
	::= { epc1105PowerEntry 20 }


epc1105RevEnergyReactive OBJECT-TYPE
	SYNTAX  Unsigned32
	UNITS	"VARh"
	MAX-ACCESS read-only
	STATUS  current
	DESCRIPTION
		"Reverse Reactive Energy counter."
	-- 1.3.6.1.4.1.28507.69.1.5.1.2.1.21
	::= { epc1105PowerEntry 21 }


epc1105RevEnergyActiveResettable OBJECT-TYPE
	SYNTAX  Unsigned32
	UNITS	"Wh"
	MAX-ACCESS read-only
	STATUS  current
	DESCRIPTION
		"Resettable Reverse Active Energy counter."
	-- 1.3.6.1.4.1.28507.69.1.5.1.2.1.22
	::= { epc1105PowerEntry 22 }


epc1105RevEnergyReactiveResettable OBJECT-TYPE
	SYNTAX  Unsigned32
	UNITS	"VARh"
	MAX-ACCESS read-only
	STATUS  current
	DESCRIPTION
		"Resettable Reverse Reactive Energy counter."
	-- 1.3.6.1.4.1.28507.69.1.5.1.2.1.23
	::= { epc1105PowerEntry 23 }


epc1105ExtSensors OBJECT IDENTIFIER 
	-- 1.3.6.1.4.1.28507.69.1.6
	::= { epc1105Objects 6 }

-- Conformance
--

epc1105Conf OBJECT IDENTIFIER 
	-- 1.3.6.1.4.1.28507.69.2
	::= { gadsEPC1105 2 }

-- Groups
--

epc1105Groups OBJECT IDENTIFIER 
	-- 1.3.6.1.4.1.28507.69.2.1
	::= { epc1105Conf 1 }

-- Compliance
--

epc1105Compls OBJECT IDENTIFIER 
	-- 1.3.6.1.4.1.28507.69.2.2
	::= { epc1105Conf 2 }

epc1105BasicGroup OBJECT-GROUP
	OBJECTS {
		epc1105TrapCtrl,
		epc1105TrapIPIndex,
		epc1105TrapAddr,
		epc1105portNumber,
		epc1105PortIndex,
		epc1105PortName,
		epc1105PortState,
		epc1105PortSwitchCount,
		epc1105PortStartupMode,
		epc1105PortStartupDelay,
		epc1105PortRepowerTime,
		epc1105ActivePowerChan,
		epc1105PowerIndex,
		epc1105ChanStatus,
		epc1105AbsEnergyActive,
		epc1105PowerActive,
		epc1105Current,
		epc1105Voltage,
		epc1105Frequency,
		epc1105PowerFactor,
		epc1105Pangle,
		epc1105PowerApparent,
		epc1105PowerReactive,
		epc1105AbsEnergyReactive,
		epc1105AbsEnergyActiveResettable,
		epc1105AbsEnergyReactiveResettable,
		epc1105ResetTime,
		epc1105ForwEnergyActive,
		epc1105ForwEnergyReactive,
		epc1105ForwEnergyActiveResettable,
		epc1105ForwEnergyReactiveResettable,
		epc1105RevEnergyActive,
		epc1105RevEnergyReactive,
		epc1105RevEnergyActiveResettable,
		epc1105RevEnergyReactiveResettable,
		epc1105SensorIndex,
		epc1105TempSensor,
		epc1105HygroSensor,
		epc1105InputSensor,
		epc1105AirPressure,
		epc1105DewPoint,
		epc1105DewPointDiff }
	STATUS  current
	DESCRIPTION
		"Basic objects."
	-- 1.3.6.1.4.1.28507.69.2.1.1
	::= { epc1105Groups 1 }

epc1105NotificationGroup NOTIFICATION-GROUP
	NOTIFICATIONS {
		epc1105HygroEvtSen,
		epc1105SwitchEvtPort,
		epc1105TempEvtSen,
		epc1105InputEvtSen,
		epc1105AirPressureEvtSen,
		epc1105DewPtDiffEvtSen,
		epc1105LineAmperageEvt }
	STATUS  current
	DESCRIPTION ""
	-- 1.3.6.1.4.1.28507.69.2.1.2
	::= { epc1105Groups 2 }

-- Notification Types
--

events OBJECT IDENTIFIER 
	-- 1.3.6.1.4.1.28507.69.3
	::= { gadsEPC1105 3 }

epc1105SensorTable OBJECT-TYPE
	SYNTAX  SEQUENCE OF Epc1105SensorEntry
	MAX-ACCESS not-accessible
	STATUS  current
	DESCRIPTION ""
	-- 1.3.6.1.4.1.28507.69.1.6.1
	::= { epc1105ExtSensors 1 }


epc1105SensorEntry OBJECT-TYPE
	SYNTAX  Epc1105SensorEntry
	MAX-ACCESS not-accessible
	STATUS  current
	DESCRIPTION ""
	INDEX {
		epc1105SensorIndex }
	-- 1.3.6.1.4.1.28507.69.1.6.1.1
	::= { epc1105SensorTable 1 }


Epc1105SensorEntry ::= SEQUENCE {

	epc1105SensorIndex  Integer32,
	epc1105TempSensor   Integer32,
	epc1105HygroSensor  Integer32,
	epc1105InputSensor  INTEGER,
	epc1105AirPressure  Integer32,
	epc1105DewPoint     Integer32,
	epc1105DewPointDiff Integer32 }


epc1105SensorIndex OBJECT-TYPE
	SYNTAX  Integer32 (1)
	MAX-ACCESS read-only
	STATUS  current
	DESCRIPTION ""
	-- 1.3.6.1.4.1.28507.69.1.6.1.1.1
	::= { epc1105SensorEntry 1 }


epc1105TempSensor OBJECT-TYPE
	SYNTAX  Integer32
	UNITS	"0.1 degree Celsius"
	MAX-ACCESS read-only
	STATUS  current
	DESCRIPTION
		"actual temperature"
	-- 1.3.6.1.4.1.28507.69.1.6.1.1.2
	::= { epc1105SensorEntry 2 }


epc1105HygroSensor OBJECT-TYPE
	SYNTAX  Integer32
	UNITS	"0.1 percent humidity"
	MAX-ACCESS read-only
	STATUS  current
	DESCRIPTION
		"actual humidity"
	-- 1.3.6.1.4.1.28507.69.1.6.1.1.3
	::= { epc1105SensorEntry 3 }


epc1105InputSensor OBJECT-TYPE
	SYNTAX  INTEGER {
			off(0),
			on(1) }
	MAX-ACCESS read-only
	STATUS  current
	DESCRIPTION
		"logical state of input sensor"
	-- 1.3.6.1.4.1.28507.69.1.6.1.1.4
	::= { epc1105SensorEntry 4 }



epc1105SwitchEvtPort NOTIFICATION-TYPE
	OBJECTS {
		epc1105PortIndex,
		epc1105PortName,
		epc1105PortState,
		epc1105PortSwitchCount}
	STATUS  current
	DESCRIPTION
		"Event is triggered when a port is switched"
	-- 1.3.6.1.4.1.28507.69.3.1
	::= { events 1 }


epc1105LineAmperageEvt NOTIFICATION-TYPE
	OBJECTS {
		epc1105PowerIndex,
		epc1105PowerActive,
		epc1105Current,
		epc1105Voltage,
		epc1105Frequency,
		epc1105PowerApparent,
		epc1105PowerReactive}
	STATUS  current
	DESCRIPTION
		"Event is triggered when a measured
		current is crossing the entered limits"
	-- 1.3.6.1.4.1.28507.69.3.7
	::= { events 7 }


epc1105TempEvtSen NOTIFICATION-TYPE
	OBJECTS {
		epc1105SensorIndex,
		epc1105TempSensor}
	STATUS  current
	DESCRIPTION
		"temperature limits exceeded"
	-- 1.3.6.1.4.1.28507.69.3.2
	::= { events 2 }


epc1105InputEvtSen NOTIFICATION-TYPE
	OBJECTS {
		epc1105SensorIndex,
		epc1105InputSensor}
	STATUS  current
	DESCRIPTION
		"change of logical input sensor state"
	-- 1.3.6.1.4.1.28507.69.3.4
	::= { events 4 }


epc1105AirPressureEvtSen NOTIFICATION-TYPE
	OBJECTS {
		epc1105SensorIndex,
		epc1105AirPressure}
	STATUS  current
	DESCRIPTION
		"Air Pressure limits exceeded"
	-- 1.3.6.1.4.1.28507.69.3.5
	::= { events 5 }


epc1105DewPtDiffEvtSen NOTIFICATION-TYPE
	OBJECTS {
		epc1105SensorIndex,
		epc1105DewPointDiff}
	STATUS  current
	DESCRIPTION
		"Dew Point Difference limits exceeded"
	-- 1.3.6.1.4.1.28507.69.3.6
	::= { events 6 }

epc1105AirPressure OBJECT-TYPE
	SYNTAX  Integer32
	UNITS	"1 hPA (hectopascal) ~ 1 milibar"
	MAX-ACCESS read-only
	STATUS  current
	DESCRIPTION
		"actual air pressure"
	-- 1.3.6.1.4.1.28507.69.1.6.1.1.5
	::= { epc1105SensorEntry 5 }


epc1105DewPoint OBJECT-TYPE
	SYNTAX  Integer32
	UNITS	"0.1 degree Celsius"
	MAX-ACCESS read-only
	STATUS  current
	DESCRIPTION
		"dew point for actual temperature and humidity"
	-- 1.3.6.1.4.1.28507.69.1.6.1.1.6
	::= { epc1105SensorEntry 6 }


epc1105DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.69.1.6.1.1.7
	::= { epc1105SensorEntry 7 }



epc1105HygroEvtSen NOTIFICATION-TYPE
	OBJECTS {
		epc1105SensorIndex,
		epc1105HygroSensor}
	STATUS  current
	DESCRIPTION
		"hygro limits exceeded"
	-- 1.3.6.1.4.1.28507.43.3.4
	-- 1.3.6.1.4.1.28507.68.3.3
	-- 1.3.6.1.4.1.28507.69.3.3
	::= { events 3 }

END
