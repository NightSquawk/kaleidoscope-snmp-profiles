GUDEADS-ENC2191-MIB DEFINITIONS ::= BEGIN

IMPORTS
	enterprises,
	MODULE-IDENTITY,
	OBJECT-TYPE,
	NOTIFICATION-TYPE,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }


enc2191POE OBJECT-TYPE
	SYNTAX  Integer32 (0..1)
	UNITS	"0 = no POE, 1 = POE available"
	MAX-ACCESS read-only
	STATUS  current
	DESCRIPTION
		"signals POE availability"
	-- 1.3.6.1.4.1.28507.61.1.5.10
	::= { enc2191IntSensors 10 }


gadsENC2191 OBJECT IDENTIFIER 
	-- 1.3.6.1.4.1.28507.61
	::= { gudeads 61 }

-- Notification Types
--

events OBJECT IDENTIFIER 
	-- 1.3.6.1.4.1.28507.61.3
	::= { gadsENC2191 3 }

-- Scalars and Tables
--

enc2191Objects OBJECT IDENTIFIER 
	-- 1.3.6.1.4.1.28507.61.1
	::= { gadsENC2191 1 }

enc2191CommonConfig OBJECT IDENTIFIER 
	-- 1.3.6.1.4.1.28507.61.1.1
	::= { enc2191Objects 1 }

enc2191SNMPaccess OBJECT IDENTIFIER 
	-- 1.3.6.1.4.1.28507.61.1.1.1
	::= { enc2191CommonConfig 1 }

enc2191TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.61.1.1.1.1
	::= { enc2191SNMPaccess 1 }


enc2191TrapIPTable OBJECT-TYPE
	SYNTAX  SEQUENCE OF Enc2191TrapIPEntry
	MAX-ACCESS not-accessible
	STATUS  current
	DESCRIPTION
		"list of all Trap receiver"
	-- 1.3.6.1.4.1.28507.61.1.1.1.2
	::= { enc2191SNMPaccess 2 }


enc2191TrapIPEntry OBJECT-TYPE
	SYNTAX  Enc2191TrapIPEntry
	MAX-ACCESS not-accessible
	STATUS  current
	DESCRIPTION
		"an entry containing management
		informations regarding the list of trap
		receivers"
	INDEX {
		enc2191TrapIPIndex }
	-- 1.3.6.1.4.1.28507.61.1.1.1.2.1
	::= { enc2191TrapIPTable 1 }


Enc2191TrapIPEntry ::= SEQUENCE {

	enc2191TrapIPIndex Integer32,
	enc2191TrapAddr    OCTET STRING }


enc2191TrapIPIndex OBJECT-TYPE
	SYNTAX  Integer32 (1..8)
	MAX-ACCESS read-only
	STATUS  current
	DESCRIPTION
		"A unique value, greater than zero, for each receiver slot."
	-- 1.3.6.1.4.1.28507.61.1.1.1.2.1.1
	::= { enc2191TrapIPEntry 1 }


enc2191TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.61.1.1.1.2.1.2
	::= { enc2191TrapIPEntry 2 }


enc2191DeviceConfig OBJECT IDENTIFIER 
	-- 1.3.6.1.4.1.28507.61.1.2
	::= { enc2191Objects 2 }

enc2191IntActors OBJECT IDENTIFIER 
	-- 1.3.6.1.4.1.28507.61.1.3
	::= { enc2191Objects 3 }

enc2191relayports OBJECT IDENTIFIER 
	-- 1.3.6.1.4.1.28507.61.1.3.1
	::= { enc2191IntActors 1 }

enc2191portNumber OBJECT-TYPE
	SYNTAX  Integer32 (1..12)
	MAX-ACCESS read-only
	STATUS  current
	DESCRIPTION
		"The number of Relay Ports"
	-- 1.3.6.1.4.1.28507.61.1.3.1.1
	::= { enc2191relayports 1 }


-- the Interfaces table
-- The Interfaces table contains information on the entity's
-- interfaces.  Each sub-layer below the internetwork-layer
-- of a network interface is considered to be an interface.

enc2191portTable OBJECT-TYPE
	SYNTAX  SEQUENCE OF Enc2191portEntry
	MAX-ACCESS not-accessible
	STATUS  current
	DESCRIPTION
		"list of all EPC Relay Ports"
	-- 1.3.6.1.4.1.28507.61.1.3.1.2
	::= { enc2191relayports 2 }


enc2191portEntry OBJECT-TYPE
	SYNTAX  Enc2191portEntry
	MAX-ACCESS not-accessible
	STATUS  current
	DESCRIPTION
		"An entry containing management information applicable to a
		particular relay port."
	INDEX {
		enc2191PortIndex }
	-- 1.3.6.1.4.1.28507.61.1.3.1.2.1
	::= { enc2191portTable 1 }


Enc2191portEntry ::= SEQUENCE {

	enc2191PortIndex        Integer32,
	enc2191PortName         OCTET STRING,
	enc2191PortState        INTEGER,
	enc2191PortSwitchCount  Integer32,
	enc2191PortStartupMode  INTEGER,
	enc2191PortStartupDelay Integer32,
	enc2191PortRepowerTime  Integer32 }


enc2191PortIndex OBJECT-TYPE
	SYNTAX  Integer32 (1..4)
	MAX-ACCESS read-only
	STATUS  current
	DESCRIPTION
		"A unique value, greater than zero, for each Relay Port."
	-- 1.3.6.1.4.1.28507.61.1.3.1.2.1.1
	::= { enc2191portEntry 1 }


enc2191PortName OBJECT-TYPE
	SYNTAX  OCTET STRING (SIZE (0..15))
	MAX-ACCESS read-write
	STATUS  current
	DESCRIPTION
		"A textual string containing name of a Relay Port."
	-- 1.3.6.1.4.1.28507.61.1.3.1.2.1.2
	::= { enc2191portEntry 2 }


enc2191PortState OBJECT-TYPE
	SYNTAX  INTEGER {
			off(0),
			on(1) }
	MAX-ACCESS read-write
	STATUS  current
	DESCRIPTION
		"current state of a Relay Port"
	-- 1.3.6.1.4.1.28507.61.1.3.1.2.1.3
	::= { enc2191portEntry 3 }


enc2191PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.61.1.3.1.2.1.4
	::= { enc2191portEntry 4 }


enc2191PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.61.1.3.1.2.1.5
	::= { enc2191portEntry 5 }


enc2191PortStartupDelay OBJECT-TYPE
	SYNTAX  Integer32
	UNITS	"seconds"
	MAX-ACCESS read-write
	STATUS  current
	DESCRIPTION
		"Delay in sec for startup action"
	DEFVAL { 0 }
	-- 1.3.6.1.4.1.28507.61.1.3.1.2.1.6
	::= { enc2191portEntry 6 }


enc2191PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.61.1.3.1.2.1.7
	::= { enc2191portEntry 7 }


enc2191ExtActors OBJECT IDENTIFIER 
	-- 1.3.6.1.4.1.28507.61.1.4
	::= { enc2191Objects 4 }

enc2191IntSensors OBJECT IDENTIFIER 
	-- 1.3.6.1.4.1.28507.61.1.5
	::= { enc2191Objects 5 }

enc2191VoltageInfo OBJECT IDENTIFIER 
	-- 1.3.6.1.4.1.28507.61.1.5.7
	::= { enc2191IntSensors 7 }

enc2191ExtSensors OBJECT IDENTIFIER 
	-- 1.3.6.1.4.1.28507.61.1.6
	::= { enc2191Objects 6 }

enc2191SensorTable OBJECT-TYPE
	SYNTAX  SEQUENCE OF Enc2191SensorEntry
	MAX-ACCESS not-accessible
	STATUS  current
	DESCRIPTION ""
	-- 1.3.6.1.4.1.28507.61.1.6.1
	::= { enc2191ExtSensors 1 }


enc2191SensorEntry OBJECT-TYPE
	SYNTAX  Enc2191SensorEntry
	MAX-ACCESS not-accessible
	STATUS  current
	DESCRIPTION ""
	INDEX {
		enc2191SensorIndex }
	-- 1.3.6.1.4.1.28507.61.1.6.1.1
	::= { enc2191SensorTable 1 }


Enc2191SensorEntry ::= SEQUENCE {

	enc2191SensorIndex  Integer32,
	enc2191TempSensor   Integer32,
	enc2191HygroSensor  Integer32,
	enc2191InputSensor  INTEGER,
	enc2191AirPressure  Integer32,
	enc2191DewPoint     Integer32,
	enc2191DewPointDiff Integer32 }


enc2191SensorIndex OBJECT-TYPE
	SYNTAX  Integer32 (1..4)
	MAX-ACCESS read-only
	STATUS  current
	DESCRIPTION ""
	-- 1.3.6.1.4.1.28507.61.1.6.1.1.1
	::= { enc2191SensorEntry 1 }


enc2191State3V OBJECT-TYPE
	SYNTAX  INTEGER {
			on(1),
			error(3) }
	MAX-ACCESS read-only
	STATUS  current
	DESCRIPTION
		"Show state of internal 3.3V"
	-- 1.3.6.1.4.1.28507.61.1.5.7.2
	::= { enc2191VoltageInfo 2 }


enc2191TempSensor OBJECT-TYPE
	SYNTAX  Integer32
	UNITS	"0.1 degree Celsius"
	MAX-ACCESS read-only
	STATUS  current
	DESCRIPTION
		"actual temperature"
	-- 1.3.6.1.4.1.28507.61.1.6.1.1.2
	::= { enc2191SensorEntry 2 }


enc2191HygroSensor OBJECT-TYPE
	SYNTAX  Integer32
	UNITS	"0.1 percent humidity"
	MAX-ACCESS read-only
	STATUS  current
	DESCRIPTION
		"actual humidity"
	-- 1.3.6.1.4.1.28507.61.1.6.1.1.3
	::= { enc2191SensorEntry 3 }


enc2191InputSensor OBJECT-TYPE
	SYNTAX  INTEGER {
			off(0),
			on(1) }
	MAX-ACCESS read-only
	STATUS  current
	DESCRIPTION
		"logical state of input sensor"
	-- 1.3.6.1.4.1.28507.61.1.6.1.1.4
	::= { enc2191SensorEntry 4 }


-- Conformance
--

enc2191Conf OBJECT IDENTIFIER 
	-- 1.3.6.1.4.1.28507.61.2
	::= { gadsENC2191 2 }

-- Groups
--

enc2191Groups OBJECT IDENTIFIER 
	-- 1.3.6.1.4.1.28507.61.2.1
	::= { enc2191Conf 1 }

-- Compliance
--

enc2191Compls OBJECT IDENTIFIER 
	-- 1.3.6.1.4.1.28507.61.2.2
	::= { enc2191Conf 2 }

enc2191BasicGroup OBJECT-GROUP
	OBJECTS {
		enc2191TrapCtrl,
		enc2191TrapIPIndex,
		enc2191TrapAddr,
		enc2191portNumber,
		enc2191PortIndex,
		enc2191PortName,
		enc2191PortState,
		enc2191PortSwitchCount,
		enc2191PortStartupMode,
		enc2191PortStartupDelay,
		enc2191PortRepowerTime,
		enc2191ActiveInputs,
		enc2191InputIndex,
		enc2191Input,
		enc2191State12V,
		enc2191State3V,
		enc2191POE,
		enc2191SensorIndex,
		enc2191TempSensor,
		enc2191HygroSensor,
		enc2191InputSensor,
		enc2191AirPressure,
		enc2191DewPoint,
		enc2191DewPointDiff }
	STATUS  current
	DESCRIPTION
		"Basic objects."
	-- 1.3.6.1.4.1.28507.61.2.1.1
	::= { enc2191Groups 1 }

enc2191NotificationGroup NOTIFICATION-GROUP
	NOTIFICATIONS {
		enc2191SwitchEvtPort,
		enc2191InputEvt,
		enc2191TempEvtSen,
		enc2191HygroEvtSen,
		enc2191InputEvtSen,
		enc2191AirPressureEvtSen,
		enc2191DewPtDiffEvtSen,
		enc2191POEEvt }
	STATUS  current
	DESCRIPTION ""
	-- 1.3.6.1.4.1.28507.61.2.1.2
	::= { enc2191Groups 2 }

enc2191Inputs OBJECT IDENTIFIER 
	-- 1.3.6.1.4.1.28507.61.1.5.6
	::= { enc2191IntSensors 6 }

enc2191InputEntry OBJECT-TYPE
	SYNTAX  Enc2191InputEntry
	MAX-ACCESS not-accessible
	STATUS  current
	DESCRIPTION ""
	INDEX {
		enc2191InputIndex }
	-- 1.3.6.1.4.1.28507.61.1.5.6.2.1
	::= { enc2191InputTable 1 }


Enc2191InputEntry ::= SEQUENCE {

	enc2191InputIndex Integer32,
	enc2191Input      INTEGER }


enc2191Input OBJECT-TYPE
	SYNTAX  INTEGER {
			lo(0),
			hi(1) }
	MAX-ACCESS read-only
	STATUS  current
	DESCRIPTION
		"Input state of device"
	-- 1.3.6.1.4.1.28507.61.1.5.6.2.1.2
	::= { enc2191InputEntry 2 }


enc2191ActiveInputs OBJECT-TYPE
	SYNTAX  Unsigned32 (1..12)
	MAX-ACCESS read-only
	STATUS  current
	DESCRIPTION
		"Number of suppported Input Channels."
	-- 1.3.6.1.4.1.28507.61.1.5.6.1
	::= { enc2191Inputs 1 }


enc2191InputTable OBJECT-TYPE
	SYNTAX  SEQUENCE OF Enc2191InputEntry
	MAX-ACCESS not-accessible
	STATUS  current
	DESCRIPTION ""
	-- 1.3.6.1.4.1.28507.61.1.5.6.2
	::= { enc2191Inputs 2 }


enc2191InputIndex OBJECT-TYPE
	SYNTAX  Integer32 (1..12)
	MAX-ACCESS read-only
	STATUS  current
	DESCRIPTION ""
	-- 1.3.6.1.4.1.28507.61.1.5.6.2.1.1
	::= { enc2191InputEntry 1 }


enc2191State12V OBJECT-TYPE
	SYNTAX  INTEGER {
			off(0),
			low(1),
			high(2),
			error(3) }
	MAX-ACCESS read-only
	STATUS  current
	DESCRIPTION
		"Show state of internal 12V"
	-- 1.3.6.1.4.1.28507.61.1.5.7.1
	::= { enc2191VoltageInfo 1 }


enc2191AirPressure OBJECT-TYPE
	SYNTAX  Integer32
	UNITS	"1 hPA (hectopascal) ~ 1 milibar"
	MAX-ACCESS read-only
	STATUS  current
	DESCRIPTION
		"actual air pressure"
	-- 1.3.6.1.4.1.28507.61.1.6.1.1.5
	::= { enc2191SensorEntry 5 }


enc2191DewPoint OBJECT-TYPE
	SYNTAX  Integer32
	UNITS	"0.1 degree Celsius"
	MAX-ACCESS read-only
	STATUS  current
	DESCRIPTION
		"dew point for actual temperature and humidity"
	-- 1.3.6.1.4.1.28507.61.1.6.1.1.6
	::= { enc2191SensorEntry 6 }


enc2191DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.61.1.6.1.1.7
	::= { enc2191SensorEntry 7 }



enc2191POEEvt NOTIFICATION-TYPE
	OBJECTS {
		enc2191POE}
	STATUS  current
	DESCRIPTION
		"Power over Ethernet changed"
	-- 1.3.6.1.4.1.28507.61.3.8
	::= { events 8 }


enc2191InputEvt NOTIFICATION-TYPE
	OBJECTS {
		enc2191InputIndex,
		enc2191Input}
	STATUS  current
	DESCRIPTION
		"Change of device input."
	-- 1.3.6.1.4.1.28507.61.3.2
	::= { events 2 }


enc2191HygroEvtSen NOTIFICATION-TYPE
	OBJECTS {
		enc2191SensorIndex,
		enc2191HygroSensor}
	STATUS  current
	DESCRIPTION
		"hygro limits exceeded"
	-- 1.3.6.1.4.1.28507.61.3.4
	::= { events 4 }


enc2191InputEvtSen NOTIFICATION-TYPE
	OBJECTS {
		enc2191SensorIndex,
		enc2191InputSensor}
	STATUS  current
	DESCRIPTION
		"change of logical input sensor state"
	-- 1.3.6.1.4.1.28507.61.3.5
	::= { events 5 }


enc2191AirPressureEvtSen NOTIFICATION-TYPE
	OBJECTS {
		enc2191SensorIndex,
		enc2191AirPressure}
	STATUS  current
	DESCRIPTION
		"Air Pressure limits exceeded

		"
	-- 1.3.6.1.4.1.28507.61.3.6
	::= { events 6 }


enc2191DewPtDiffEvtSen NOTIFICATION-TYPE
	OBJECTS {
		enc2191SensorIndex,
		enc2191DewPointDiff}
	STATUS  current
	DESCRIPTION
		"Dew Point Difference limits exceeded"
	-- 1.3.6.1.4.1.28507.61.3.7
	::= { events 7 }


enc2191TempEvtSen NOTIFICATION-TYPE
	OBJECTS {
		enc2191SensorIndex,
		enc2191TempSensor}
	STATUS  current
	DESCRIPTION
		"temperature limits exceeded"
	-- 1.3.6.1.4.1.28507.61.3.3
	::= { events 3 }


enc2191SwitchEvtPort NOTIFICATION-TYPE
	OBJECTS {
		enc2191PortIndex,
		enc2191PortName,
		enc2191PortState,
		enc2191PortSwitchCount}
	STATUS  current
	DESCRIPTION
		"Event is triggered when a port is switched"
	-- 1.3.6.1.4.1.28507.61.3.1
	::= { events 1 }

END
