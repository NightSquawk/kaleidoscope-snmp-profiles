GUDEADS-EPC1292-MIB DEFINITIONS ::= BEGIN

IMPORTS
	enterprises,
	MODULE-IDENTITY,
	OBJECT-TYPE,
	NOTIFICATION-TYPE,
	Gauge32,
	Integer32,
	Unsigned32
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id:$"
	-- 1.3.6.1.4.1.28507
	::= { enterprises 28507 }



epc1292HygroEvtSen NOTIFICATION-TYPE
	OBJECTS {
		epc1292SensorIndex,
		epc1292HygroSensor}
	STATUS  current
	DESCRIPTION
		"hygro limits exceeded"
	-- 1.3.6.1.4.1.28507.50.3.3
	::= { events 3 }

gadsEPC1292 OBJECT IDENTIFIER 
	-- 1.3.6.1.4.1.28507.50
	::= { gudeads 50 }

-- Notification Types
--

events OBJECT IDENTIFIER 
	-- 1.3.6.1.4.1.28507.50.3
	::= { gadsEPC1292 3 }

-- Scalars and Tables
--

epc1292Objects OBJECT IDENTIFIER 
	-- 1.3.6.1.4.1.28507.50.1
	::= { gadsEPC1292 1 }

epc1292CommonConfig OBJECT IDENTIFIER 
	-- 1.3.6.1.4.1.28507.50.1.1
	::= { epc1292Objects 1 }

epc1292SNMPaccess OBJECT IDENTIFIER 
	-- 1.3.6.1.4.1.28507.50.1.1.1
	::= { epc1292CommonConfig 1 }

epc1292TrapCtrl OBJECT-TYPE
	SYNTAX  Integer32 (0..3)
	MAX-ACCESS read-write
	STATUS  current
	DESCRIPTION
		"0 = off
		1 = Ver. 1
		2 = Ver. 2c
		3 = Ver. 3"
	-- 1.3.6.1.4.1.28507.50.1.1.1.1
	::= { epc1292SNMPaccess 1 }


epc1292TrapIPTable OBJECT-TYPE
	SYNTAX  SEQUENCE OF Epc1292TrapIPEntry
	MAX-ACCESS not-accessible
	STATUS  current
	DESCRIPTION
		"list of all Trap receiver"
	-- 1.3.6.1.4.1.28507.50.1.1.1.2
	::= { epc1292SNMPaccess 2 }


epc1292TrapIPEntry OBJECT-TYPE
	SYNTAX  Epc1292TrapIPEntry
	MAX-ACCESS not-accessible
	STATUS  current
	DESCRIPTION
		"an entry containing management
		informations regarding the list of trap
		receivers"
	INDEX {
		epc1292TrapIPIndex }
	-- 1.3.6.1.4.1.28507.50.1.1.1.2.1
	::= { epc1292TrapIPTable 1 }


Epc1292TrapIPEntry ::= SEQUENCE {

	epc1292TrapIPIndex Integer32,
	epc1292TrapAddr    OCTET STRING }


epc1292TrapIPIndex OBJECT-TYPE
	SYNTAX  Integer32 (1..8)
	MAX-ACCESS read-only
	STATUS  current
	DESCRIPTION
		"A unique value, greater than zero, for each receiver slot."
	-- 1.3.6.1.4.1.28507.50.1.1.1.2.1.1
	::= { epc1292TrapIPEntry 1 }


epc1292TrapAddr OBJECT-TYPE
	SYNTAX  OCTET STRING (SIZE (0..99))
	MAX-ACCESS read-write
	STATUS  current
	DESCRIPTION
		"DNS name or IP address specifying one Trap receiver slot.
		A port can optionally be specified: 'name:port' An empty
		string disables this slot."
	-- 1.3.6.1.4.1.28507.50.1.1.1.2.1.2
	::= { epc1292TrapIPEntry 2 }


epc1292DeviceConfig OBJECT IDENTIFIER 
	-- 1.3.6.1.4.1.28507.50.1.2
	::= { epc1292Objects 2 }

epc1292IntActors OBJECT IDENTIFIER 
	-- 1.3.6.1.4.1.28507.50.1.3
	::= { epc1292Objects 3 }

epc1292relayports OBJECT IDENTIFIER 
	-- 1.3.6.1.4.1.28507.50.1.3.1
	::= { epc1292IntActors 1 }

epc1292portNumber OBJECT-TYPE
	SYNTAX  Integer32 (1..4)
	MAX-ACCESS read-only
	STATUS  current
	DESCRIPTION
		"The number of Relay Ports"
	-- 1.3.6.1.4.1.28507.50.1.3.1.1
	::= { epc1292relayports 1 }


-- the Interfaces table
-- The Interfaces table contains information on the entity's
-- interfaces.  Each sub-layer below the internetwork-layer
-- of a network interface is considered to be an interface.

epc1292portTable OBJECT-TYPE
	SYNTAX  SEQUENCE OF Epc1292portEntry
	MAX-ACCESS not-accessible
	STATUS  current
	DESCRIPTION
		"list of all EPC Relay Ports"
	-- 1.3.6.1.4.1.28507.50.1.3.1.2
	::= { epc1292relayports 2 }


epc1292portEntry OBJECT-TYPE
	SYNTAX  Epc1292portEntry
	MAX-ACCESS not-accessible
	STATUS  current
	DESCRIPTION
		"An entry containing management information applicable to a
		particular relay port."
	INDEX {
		epc1292PortIndex }
	-- 1.3.6.1.4.1.28507.50.1.3.1.2.1
	::= { epc1292portTable 1 }


Epc1292portEntry ::= SEQUENCE {

	epc1292PortIndex        Integer32,
	epc1292PortName         OCTET STRING,
	epc1292PortState        INTEGER,
	epc1292PortSwitchCount  Integer32,
	epc1292PortStartupMode  INTEGER,
	epc1292PortStartupDelay Integer32,
	epc1292PortRepowerTime  Integer32 }


epc1292PortIndex OBJECT-TYPE
	SYNTAX  Integer32 (1..4)
	MAX-ACCESS read-only
	STATUS  current
	DESCRIPTION
		"A unique value, greater than zero, for each Relay Port."
	-- 1.3.6.1.4.1.28507.50.1.3.1.2.1.1
	::= { epc1292portEntry 1 }


epc1292PortName OBJECT-TYPE
	SYNTAX  OCTET STRING (SIZE (0..15))
	MAX-ACCESS read-write
	STATUS  current
	DESCRIPTION
		"A textual string containing name of a Relay Port."
	-- 1.3.6.1.4.1.28507.50.1.3.1.2.1.2
	::= { epc1292portEntry 2 }


epc1292PortState OBJECT-TYPE
	SYNTAX  INTEGER {
			off(0),
			on(1) }
	MAX-ACCESS read-write
	STATUS  current
	DESCRIPTION
		"current state of a Relay Port"
	-- 1.3.6.1.4.1.28507.50.1.3.1.2.1.3
	::= { epc1292portEntry 3 }


epc1292PortSwitchCount OBJECT-TYPE
	SYNTAX  Integer32
	MAX-ACCESS read-only
	STATUS  current
	DESCRIPTION
		"The total number of switch actions ocurred on a Relay Port.
		Does not count switch commands which will not switch
		the ralay state, so just real relay switches are displayed here."
	-- 1.3.6.1.4.1.28507.50.1.3.1.2.1.4
	::= { epc1292portEntry 4 }


epc1292PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.50.1.3.1.2.1.5
	::= { epc1292portEntry 5 }


epc1292PortStartupDelay OBJECT-TYPE
	SYNTAX  Integer32
	UNITS	"seconds"
	MAX-ACCESS read-write
	STATUS  current
	DESCRIPTION
		"Delay in sec for startup action"
	DEFVAL { 0 }
	-- 1.3.6.1.4.1.28507.50.1.3.1.2.1.6
	::= { epc1292portEntry 6 }


epc1292PortRepowerTime OBJECT-TYPE
	SYNTAX  Integer32 (0..65535)
	UNITS	"seconds"
	MAX-ACCESS read-write
	STATUS  current
	DESCRIPTION
		"Delay in sec for repower port after switching off"
	DEFVAL { 0 }
	-- 1.3.6.1.4.1.28507.50.1.3.1.2.1.7
	::= { epc1292portEntry 7 }


epc1292ExtActors OBJECT IDENTIFIER 
	-- 1.3.6.1.4.1.28507.50.1.4
	::= { epc1292Objects 4 }

epc1292IntSensors OBJECT IDENTIFIER 
	-- 1.3.6.1.4.1.28507.50.1.5
	::= { epc1292Objects 5 }

epc1292PowerChan OBJECT IDENTIFIER 
	-- 1.3.6.1.4.1.28507.50.1.5.1
	::= { epc1292IntSensors 1 }

epc1292ActivePowerChan OBJECT-TYPE
	SYNTAX  Unsigned32 (1)
	MAX-ACCESS read-only
	STATUS  current
	DESCRIPTION
		"Number of suppported Power Channels."
	-- 1.3.6.1.4.1.28507.50.1.5.1.1
	::= { epc1292PowerChan 1 }


epc1292PowerTable OBJECT-TYPE
	SYNTAX  SEQUENCE OF Epc1292PowerEntry
	MAX-ACCESS not-accessible
	STATUS  current
	DESCRIPTION
		"All available Channel Interfaces."
	-- 1.3.6.1.4.1.28507.50.1.5.1.2
	::= { epc1292PowerChan 2 }


epc1292PowerEntry OBJECT-TYPE
	SYNTAX  Epc1292PowerEntry
	MAX-ACCESS not-accessible
	STATUS  current
	DESCRIPTION
		"An entry containing management information
		applicable to a particular Power Channel."
	INDEX {
		epc1292PowerIndex }
	-- 1.3.6.1.4.1.28507.50.1.5.1.2.1
	::= { epc1292PowerTable 1 }


Epc1292PowerEntry ::= SEQUENCE {

	epc1292PowerIndex                   Integer32,
	epc1292ChanStatus                   Integer32,
	epc1292AbsEnergyActive              Gauge32,
	epc1292PowerActive                  Integer32,
	epc1292Current                      Gauge32,
	epc1292Voltage                      Gauge32,
	epc1292Frequency                    Gauge32,
	epc1292PowerFactor                  Integer32,
	epc1292Pangle                       Integer32,
	epc1292PowerApparent                Integer32,
	epc1292PowerReactive                Integer32,
	epc1292AbsEnergyReactive            Gauge32,
	epc1292AbsEnergyActiveResettable    Gauge32,
	epc1292AbsEnergyReactiveResettable  Gauge32,
	epc1292ResetTime                    Gauge32,
	epc1292ForwEnergyActive             Gauge32,
	epc1292ForwEnergyReactive           Gauge32,
	epc1292ForwEnergyActiveResettable   Gauge32,
	epc1292ForwEnergyReactiveResettable Gauge32,
	epc1292RevEnergyActive              Gauge32,
	epc1292RevEnergyReactive            Gauge32,
	epc1292RevEnergyActiveResettable    Gauge32,
	epc1292RevEnergyReactiveResettable  Gauge32 }


epc1292PowerIndex OBJECT-TYPE
	SYNTAX  Integer32 (1)
	MAX-ACCESS read-only
	STATUS  current
	DESCRIPTION
		"Index of Power Channel entries"
	-- 1.3.6.1.4.1.28507.50.1.5.1.2.1.1
	::= { epc1292PowerEntry 1 }


epc1292ChanStatus OBJECT-TYPE
	SYNTAX  Integer32 (0..1)
	MAX-ACCESS read-only
	STATUS  current
	DESCRIPTION
		"0 = data not active, 1 = data valid"
	-- 1.3.6.1.4.1.28507.50.1.5.1.2.1.2
	::= { epc1292PowerEntry 2 }


epc1292PowerActive OBJECT-TYPE
	SYNTAX  Integer32
	UNITS	"W"
	MAX-ACCESS read-only
	STATUS  current
	DESCRIPTION
		"Active Power"
	-- 1.3.6.1.4.1.28507.50.1.5.1.2.1.4
	::= { epc1292PowerEntry 4 }


epc1292PowerFactor OBJECT-TYPE
	SYNTAX  Integer32
	UNITS	"0.001"
	MAX-ACCESS read-only
	STATUS  current
	DESCRIPTION
		"Power Factor of Channel between
		-1.0 and 1.00"
	-- 1.3.6.1.4.1.28507.50.1.5.1.2.1.8
	::= { epc1292PowerEntry 8 }


epc1292Pangle OBJECT-TYPE
	SYNTAX  Integer32
	UNITS	"0.1 degree"
	MAX-ACCESS read-only
	STATUS  current
	DESCRIPTION
		"Phase Angle between Voltage
		and L Line Current between
		-180.0 and 180.0"
	-- 1.3.6.1.4.1.28507.50.1.5.1.2.1.9
	::= { epc1292PowerEntry 9 }


epc1292PowerApparent OBJECT-TYPE
	SYNTAX  Integer32
	UNITS	"VA"
	MAX-ACCESS read-only
	STATUS  current
	DESCRIPTION
		"L Line Mean Apparent Power"
	-- 1.3.6.1.4.1.28507.50.1.5.1.2.1.10
	::= { epc1292PowerEntry 10 }


epc1292PowerReactive OBJECT-TYPE
	SYNTAX  Integer32
	UNITS	"VAR"
	MAX-ACCESS read-only
	STATUS  current
	DESCRIPTION
		"L Line Mean Reactive Power"
	-- 1.3.6.1.4.1.28507.50.1.5.1.2.1.11
	::= { epc1292PowerEntry 11 }


epc1292OVPTable OBJECT-TYPE
	SYNTAX  SEQUENCE OF Epc1292OVPEntry
	MAX-ACCESS not-accessible
	STATUS  current
	DESCRIPTION
		"Overvoltage Protection Table"
	-- 1.3.6.1.4.1.28507.50.1.5.2
	::= { epc1292IntSensors 2 }


epc1292OVPEntry OBJECT-TYPE
	SYNTAX  Epc1292OVPEntry
	MAX-ACCESS not-accessible
	STATUS  current
	DESCRIPTION ""
	INDEX {
		epc1292OVPIndex }
	-- 1.3.6.1.4.1.28507.50.1.5.2.1
	::= { epc1292OVPTable 1 }


Epc1292OVPEntry ::= SEQUENCE {

	epc1292OVPIndex  Integer32,
	epc1292OVPStatus INTEGER }


epc1292OVPIndex OBJECT-TYPE
	SYNTAX  Integer32 (1)
	MAX-ACCESS read-only
	STATUS  current
	DESCRIPTION ""
	-- 1.3.6.1.4.1.28507.50.1.5.2.1.1
	::= { epc1292OVPEntry 1 }


epc1292ExtSensors OBJECT IDENTIFIER 
	-- 1.3.6.1.4.1.28507.50.1.6
	::= { epc1292Objects 6 }

epc1292SensorTable OBJECT-TYPE
	SYNTAX  SEQUENCE OF Epc1292SensorEntry
	MAX-ACCESS not-accessible
	STATUS  current
	DESCRIPTION ""
	-- 1.3.6.1.4.1.28507.50.1.6.1
	::= { epc1292ExtSensors 1 }


epc1292SensorEntry OBJECT-TYPE
	SYNTAX  Epc1292SensorEntry
	MAX-ACCESS not-accessible
	STATUS  current
	DESCRIPTION ""
	INDEX {
		epc1292SensorIndex }
	-- 1.3.6.1.4.1.28507.50.1.6.1.1
	::= { epc1292SensorTable 1 }


Epc1292SensorEntry ::= SEQUENCE {

	epc1292SensorIndex  Integer32,
	epc1292TempSensor   Integer32,
	epc1292HygroSensor  Integer32,
	epc1292InputSensor  INTEGER,
	epc1292AirPressure  Integer32,
	epc1292DewPoint     Integer32,
	epc1292DewPointDiff Integer32 }


epc1292SensorIndex OBJECT-TYPE
	SYNTAX  Integer32 (1)
	MAX-ACCESS read-only
	STATUS  current
	DESCRIPTION ""
	-- 1.3.6.1.4.1.28507.50.1.6.1.1.1
	::= { epc1292SensorEntry 1 }


epc1292TempSensor OBJECT-TYPE
	SYNTAX  Integer32
	UNITS	"0.1 degree Celsius"
	MAX-ACCESS read-only
	STATUS  current
	DESCRIPTION
		"actual temperature"
	-- 1.3.6.1.4.1.28507.50.1.6.1.1.2
	::= { epc1292SensorEntry 2 }


epc1292HygroSensor OBJECT-TYPE
	SYNTAX  Integer32
	UNITS	"0.1 percent humidity"
	MAX-ACCESS read-only
	STATUS  current
	DESCRIPTION
		"actual humidity"
	-- 1.3.6.1.4.1.28507.50.1.6.1.1.3
	::= { epc1292SensorEntry 3 }


epc1292InputSensor OBJECT-TYPE
	SYNTAX  INTEGER {
			off(0),
			on(1) }
	MAX-ACCESS read-only
	STATUS  current
	DESCRIPTION
		"logical state of input sensor"
	-- 1.3.6.1.4.1.28507.50.1.6.1.1.4
	::= { epc1292SensorEntry 4 }


-- Conformance
--

epc1292Conf OBJECT IDENTIFIER 
	-- 1.3.6.1.4.1.28507.50.2
	::= { gadsEPC1292 2 }

-- Groups
--

epc1292Groups OBJECT IDENTIFIER 
	-- 1.3.6.1.4.1.28507.50.2.1
	::= { epc1292Conf 1 }

-- Compliance
--

epc1292Compls OBJECT IDENTIFIER 
	-- 1.3.6.1.4.1.28507.50.2.2
	::= { epc1292Conf 2 }


epc1292SwitchEvtPort NOTIFICATION-TYPE
	OBJECTS {
		epc1292PortIndex,
		epc1292PortName,
		epc1292PortState,
		epc1292PortSwitchCount}
	STATUS  current
	DESCRIPTION
		"Event is triggered when a port is switched"
	-- 1.3.6.1.4.1.28507.50.3.1
	::= { events 1 }


epc1292LineAmperageEvt NOTIFICATION-TYPE
	OBJECTS {
		epc1292PowerIndex,
		epc1292PowerActive,
		epc1292Current,
		epc1292Voltage,
		epc1292Frequency,
		epc1292PowerApparent,
		epc1292PowerReactive}
	STATUS  current
	DESCRIPTION
		"Event is triggered when a measured
		current is crossing the entered limits"
	-- 1.3.6.1.4.1.28507.50.3.8
	::= { events 8 }


epc1292TempEvtSen NOTIFICATION-TYPE
	OBJECTS {
		epc1292SensorIndex,
		epc1292TempSensor}
	STATUS  current
	DESCRIPTION
		"temperature limits exceeded"
	-- 1.3.6.1.4.1.28507.50.3.2
	::= { events 2 }


epc1292InputEvtSen NOTIFICATION-TYPE
	OBJECTS {
		epc1292SensorIndex,
		epc1292InputSensor}
	STATUS  current
	DESCRIPTION
		"change of logical input sensor state"
	-- 1.3.6.1.4.1.28507.50.3.4
	::= { events 4 }


epc1292OVPEvt NOTIFICATION-TYPE
	OBJECTS {
		epc1292OVPStatus}
	STATUS  current
	DESCRIPTION
		"Event is triggered when the OVP status changes"
	-- 1.3.6.1.4.1.28507.50.3.7
	::= { events 7 }

epc1292BasicGroup OBJECT-GROUP
	OBJECTS {
		epc1292TrapCtrl,
		epc1292TrapIPIndex,
		epc1292TrapAddr,
		epc1292portNumber,
		epc1292PortIndex,
		epc1292PortName,
		epc1292PortState,
		epc1292PortSwitchCount,
		epc1292PortStartupMode,
		epc1292PortStartupDelay,
		epc1292PortRepowerTime,
		epc1292ActivePowerChan,
		epc1292PowerIndex,
		epc1292ChanStatus,
		epc1292AbsEnergyActive,
		epc1292PowerActive,
		epc1292Current,
		epc1292Voltage,
		epc1292Frequency,
		epc1292PowerFactor,
		epc1292Pangle,
		epc1292PowerApparent,
		epc1292PowerReactive,
		epc1292AbsEnergyReactive,
		epc1292AbsEnergyActiveResettable,
		epc1292AbsEnergyReactiveResettable,
		epc1292ResetTime,
		epc1292ForwEnergyActive,
		epc1292ForwEnergyReactive,
		epc1292ForwEnergyActiveResettable,
		epc1292ForwEnergyReactiveResettable,
		epc1292RevEnergyActive,
		epc1292RevEnergyReactive,
		epc1292RevEnergyActiveResettable,
		epc1292RevEnergyReactiveResettable,
		epc1292OVPIndex,
		epc1292OVPStatus,
		epc1292SensorIndex,
		epc1292TempSensor,
		epc1292HygroSensor,
		epc1292InputSensor,
		epc1292AirPressure,
		epc1292DewPoint,
		epc1292DewPointDiff }
	STATUS  current
	DESCRIPTION
		"Basic objects."
	-- 1.3.6.1.4.1.28507.50.2.1.1
	::= { epc1292Groups 1 }

epc1292NotificationGroup NOTIFICATION-GROUP
	NOTIFICATIONS {
		epc1292SwitchEvtPort,
		epc1292TempEvtSen,
		epc1292InputEvtSen,
		epc1292AirPressureEvtSen,
		epc1292DewPtDiffEvtSen,
		epc1292OVPEvt,
		epc1292LineAmperageEvt,
		epc1292HygroEvtSen }
	STATUS  current
	DESCRIPTION
		""
	-- 1.3.6.1.4.1.28507.50.2.1.2
	::= { epc1292Groups 2 }

epc1292AbsEnergyActive OBJECT-TYPE
	SYNTAX  Gauge32
	UNITS	"Wh"
	MAX-ACCESS read-only
	STATUS  current
	DESCRIPTION
		"Absolute Active Energy counter."
	-- 1.3.6.1.4.1.28507.50.1.5.1.2.1.3
	::= { epc1292PowerEntry 3 }


epc1292Current OBJECT-TYPE
	SYNTAX  Gauge32
	UNITS	"mA"
	MAX-ACCESS read-only
	STATUS  current
	DESCRIPTION
		"Actual Curent on Power Channel."
	-- 1.3.6.1.4.1.28507.50.1.5.1.2.1.5
	::= { epc1292PowerEntry 5 }


epc1292Voltage OBJECT-TYPE
	SYNTAX  Gauge32
	UNITS	"V"
	MAX-ACCESS read-only
	STATUS  current
	DESCRIPTION
		"Actual Voltage on Power Channel"
	-- 1.3.6.1.4.1.28507.50.1.5.1.2.1.6
	::= { epc1292PowerEntry 6 }


epc1292Frequency OBJECT-TYPE
	SYNTAX  Gauge32
	UNITS	"0.01 hz"
	MAX-ACCESS read-only
	STATUS  current
	DESCRIPTION
		"Frequency of Power Channel"
	-- 1.3.6.1.4.1.28507.50.1.5.1.2.1.7
	::= { epc1292PowerEntry 7 }


epc1292AbsEnergyReactive OBJECT-TYPE
	SYNTAX  Gauge32
	UNITS	"VARh"
	MAX-ACCESS read-only
	STATUS  current
	DESCRIPTION
		"Absolute Reactive Energy counter."
	-- 1.3.6.1.4.1.28507.50.1.5.1.2.1.12
	::= { epc1292PowerEntry 12 }


epc1292AbsEnergyActiveResettable OBJECT-TYPE
	SYNTAX  Gauge32
	UNITS	"Wh"
	MAX-ACCESS read-write
	STATUS  current
	DESCRIPTION
		"Resettable Absolute Active Energy counter.
		Writing '0' resets all resettable counter."
	-- 1.3.6.1.4.1.28507.50.1.5.1.2.1.13
	::= { epc1292PowerEntry 13 }


epc1292AbsEnergyReactiveResettable OBJECT-TYPE
	SYNTAX  Gauge32
	UNITS	"VARh"
	MAX-ACCESS read-only
	STATUS  current
	DESCRIPTION
		"Resettable Absolute Reactive Energy counter."
	-- 1.3.6.1.4.1.28507.50.1.5.1.2.1.14
	::= { epc1292PowerEntry 14 }


epc1292ResetTime OBJECT-TYPE
	SYNTAX  Gauge32
	UNITS	"s"
	MAX-ACCESS read-only
	STATUS  current
	DESCRIPTION
		"Time in seconds since last Energy
		Counter reset."
	-- 1.3.6.1.4.1.28507.50.1.5.1.2.1.15
	::= { epc1292PowerEntry 15 }


epc1292ForwEnergyActive OBJECT-TYPE
	SYNTAX  Gauge32
	UNITS	"Wh"
	MAX-ACCESS read-only
	STATUS  current
	DESCRIPTION
		"Forward Active Energy counter."
	-- 1.3.6.1.4.1.28507.50.1.5.1.2.1.16
	::= { epc1292PowerEntry 16 }


epc1292ForwEnergyReactive OBJECT-TYPE
	SYNTAX  Gauge32
	UNITS	"VARh"
	MAX-ACCESS read-only
	STATUS  current
	DESCRIPTION
		"Forward Reactive Energy counter."
	-- 1.3.6.1.4.1.28507.50.1.5.1.2.1.17
	::= { epc1292PowerEntry 17 }


epc1292ForwEnergyActiveResettable OBJECT-TYPE
	SYNTAX  Gauge32
	UNITS	"Wh"
	MAX-ACCESS read-only
	STATUS  current
	DESCRIPTION
		"Resettable Forward Active Energy counter."
	-- 1.3.6.1.4.1.28507.50.1.5.1.2.1.18
	::= { epc1292PowerEntry 18 }


epc1292ForwEnergyReactiveResettable OBJECT-TYPE
	SYNTAX  Gauge32
	UNITS	"VARh"
	MAX-ACCESS read-only
	STATUS  current
	DESCRIPTION
		"Resettable Forward Reactive Energy counter."
	-- 1.3.6.1.4.1.28507.50.1.5.1.2.1.19
	::= { epc1292PowerEntry 19 }


epc1292RevEnergyActive OBJECT-TYPE
	SYNTAX  Gauge32
	UNITS	"Wh"
	MAX-ACCESS read-only
	STATUS  current
	DESCRIPTION
		"Reverse Active Energy counter."
	-- 1.3.6.1.4.1.28507.50.1.5.1.2.1.20
	::= { epc1292PowerEntry 20 }


epc1292RevEnergyReactive OBJECT-TYPE
	SYNTAX  Gauge32
	UNITS	"VARh"
	MAX-ACCESS read-only
	STATUS  current
	DESCRIPTION
		"Reverse Reactive Energy counter."
	-- 1.3.6.1.4.1.28507.50.1.5.1.2.1.21
	::= { epc1292PowerEntry 21 }


epc1292RevEnergyActiveResettable OBJECT-TYPE
	SYNTAX  Gauge32
	UNITS	"Wh"
	MAX-ACCESS read-only
	STATUS  current
	DESCRIPTION
		"Resettable Reverse Active Energy counter."
	-- 1.3.6.1.4.1.28507.50.1.5.1.2.1.22
	::= { epc1292PowerEntry 22 }


epc1292RevEnergyReactiveResettable OBJECT-TYPE
	SYNTAX  Gauge32
	UNITS	"VARh"
	MAX-ACCESS read-only
	STATUS  current
	DESCRIPTION
		"Resettable Reverse Reactive Energy counter."
	-- 1.3.6.1.4.1.28507.50.1.5.1.2.1.23
	::= { epc1292PowerEntry 23 }



epc1292AirPressureEvtSen NOTIFICATION-TYPE
	OBJECTS {
		epc1292SensorIndex,
		epc1292AirPressure}
	STATUS  current
	DESCRIPTION
		"Air Pressure limits exceeded"
	-- 1.3.6.1.4.1.28507.50.3.5
	::= { events 5 }


epc1292DewPtDiffEvtSen NOTIFICATION-TYPE
	OBJECTS {
		epc1292SensorIndex,
		epc1292DewPointDiff}
	STATUS  current
	DESCRIPTION
		"Dew Point Difference limits exceeded"
	-- 1.3.6.1.4.1.28507.50.3.6
	::= { events 6 }

epc1292AirPressure OBJECT-TYPE
	SYNTAX  Integer32
	UNITS	"1 hPA (hectopascal) ~ 1 milibar"
	MAX-ACCESS read-only
	STATUS  current
	DESCRIPTION
		"actual air pressure"
	-- 1.3.6.1.4.1.28507.50.1.6.1.1.5
	::= { epc1292SensorEntry 5 }


epc1292DewPoint OBJECT-TYPE
	SYNTAX  Integer32
	UNITS	"0.1 degree Celsius"
	MAX-ACCESS read-only
	STATUS  current
	DESCRIPTION
		"dew point for actual temperature and humidity"
	-- 1.3.6.1.4.1.28507.50.1.6.1.1.6
	::= { epc1292SensorEntry 6 }


epc1292DewPointDiff OBJECT-TYPE
	SYNTAX  Integer32
	UNITS	"0.1 degree Celsius"
	MAX-ACCESS read-only
	STATUS  current
	DESCRIPTION
		"difference between dew point and actual
		temperature (Temp - DewPoint)"
	-- 1.3.6.1.4.1.28507.50.1.6.1.1.7
	::= { epc1292SensorEntry 7 }


epc1292OVPStatus OBJECT-TYPE
	SYNTAX  INTEGER {
			unknown(2),
			ok(1),
			failure(0) }
	MAX-ACCESS read-only
	STATUS  current
	DESCRIPTION
		"shows the status of the
		built-in Overvoltage Protection"
	-- 1.3.6.1.4.1.28507.50.1.5.2.1.2
::= { epc1292OVPEntry 2 }


END
