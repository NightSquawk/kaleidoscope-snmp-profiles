-- ########################################################################
-- #
-- # CLAVISTER-STREAM-MIB:	Clavister AB
-- #
-- # Copyright (c) by Clavister AB
-- # All rights reserved.
-- #
-- ########################################################################

CLAVISTER-STREAM-MIB DEFINITIONS ::= BEGIN

IMPORTS
    clavisterMibConfs,
    clavisterMibModules,
    clavisterMibObjectGroups,
    clavisterSystemStats
        FROM CLAVISTER-SMI
    MODULE-COMPLIANCE, OBJECT-GROUP
        FROM SNMPv2-CONF
    Counter32,
    Counter64,
    Gauge32,
    Integer32,
    Unsigned32,
    TimeTicks,
    MODULE-IDENTITY,
    OBJECT-TYPE
        FROM SNMPv2-SMI
    DisplayString
        FROM SNMPv2-TC
    CounterBasedGauge64
          FROM HCNUM-TC
    ;

clavisterStatsMibModule MODULE-IDENTITY
    LAST-UPDATED "202111190000Z"
    ORGANIZATION 
        "Clavister AB"
    CONTACT-INFO
        "Clavister Support

         Sjogatan 6J
         SE-891 60 ORNSKOLDSVIK
         SWEDEN

         Tel: +46-660-299200
         http://www.clavister.com"
    DESCRIPTION
        "The MIB module for Clavister cOS Stream products."
    REVISION  "202111190000Z"
    DESCRIPTION
        "Updated statistical values in HA and NATPool."
    REVISION  "202005150000Z"
    DESCRIPTION
        "Added additional statistics for memory and SSLVPN."
    REVISION  "202003020000Z"
    DESCRIPTION
        "Log receiver updates."
    REVISION  "201908150000Z"
    DESCRIPTION
        "Added statistics for Application Control Audit Mode."
    REVISION  "201905070000Z"
    DESCRIPTION
        "Renamed 'unsupported message type' statistic for GTP Inspection"
    REVISION  "201904250000Z"
    DESCRIPTION
        "Added additional statistics for GTP Inspection."
    REVISION  "201902070000Z"
    DESCRIPTION
        "Additional statistics for SNMP engine."
    REVISION  "201812100000Z"
    DESCRIPTION
        "Added statistics for GTP Inspection and SSL Inspection."
    REVISION  "201806200000Z"
    DESCRIPTION
        "Added SSLVPN statistics."
    REVISION  "201806050000Z"
    DESCRIPTION
        "Added statistics for SNMPv3, IPS scan limit, product name as well as threshold rule statistics for limits and actions."
    REVISION  "201806040000Z"
    DESCRIPTION
        "Added Worker CPU usage statistics."
    REVISION  "201710190000Z"
    DESCRIPTION
        "More IPS statistics additions."
    REVISION  "201710170000Z"
    DESCRIPTION
        "Updates for rule usage counter statistics."
    REVISION  "201710100000Z"
    DESCRIPTION
        "added IPS statistics."
    REVISION  "201709250000Z"
    DESCRIPTION
        "Added rule 'hit' counters for IP and threshold rules."
    REVISION  "201707120000Z"
    DESCRIPTION
        "Minor updates."
    REVISION  "201705190000Z"
    DESCRIPTION
        "Added SIP statistics values."
    REVISION  "201704270000Z"
    DESCRIPTION
        "Adding statistical values for SIP and DNS ALGs."
    REVISION  "201612010000Z"
    DESCRIPTION
        "Added SCTP specific values to Deterministic NATPool statistics."
    REVISION  "201611250000Z"
    DESCRIPTION
        "Added NATPool and forwarding statistics values."
    REVISION  "201610170000Z"
    DESCRIPTION
        "Added some statistics for Blacklisting, Threshold Rules, FTP ALG and NDP."
    REVISION  "201609150000Z"
    DESCRIPTION
        "Added additional NAT pool statistics."
    REVISION  "201606080000Z"
    DESCRIPTION
        "Added NAT-pool statistics."
    REVISION  "201604190000Z"
    DESCRIPTION
        "Nokia."
    REVISION  "201511200000Z"
    DESCRIPTION
        "Modified the description for a few statistical values."
    REVISION  "201510280000Z"
    DESCRIPTION
        "Added statistical values regarding management and device information."
    REVISION  "201510270000Z"
    DESCRIPTION
        "Added additional statistics for interfaces, CPU usage and DHCP server."
    REVISION  "201510260000Z"
    DESCRIPTION
        "Added crypto device statistics."
    REVISION  "201509090000Z"
    DESCRIPTION
        "Added statistics related to time sync status."
    REVISION  "201505060000Z"
    DESCRIPTION
        "Added route monitoring statistics."
    REVISION  "201412190000Z"
    DESCRIPTION
        "statistics update."
    REVISION  "201412180000Z"
    DESCRIPTION
        "Statistics update."
    REVISION  "201411260000Z"
    DESCRIPTION
        "Added pipe statistics."
    REVISION  "201404240000Z"
    DESCRIPTION
        "Added flow statistics."
    REVISION  "201309100000Z"
    DESCRIPTION
        "misc reorganization."
    REVISION  "201306200000Z"
    DESCRIPTION
        "Moved DHCPServer to Services folder."
    REVISION  "201306190000Z"
    DESCRIPTION
        "Adding various statistics."
    REVISION  "201206290000Z"
    DESCRIPTION
        "Updated HA statistics."
    REVISION    "201206270900Z"
    DESCRIPTION 
        "Updated with regards to name change."
    REVISION  "201203300000Z"
    DESCRIPTION
        "Adding statistical values for OSPF, EAP-MD5, DHCPServer and IKEv1."        
    REVISION  "201111180000Z"
    DESCRIPTION
        "Updating some descriptions."
    REVISION  "201110210000Z"
    DESCRIPTION
        "Added some IKE statistics etc."
    REVISION  "201109150000Z"
    DESCRIPTION
        "Statistics update."
    REVISION  "201109090000Z"
    DESCRIPTION
        "Statistics update."
    REVISION  "201107140000Z"
    DESCRIPTION
        "Updated statistics values."
    REVISION  "201009130000Z"
    DESCRIPTION
        "first edition."
    ::= { clavisterMibModules 1 }

ssmSystem OBJECT IDENTIFIER
    ::= { clavisterSystemStats 2005 }

ssmSysContact OBJECT-TYPE
    SYNTAX      DisplayString
    MAX-ACCESS  read-only
    STATUS      current
    DESCRIPTION 
        "Identity and contact information of a person responsible for
         this managed node."
    ::= { ssmSystem 1005 }

ssmSysName OBJECT-TYPE
    SYNTAX      DisplayString
    MAX-ACCESS  read-only
    STATUS      current
    DESCRIPTION 
        "A name assigned to this node by the administrator."
    ::= { ssmSystem 1010 }

ssmSysLocation OBJECT-TYPE
    SYNTAX      DisplayString
    MAX-ACCESS  read-only
    STATUS      current
    DESCRIPTION 
        "Physical location of this node."
    ::= { ssmSystem 1015 }

ssmVendorName OBJECT-TYPE
    SYNTAX      DisplayString
    MAX-ACCESS  read-only
    STATUS      current
    DESCRIPTION 
        "Vendor name."
    ::= { ssmSystem 1020 }

ssmHardwareModel OBJECT-TYPE
    SYNTAX      DisplayString
    MAX-ACCESS  read-only
    STATUS      current
    DESCRIPTION 
        "Hardware model."
    ::= { ssmSystem 1030 }

ssmProductName OBJECT-TYPE
    SYNTAX      DisplayString
    MAX-ACCESS  read-only
    STATUS      current
    DESCRIPTION 
        "Product name."
    ::= { ssmSystem 1033 }

ssmHardwareSerialNumber OBJECT-TYPE
    SYNTAX      DisplayString
    MAX-ACCESS  read-only
    STATUS      current
    DESCRIPTION 
        "Hardware serial number."
    ::= { ssmSystem 1035 }

ssmHardwareDateOfManufacture OBJECT-TYPE
    SYNTAX      DisplayString
    MAX-ACCESS  read-only
    STATUS      current
    DESCRIPTION 
        "Date of manufacture."
    ::= { ssmSystem 1040 }

ssmFlow OBJECT IDENTIFIER
    ::= { ssmSystem 2010 }

ssmFlowsCurrent OBJECT-TYPE
    SYNTAX      Unsigned32
    MAX-ACCESS  read-only
    STATUS      current
    DESCRIPTION 
        "Number of flows in the system."
    ::= { ssmFlow 1005 }

ssmFlowLimit OBJECT-TYPE
    SYNTAX      Unsigned32
    MAX-ACCESS  read-only
    STATUS      current
    DESCRIPTION 
        "Maximum number of flows allowed in the system."
    ::= { ssmFlow 1010 }

ssmFlowsIPv4 OBJECT-TYPE
    SYNTAX      Unsigned32
    MAX-ACCESS  read-only
    STATUS      current
    DESCRIPTION 
        "Number of IPv4 flows in the system."
    ::= { ssmFlow 1015 }

ssmFlowsIPv6 OBJECT-TYPE
    SYNTAX      Unsigned32
    MAX-ACCESS  read-only
    STATUS      current
    DESCRIPTION 
        "Number of IPv6 flows in the system."
    ::= { ssmFlow 1020 }

ssmFlowsOpened OBJECT-TYPE
    SYNTAX      Counter32
    MAX-ACCESS  read-only
    STATUS      current
    DESCRIPTION 
        "Number of flows opened."
    ::= { ssmFlow 1025 }

ssmFlowsClosed OBJECT-TYPE
    SYNTAX      Counter32
    MAX-ACCESS  read-only
    STATUS      current
    DESCRIPTION 
        "Number of flows closed."
    ::= { ssmFlow 1030 }

ssmFlowsReplaced OBJECT-TYPE
    SYNTAX      Counter32
    MAX-ACCESS  read-only
    STATUS      current
    DESCRIPTION 
        "Number of flows closed to allow a new flow to be opened when the
         flow table was full."
    ::= { ssmFlow 1035 }

ssmCPU OBJECT IDENTIFIER
    ::= { ssmSystem 2020 }

ssmCtrlPlaneCpuUsage OBJECT-TYPE
    SYNTAX      Gauge32 (0..100)
    MAX-ACCESS  read-only
    STATUS      current
    DESCRIPTION 
        "Total CPU usage in control plane."
    ::= { ssmCPU 1005 }

ssmCtrlPlaneCpuMax OBJECT-TYPE
    SYNTAX      Gauge32 (0..100)
    MAX-ACCESS  read-only
    STATUS      current
    DESCRIPTION 
        "Maximum recorded CPU usage in control plane."
    ::= { ssmCPU 1006 }

ssmCtrlPlaneCpuAverage OBJECT-TYPE
    SYNTAX      Gauge32 (0..100)
    MAX-ACCESS  read-only
    STATUS      current
    DESCRIPTION 
        "Average (for the last 10 minutes) CPU usage in control plane."
    ::= { ssmCPU 1007 }

ssmFastPathCpuUsage OBJECT-TYPE
    SYNTAX      Gauge32 (0..100)
    MAX-ACCESS  read-only
    STATUS      current
    DESCRIPTION 
        "Total CPU usage for all fast path CPUs."
    ::= { ssmCPU 1010 }

ssmFastPathCpuMax OBJECT-TYPE
    SYNTAX      Gauge32 (0..100)
    MAX-ACCESS  read-only
    STATUS      current
    DESCRIPTION 
        "Maximum recorded CPU usage for all fast path CPUs."
    ::= { ssmCPU 1011 }

ssmFastPathCpuAverage OBJECT-TYPE
    SYNTAX      Gauge32 (0..100)
    MAX-ACCESS  read-only
    STATUS      current
    DESCRIPTION 
        "Average (for the last 10 minutes) CPU usage for all fast path
         CPUs."
    ::= { ssmCPU 1012 }

ssmSlowPathCpuUsage OBJECT-TYPE
    SYNTAX      Gauge32 (0..100)
    MAX-ACCESS  read-only
    STATUS      current
    DESCRIPTION 
        "Total CPU usage for all slow path CPUs."
    ::= { ssmCPU 1015 }

ssmSlowPathCpuMax OBJECT-TYPE
    SYNTAX      Gauge32 (0..100)
    MAX-ACCESS  read-only
    STATUS      current
    DESCRIPTION 
        "Maximum recorded CPU usage for all slow path CPUs."
    ::= { ssmCPU 1016 }

ssmSlowPathCpuAverage OBJECT-TYPE
    SYNTAX      Gauge32 (0..100)
    MAX-ACCESS  read-only
    STATUS      current
    DESCRIPTION 
        "Average (for the last 10 minutes) CPU usage for all slow path
         CPUs."
    ::= { ssmCPU 1017 }

ssmWorkerCpuUsage OBJECT-TYPE
    SYNTAX      Gauge32 (0..100)
    MAX-ACCESS  read-only
    STATUS      current
    DESCRIPTION 
        "Total CPU usage for all worker CPUs."
    ::= { ssmCPU 1020 }

ssmWorkerCpuAverage OBJECT-TYPE
    SYNTAX      Gauge32 (0..100)
    MAX-ACCESS  read-only
    STATUS      current
    DESCRIPTION 
        "Average (for the last 10 minutes) CPU usage for all worker CPUs."
    ::= { ssmCPU 1021 }

ssmWorkerCpuMax OBJECT-TYPE
    SYNTAX      Gauge32 (0..100)
    MAX-ACCESS  read-only
    STATUS      current
    DESCRIPTION 
        "Maximum recorded CPU usage for all worker CPUs."
    ::= { ssmCPU 1022 }

ssmCpuStatsTable OBJECT-TYPE
    SYNTAX      SEQUENCE OF SsmCpuStatsEntry
    MAX-ACCESS  not-accessible
    STATUS      current
    DESCRIPTION 
        "CPU statistics table."
    ::= { ssmCPU 3000 }

ssmCpuStatsEntry OBJECT-TYPE
    SYNTAX      SsmCpuStatsEntry
    MAX-ACCESS  not-accessible
    STATUS      current
    DESCRIPTION 
        "The row in a table of CPU statistics."
    INDEX       { ssmCpuIndex }
    ::= { ssmCpuStatsTable 1 }

SsmCpuStatsEntry ::= SEQUENCE {
    ssmCpuIndex    Integer32,
    ssmCpuName    DisplayString,
    ssmCpuUsage    Gauge32
}

ssmCpuIndex OBJECT-TYPE
    SYNTAX      Integer32 (1..2147483647)
    MAX-ACCESS  not-accessible
    STATUS      current
    DESCRIPTION 
        "CPU index."
    ::= { ssmCpuStatsEntry 1 }

ssmCpuUsage OBJECT-TYPE
    SYNTAX      Gauge32 (0..100)
    MAX-ACCESS  read-only
    STATUS      current
    DESCRIPTION 
        "CPU usage."
    ::= { ssmCpuStatsEntry 1010 }

ssmCpuName OBJECT-TYPE
    SYNTAX      DisplayString
    MAX-ACCESS  read-only
    STATUS      current
    DESCRIPTION 
        "CPU name."
    ::= { ssmCpuStatsEntry 2 }

ssmMemory OBJECT IDENTIFIER
    ::= { ssmSystem 2030 }

ssmCtrlPlaneMemUsage OBJECT-TYPE
    SYNTAX      CounterBasedGauge64
    MAX-ACCESS  read-only
    STATUS      current
    DESCRIPTION 
        "Amount of memory used in control plane."
    ::= { ssmMemory 1005 }

ssmCtrlPlaneMemFree OBJECT-TYPE
    SYNTAX      CounterBasedGauge64
    MAX-ACCESS  read-only
    STATUS      current
    DESCRIPTION 
        "Amount of free memory in Control Plane."
    ::= { ssmMemory 1010 }

ssmCtrlPlaneMemTot OBJECT-TYPE
    SYNTAX      CounterBasedGauge64
    MAX-ACCESS  read-only
    STATUS      current
    DESCRIPTION 
        "Total amount of memory in control plane."
    ::= { ssmMemory 1015 }

ssmCtrlPlaneMemRegistered OBJECT-TYPE
    SYNTAX      CounterBasedGauge64
    MAX-ACCESS  read-only
    STATUS      current
    DESCRIPTION 
        "Amount of registered memory in Control Plane."
    ::= { ssmMemory 1018 }

ssmDataPlaneMemUsage OBJECT-TYPE
    SYNTAX      CounterBasedGauge64
    MAX-ACCESS  read-only
    STATUS      current
    DESCRIPTION 
        "Amount of memory used in Data Plane."
    ::= { ssmMemory 1020 }

ssmDataPlaneMemFree OBJECT-TYPE
    SYNTAX      CounterBasedGauge64
    MAX-ACCESS  read-only
    STATUS      current
    DESCRIPTION 
        "Amount of free memory in Data Plane."
    ::= { ssmMemory 1025 }

ssmDataPlaneMemTot OBJECT-TYPE
    SYNTAX      CounterBasedGauge64
    MAX-ACCESS  read-only
    STATUS      current
    DESCRIPTION 
        "Total amount of memory in Data Plane."
    ::= { ssmMemory 1030 }

ssmDataPlaneMemRegistered OBJECT-TYPE
    SYNTAX      CounterBasedGauge64
    MAX-ACCESS  read-only
    STATUS      current
    DESCRIPTION 
        "Amount of registered memory in Data Plane."
    ::= { ssmMemory 1033 }

ssmMemCatTable OBJECT-TYPE
    SYNTAX      SEQUENCE OF SsmMemCatEntry
    MAX-ACCESS  not-accessible
    STATUS      current
    DESCRIPTION 
        "Memory statistics for memory categories."
    ::= { ssmMemory 3010 }

ssmMemCatEntry OBJECT-TYPE
    SYNTAX      SsmMemCatEntry
    MAX-ACCESS  not-accessible
    STATUS      current
    DESCRIPTION 
        "The row in a table of memory statistics for a memory category."
    INDEX       { ssmMemCatIndex }
    ::= { ssmMemCatTable 1 }

SsmMemCatEntry ::= SEQUENCE {
    ssmMemCatIndex                 Integer32,
    ssmMemCatName                  DisplayString,
    ssmMemCatCtrlPlaneUsage        CounterBasedGauge64,
    ssmMemCatDataPlaneUsage        CounterBasedGauge64
}

ssmMemCatIndex OBJECT-TYPE
    SYNTAX      Integer32 (1..2147483647)
    MAX-ACCESS  not-accessible
    STATUS      current
    DESCRIPTION 
        "Category index."
    ::= { ssmMemCatEntry 1 }

ssmMemCatCtrlPlaneUsage OBJECT-TYPE
    SYNTAX      CounterBasedGauge64
    MAX-ACCESS  read-only
    STATUS      current
    DESCRIPTION 
        "Amount of memory used by category in control plane."
    ::= { ssmMemCatEntry 1010 }

ssmMemCatDataPlaneUsage OBJECT-TYPE
    SYNTAX      CounterBasedGauge64
    MAX-ACCESS  read-only
    STATUS      current
    DESCRIPTION 
        "Amount of memory used by category in data plane."
    ::= { ssmMemCatEntry 1015 }

ssmMemCatName OBJECT-TYPE
    SYNTAX      DisplayString
    MAX-ACCESS  read-only
    STATUS      current
    DESCRIPTION 
        "Name of category."
    ::= { ssmMemCatEntry 2 }

ssmMemProcessTable OBJECT-TYPE
    SYNTAX      SEQUENCE OF SsmMemProcessEntry
    MAX-ACCESS  not-accessible
    STATUS      current
    DESCRIPTION 
        "Memory statistics for Control Plane processes."
    ::= { ssmMemory 3020 }

ssmMemProcessEntry OBJECT-TYPE
    SYNTAX      SsmMemProcessEntry
    MAX-ACCESS  not-accessible
    STATUS      current
    DESCRIPTION 
        "The row in a table of memory statistics for a Control Plane
         process."
    INDEX       { ssmMemProcessIndex }
    ::= { ssmMemProcessTable 1 }

SsmMemProcessEntry ::= SEQUENCE {
    ssmMemProcessIndex     Integer32,
    ssmMemProcessName      DisplayString,
    ssmMemProcessUsage     CounterBasedGauge64
}

ssmMemProcessIndex OBJECT-TYPE
    SYNTAX      Integer32 (1..2147483647)
    MAX-ACCESS  not-accessible
    STATUS      current
    DESCRIPTION 
        "Control Plane process index."
    ::= { ssmMemProcessEntry 1 }

ssmMemProcessUsage OBJECT-TYPE
    SYNTAX      CounterBasedGauge64
    MAX-ACCESS  read-only
    STATUS      current
    DESCRIPTION 
        "Amount of memory used by Control Plane process."
    ::= { ssmMemProcessEntry 1010 }

ssmMemProcessName OBJECT-TYPE
    SYNTAX      DisplayString
    MAX-ACCESS  read-only
    STATUS      current
    DESCRIPTION 
        "Name of Control Plane process."
    ::= { ssmMemProcessEntry 2 }

ssmTraffic OBJECT IDENTIFIER
    ::= { ssmSystem 2035 }

ssmSysFwdBytes OBJECT-TYPE
    SYNTAX      Counter64
    MAX-ACCESS  read-only
    STATUS      current
    DESCRIPTION 
        "Forwarded bytes."
    ::= { ssmTraffic 1000 }

ssmSysFwdPackets OBJECT-TYPE
    SYNTAX      Counter64
    MAX-ACCESS  read-only
    STATUS      current
    DESCRIPTION 
        "Forwarded packets."
    ::= { ssmTraffic 1010 }

ssmSysFwdIPsecBytes OBJECT-TYPE
    SYNTAX      Counter64
    MAX-ACCESS  read-only
    STATUS      current
    DESCRIPTION 
        "Forwarded bytes through IPsec interfaces."
    ::= { ssmTraffic 1020 }

ssmSysFwdIPsecPackets OBJECT-TYPE
    SYNTAX      Counter64
    MAX-ACCESS  read-only
    STATUS      current
    DESCRIPTION 
        "Forwarded packets through IPsec interfaces."
    ::= { ssmTraffic 1030 }

ssmSysForwardedVPNBytes OBJECT-TYPE
    SYNTAX      Counter64
    MAX-ACCESS  read-only
    STATUS      current
    DESCRIPTION 
        "Forwarded bytes through SSL VPN interfaces. IPsec traffic is not
         included."
    ::= { ssmTraffic 1040 }

ssmSysForwardedVPNPackets OBJECT-TYPE
    SYNTAX      Counter64
    MAX-ACCESS  read-only
    STATUS      current
    DESCRIPTION 
        "Forwarded packets through SSL VPN interfaces. IPsec traffic is
         not included."
    ::= { ssmTraffic 1050 }

ssmHA OBJECT IDENTIFIER
    ::= { ssmSystem 2040 }

ssmHAIsActive OBJECT-TYPE
    SYNTAX      Unsigned32
    MAX-ACCESS  read-only
    STATUS      current
    DESCRIPTION 
        "Current HA status for node (1=active, 0=inactive)."
    ::= { ssmHA 1005 }

ssmHATimeStatusChange OBJECT-TYPE
    SYNTAX      Unsigned32
    MAX-ACCESS  read-only
    STATUS      current
    DESCRIPTION 
        "Elapsed time since last HA status (active/inactive) change."
    ::= { ssmHA 1010 }

ssmHAElapsedTimeActive OBJECT-TYPE
    SYNTAX      Counter32
    MAX-ACCESS  read-only
    STATUS      current
    DESCRIPTION 
        "Total time spent as active."
    ::= { ssmHA 1015 }

ssmHAElapsedTimeInactive OBJECT-TYPE
    SYNTAX      Counter32
    MAX-ACCESS  read-only
    STATUS      current
    DESCRIPTION 
        "Total time spent as inactive."
    ::= { ssmHA 1020 }

ssmHAHbeatInterval OBJECT-TYPE
    SYNTAX      Unsigned32
    MAX-ACCESS  read-only
    STATUS      current
    DESCRIPTION 
        "Number of milliseconds between periodic HA heartbeats."
    ::= { ssmHA 1022 }

ssmHAHbeatTimeslotsMissed OBJECT-TYPE
    SYNTAX      Counter32
    MAX-ACCESS  read-only
    STATUS      current
    DESCRIPTION 
        "Number of times the system have missed the timeslot for sending
         HA heartbeats."
    ::= { ssmHA 1023 }

ssmHAPeerUptime OBJECT-TYPE
    SYNTAX      Unsigned32
    MAX-ACCESS  read-only
    STATUS      current
    DESCRIPTION 
        "Time elapsed since peer came online."
    ::= { ssmHA 1025 }

ssmHASentConfigurations OBJECT-TYPE
    SYNTAX      Counter32
    MAX-ACCESS  read-only
    STATUS      current
    DESCRIPTION 
        "Number of configuration synchronizations to the HA peer."
    ::= { ssmHA 1030 }

ssmHAMessagesRecv OBJECT-TYPE
    SYNTAX      Counter32
    MAX-ACCESS  read-only
    STATUS      current
    DESCRIPTION 
        "Number of received HA sync messages in total."
    ::= { ssmHA 1035 }

ssmHAMessagesResent OBJECT-TYPE
    SYNTAX      Counter32
    MAX-ACCESS  read-only
    STATUS      current
    DESCRIPTION 
        "Number of resent HA sync messages in total."
    ::= { ssmHA 1040 }

ssmHAMessagesSent OBJECT-TYPE
    SYNTAX      Counter32
    MAX-ACCESS  read-only
    STATUS      current
    DESCRIPTION 
        "Number of sent HA sync messages in total."
    ::= { ssmHA 1045 }

ssmHANumFailovers OBJECT-TYPE
    SYNTAX      Counter32
    MAX-ACCESS  read-only
    STATUS      current
    DESCRIPTION 
        "Number of occurrences that the unit has 'taken over' due the
         peer becoming non-operational."
    ::= { ssmHA 1050 }

ssmHANumHandovers OBJECT-TYPE
    SYNTAX      Counter32
    MAX-ACCESS  read-only
    STATUS      current
    DESCRIPTION 
        "Number of times that the unit has handed over or been asked to
         take over."
    ::= { ssmHA 1055 }

ssmHAObjectCount OBJECT-TYPE
    SYNTAX      Unsigned32
    MAX-ACCESS  read-only
    STATUS      current
    DESCRIPTION 
        "Current number of installed HA objects."
    ::= { ssmHA 1060 }

ssmHAObjectsNotSynched OBJECT-TYPE
    SYNTAX      Unsigned32
    MAX-ACCESS  read-only
    STATUS      current
    DESCRIPTION 
        "Number of objects that remain to be synchronized to peer."
    ::= { ssmHA 1065 }

ssmHAReservedBuffersFree OBJECT-TYPE
    SYNTAX      Unsigned32
    MAX-ACCESS  read-only
    STATUS      current
    DESCRIPTION 
        "Current number of free buffers that are in reserve to use for HA
         heartbeats."
    ::= { ssmHA 1070 }

ssmHAReservedBuffersTotal OBJECT-TYPE
    SYNTAX      Unsigned32
    MAX-ACCESS  read-only
    STATUS      current
    DESCRIPTION 
        "Number of buffers that are in reserve to use for HA heartbeats."
    ::= { ssmHA 1075 }

ssmHAFlow OBJECT IDENTIFIER
    ::= { ssmHA 2010 }

ssmHAFlowNotSynced OBJECT-TYPE
    SYNTAX      Unsigned32
    MAX-ACCESS  read-only
    STATUS      current
    DESCRIPTION 
        "Current number of HA synchronizable flows that has not been
         synchronized."
    ::= { ssmHAFlow 1005 }

ssmHAFlowSyncFailed OBJECT-TYPE
    SYNTAX      Unsigned32
    MAX-ACCESS  read-only
    STATUS      current
    DESCRIPTION 
        "Current number of HA synchronizable flow that failed to be
         synchronized."
    ::= { ssmHAFlow 1010 }

ssmHAFlowSynced OBJECT-TYPE
    SYNTAX      Unsigned32
    MAX-ACCESS  read-only
    STATUS      current
    DESCRIPTION 
        "Current number of HA synchronizable flows that has been
         successfully synchronized."
    ::= { ssmHAFlow 1015 }

ssmHAFlowSyncing OBJECT-TYPE
    SYNTAX      Unsigned32
    MAX-ACCESS  read-only
    STATUS      current
    DESCRIPTION 
        "Number of flows currently being synchronized to the peer."
    ::= { ssmHAFlow 1020 }

ssmHAFrag OBJECT IDENTIFIER
    ::= { ssmHA 2020 }

ssmHAFragReassTimeout OBJECT-TYPE
    SYNTAX      Counter64
    MAX-ACCESS  read-only
    STATUS      current
    DESCRIPTION 
        "Number of fragmented HA sync message that has failed due to
         reassembly timeout."
    ::= { ssmHAFrag 1005 }

ssmHAFragRecv OBJECT-TYPE
    SYNTAX      Counter64
    MAX-ACCESS  read-only
    STATUS      current
    DESCRIPTION 
        "Number of HA sync message fragments received."
    ::= { ssmHAFrag 1010 }

ssmHAFragRecvOK OBJECT-TYPE
    SYNTAX      Counter64
    MAX-ACCESS  read-only
    STATUS      current
    DESCRIPTION 
        "Number of HA sync message fragments received OK."
    ::= { ssmHAFrag 1015 }

ssmHAFragReassFail OBJECT-TYPE
    SYNTAX      Counter64
    MAX-ACCESS  read-only
    STATUS      current
    DESCRIPTION 
        "Number of failed reassemblies of fragmented HA sync messages."
    ::= { ssmHAFrag 1020 }

ssmHAFragFragsReassOK OBJECT-TYPE
    SYNTAX      Counter64
    MAX-ACCESS  read-only
    STATUS      current
    DESCRIPTION 
        "Number of successful reassemblies of fragmented HA sync messages."
    ::= { ssmHAFrag 1025 }

ssmHAFragNumLocalReassFail OBJECT-TYPE
    SYNTAX      Counter32
    MAX-ACCESS  read-only
    STATUS      current
    DESCRIPTION 
        "Number of fragmented HA sync messages that has been discarded
         due to an error when rebuilding the original message."
    ::= { ssmHAFrag 1030 }

ssmHAFragNumNoReassBuf OBJECT-TYPE
    SYNTAX      Counter32
    MAX-ACCESS  read-only
    STATUS      current
    DESCRIPTION 
        "Number of fragmented HA sync messages that has been discarded
         due to lack of buffers when rebuilding the original message."
    ::= { ssmHAFrag 1035 }

ssmHAFailuresTable OBJECT-TYPE
    SYNTAX      SEQUENCE OF SsmHAFailuresEntry
    MAX-ACCESS  not-accessible
    STATUS      current
    DESCRIPTION 
        "High Availability interface statistics."
    ::= { ssmHA 3010 }

ssmHAFailuresEntry OBJECT-TYPE
    SYNTAX      SsmHAFailuresEntry
    MAX-ACCESS  not-accessible
    STATUS      current
    DESCRIPTION 
        "High Availability failure statistics entry."
    INDEX       { ssmHAFailureIndex }
    ::= { ssmHAFailuresTable 1 }

SsmHAFailuresEntry ::= SEQUENCE {
    ssmHAFailureIndex      Integer32,
    ssmHAFailureCategory    DisplayString,
    ssmHAFailureCurrent    Unsigned32,
    ssmHAFailureTotal      Counter32
}

ssmHAFailureIndex OBJECT-TYPE
    SYNTAX      Integer32 (1..2147483647)
    MAX-ACCESS  not-accessible
    STATUS      current
    DESCRIPTION 
        "HA failure row index."
    ::= { ssmHAFailuresEntry 1 }

ssmHAFailureCurrent OBJECT-TYPE
    SYNTAX      Unsigned32
    MAX-ACCESS  read-only
    STATUS      current
    DESCRIPTION 
        "Current number of interface failures."
    ::= { ssmHAFailuresEntry 1005 }

ssmHAFailureTotal OBJECT-TYPE
    SYNTAX      Counter32
    MAX-ACCESS  read-only
    STATUS      current
    DESCRIPTION 
        "Cumulative occurred failures for the specified category."
    ::= { ssmHAFailuresEntry 1010 }

ssmHAFailureCategory OBJECT-TYPE
    SYNTAX      DisplayString
    MAX-ACCESS  read-only
    STATUS      current
    DESCRIPTION 
        "HA Failure category."
    ::= { ssmHAFailuresEntry 2 }

ssmHAIfStatsTable OBJECT-TYPE
    SYNTAX      SEQUENCE OF SsmHAIfStatsEntry
    MAX-ACCESS  not-accessible
    STATUS      current
    DESCRIPTION 
        "High Availability interface statistics."
    ::= { ssmHA 3020 }

ssmHAIfStatsEntry OBJECT-TYPE
    SYNTAX      SsmHAIfStatsEntry
    MAX-ACCESS  not-accessible
    STATUS      current
    DESCRIPTION 
        "High Availability interface statistics entry."
    INDEX       { ssmHAIfIndex }
    ::= { ssmHAIfStatsTable 1 }

SsmHAIfStatsEntry ::= SEQUENCE {
    ssmHAIfIndex               Integer32,
    ssmHAIfName                DisplayString,
    ssmHAIfHeartbeatsSent      Counter32,
    ssmHAIfHeartbeatsRecv      Counter32,
    ssmHAIfHeartbeatsSendFail    Counter32,
    ssmHAIfHeartbeatsMissed    Counter32,
    ssmHAIfDownCount           Counter32,
    ssmHAIfEarlyDownCount      Counter32
}

ssmHAIfIndex OBJECT-TYPE
    SYNTAX      Integer32 (1..2147483647)
    MAX-ACCESS  not-accessible
    STATUS      current
    DESCRIPTION 
        "HA interface statistics row index."
    ::= { ssmHAIfStatsEntry 1 }

ssmHAIfHeartbeatsSent OBJECT-TYPE
    SYNTAX      Counter32
    MAX-ACCESS  read-only
    STATUS      current
    DESCRIPTION 
        "Total number of sent heartbeats."
    ::= { ssmHAIfStatsEntry 1005 }

ssmHAIfHeartbeatsRecv OBJECT-TYPE
    SYNTAX      Counter32
    MAX-ACCESS  read-only
    STATUS      current
    DESCRIPTION 
        "Total number of received heartbeats."
    ::= { ssmHAIfStatsEntry 1010 }

ssmHAIfHeartbeatsSendFail OBJECT-TYPE
    SYNTAX      Counter32
    MAX-ACCESS  read-only
    STATUS      current
    DESCRIPTION 
        "Number of heartbeats that failed sending."
    ::= { ssmHAIfStatsEntry 1015 }

ssmHAIfHeartbeatsMissed OBJECT-TYPE
    SYNTAX      Counter32
    MAX-ACCESS  read-only
    STATUS      current
    DESCRIPTION 
        "Number of missing heartbeats from peer."
    ::= { ssmHAIfStatsEntry 1020 }

ssmHAIfDownCount OBJECT-TYPE
    SYNTAX      Counter32
    MAX-ACCESS  read-only
    STATUS      current
    DESCRIPTION 
        "Number of times the interfaces have been declared
         down/non-operational."
    ::= { ssmHAIfStatsEntry 1025 }

ssmHAIfEarlyDownCount OBJECT-TYPE
    SYNTAX      Counter32
    MAX-ACCESS  read-only
    STATUS      current
    DESCRIPTION 
        "Number of times that the interface have suffered
         packetloss/latency-problems but was able to recover prior to
         fail/hand-over."
    ::= { ssmHAIfStatsEntry 1030 }

ssmHAIfName OBJECT-TYPE
    SYNTAX      DisplayString
    MAX-ACCESS  read-only
    STATUS      current
    DESCRIPTION 
        "Name of the interface."
    ::= { ssmHAIfStatsEntry 2 }

ssmHAModulesTable OBJECT-TYPE
    SYNTAX      SEQUENCE OF SsmHAModulesEntry
    MAX-ACCESS  not-accessible
    STATUS      current
    DESCRIPTION 
        "High Availability module statistics."
    ::= { ssmHA 3030 }

ssmHAModulesEntry OBJECT-TYPE
    SYNTAX      SsmHAModulesEntry
    MAX-ACCESS  not-accessible
    STATUS      current
    DESCRIPTION 
        "Interface statistics entry."
    INDEX       { ssmHAModIndex }
    ::= { ssmHAModulesTable 1 }

SsmHAModulesEntry ::= SEQUENCE {
    ssmHAModIndex          Integer32,
    ssmHAModName           DisplayString,
    ssmHAModMessageTokens    Integer32,
    ssmHAModMessagesRecv    Counter32,
    ssmHAModMessagesResent    Counter32,
    ssmHAModMessagesSent    Counter32,
    ssmHAModMessagesThrottled    Counter32,
    ssmHAModObjectCount    Unsigned32,
    ssmHAModObjectQueries    Counter32,
    ssmHAModRecreatedRequests    Counter32,
    ssmHAModRecvAcks       Counter32,
    ssmHAModRecvNAcks      Counter32
}

ssmHAModIndex OBJECT-TYPE
    SYNTAX      Integer32 (1..2147483647)
    MAX-ACCESS  not-accessible
    STATUS      current
    DESCRIPTION 
        "HA module statistics row index."
    ::= { ssmHAModulesEntry 1 }

ssmHAModMessageTokens OBJECT-TYPE
    SYNTAX      Integer32
    MAX-ACCESS  read-only
    STATUS      current
    DESCRIPTION 
        "Current HA sync message token balance for the module."
    ::= { ssmHAModulesEntry 1005 }

ssmHAModMessagesRecv OBJECT-TYPE
    SYNTAX      Counter32
    MAX-ACCESS  read-only
    STATUS      current
    DESCRIPTION 
        "Number of received HA sync message by module."
    ::= { ssmHAModulesEntry 1010 }

ssmHAModMessagesResent OBJECT-TYPE
    SYNTAX      Counter32
    MAX-ACCESS  read-only
    STATUS      current
    DESCRIPTION 
        "Number of resent HA sync messages by module."
    ::= { ssmHAModulesEntry 1015 }

ssmHAModMessagesSent OBJECT-TYPE
    SYNTAX      Counter32
    MAX-ACCESS  read-only
    STATUS      current
    DESCRIPTION 
        "Number of sent HA sync messages by module."
    ::= { ssmHAModulesEntry 1020 }

ssmHAModMessagesThrottled OBJECT-TYPE
    SYNTAX      Counter32
    MAX-ACCESS  read-only
    STATUS      current
    DESCRIPTION 
        "Number of attempts to send an HA sync message by this module
         that has been denied due to message rate limiting."
    ::= { ssmHAModulesEntry 1025 }

ssmHAModObjectCount OBJECT-TYPE
    SYNTAX      Unsigned32
    MAX-ACCESS  read-only
    STATUS      current
    DESCRIPTION 
        "Current number of HA objects installed in this module."
    ::= { ssmHAModulesEntry 1030 }

ssmHAModObjectQueries OBJECT-TYPE
    SYNTAX      Counter32
    MAX-ACCESS  read-only
    STATUS      current
    DESCRIPTION 
        "Number of queries sent to the module when resolving dependencies
         to determine if a specific object exists."
    ::= { ssmHAModulesEntry 1035 }

ssmHAModRecreatedRequests OBJECT-TYPE
    SYNTAX      Counter32
    MAX-ACCESS  read-only
    STATUS      current
    DESCRIPTION 
        "Number of request to recreate a lost HA object message sent to
         the module."
    ::= { ssmHAModulesEntry 1040 }

ssmHAModRecvAcks OBJECT-TYPE
    SYNTAX      Counter32
    MAX-ACCESS  read-only
    STATUS      current
    DESCRIPTION 
        "Number of positive acknowledgments forwarded to the module on
         the active node."
    ::= { ssmHAModulesEntry 1045 }

ssmHAModRecvNAcks OBJECT-TYPE
    SYNTAX      Counter32
    MAX-ACCESS  read-only
    STATUS      current
    DESCRIPTION 
        "Number of negative acknowledgments forwarded to the module on
         the active node."
    ::= { ssmHAModulesEntry 1050 }

ssmHAModName OBJECT-TYPE
    SYNTAX      DisplayString
    MAX-ACCESS  read-only
    STATUS      current
    DESCRIPTION 
        "HA module name."
    ::= { ssmHAModulesEntry 2 }

ssmDevice OBJECT IDENTIFIER
    ::= { ssmSystem 2050 }

ssmCryptoDeviceTable OBJECT-TYPE
    SYNTAX      SEQUENCE OF SsmCryptoDeviceEntry
    MAX-ACCESS  not-accessible
    STATUS      current
    DESCRIPTION 
        "Crypto device statistics."
    ::= { ssmDevice 3000 }

ssmCryptoDeviceEntry OBJECT-TYPE
    SYNTAX      SsmCryptoDeviceEntry
    MAX-ACCESS  not-accessible
    STATUS      current
    DESCRIPTION 
        "Crypto device statistics entry."
    INDEX       { ssmCryptoDeviceIndex }
    ::= { ssmCryptoDeviceTable 1 }

SsmCryptoDeviceEntry ::= SEQUENCE {
    ssmCryptoDeviceIndex            Integer32,
    ssmCryptoDeviceName             DisplayString,
    ssmCryptoDeviceIsOnline         Unsigned32,
    ssmCryptoDeviceSymSessions      CounterBasedGauge64,
    ssmCryptoDeviceSymSessionFails    Counter64,
    ssmCryptoDeviceSymDecrypts      Counter64,
    ssmCryptoDeviceSymDecryptFails    Counter64,
    ssmCryptoDeviceSymAuthFails     Counter64,
    ssmCryptoDeviceSymEncrypts      Counter64,
    ssmCryptoDeviceSymEncryptFails    Counter64,
    ssmCryptoDeviceSymInFlight      Gauge32
}

ssmCryptoDeviceIndex OBJECT-TYPE
    SYNTAX      Integer32 (1..2147483647)
    MAX-ACCESS  not-accessible
    STATUS      current
    DESCRIPTION 
        "Crypto device statistics row index."
    ::= { ssmCryptoDeviceEntry 1 }

ssmCryptoDeviceIsOnline OBJECT-TYPE
    SYNTAX      Unsigned32
    MAX-ACCESS  read-only
    STATUS      current
    DESCRIPTION 
        "Current status of the device (1=online, 0=offline)."
    ::= { ssmCryptoDeviceEntry 1005 }

ssmCryptoDeviceSymSessions OBJECT-TYPE
    SYNTAX      CounterBasedGauge64
    MAX-ACCESS  read-only
    STATUS      current
    DESCRIPTION 
        "Number of active crypto sessions."
    ::= { ssmCryptoDeviceEntry 1010 }

ssmCryptoDeviceSymSessionFails OBJECT-TYPE
    SYNTAX      Counter64
    MAX-ACCESS  read-only
    STATUS      current
    DESCRIPTION 
        "Number of session setup failures."
    ::= { ssmCryptoDeviceEntry 1015 }

ssmCryptoDeviceSymDecrypts OBJECT-TYPE
    SYNTAX      Counter64
    MAX-ACCESS  read-only
    STATUS      current
    DESCRIPTION 
        "Number of successful encrypt operations."
    ::= { ssmCryptoDeviceEntry 1020 }

ssmCryptoDeviceSymDecryptFails OBJECT-TYPE
    SYNTAX      Counter64
    MAX-ACCESS  read-only
    STATUS      current
    DESCRIPTION 
        "Number of failed decrypt operations."
    ::= { ssmCryptoDeviceEntry 1025 }

ssmCryptoDeviceSymAuthFails OBJECT-TYPE
    SYNTAX      Counter64
    MAX-ACCESS  read-only
    STATUS      current
    DESCRIPTION 
        "Number of authentication verification failures for decrypt
         operations."
    ::= { ssmCryptoDeviceEntry 1030 }

ssmCryptoDeviceSymEncrypts OBJECT-TYPE
    SYNTAX      Counter64
    MAX-ACCESS  read-only
    STATUS      current
    DESCRIPTION 
        "Number of successful encrypt operations."
    ::= { ssmCryptoDeviceEntry 1035 }

ssmCryptoDeviceSymEncryptFails OBJECT-TYPE
    SYNTAX      Counter64
    MAX-ACCESS  read-only
    STATUS      current
    DESCRIPTION 
        "Number of failed encrypt operations."
    ::= { ssmCryptoDeviceEntry 1040 }

ssmCryptoDeviceSymInFlight OBJECT-TYPE
    SYNTAX      Gauge32
    MAX-ACCESS  read-only
    STATUS      current
    DESCRIPTION 
        "Number of symmetric crypto operations currently in flight."
    ::= { ssmCryptoDeviceEntry 1050 }

ssmCryptoDeviceName OBJECT-TYPE
    SYNTAX      DisplayString
    MAX-ACCESS  read-only
    STATUS      current
    DESCRIPTION 
        "Name of the crypto device."
    ::= { ssmCryptoDeviceEntry 2 }

ssmAdminParameters OBJECT IDENTIFIER
    ::= { ssmSystem 2100 }

ssmUserDefinedState OBJECT-TYPE
    SYNTAX      DisplayString
    MAX-ACCESS  read-only
    STATUS      current
    DESCRIPTION 
        "User defined state."
    ::= { ssmAdminParameters 1010 }

ssmManagementIPAddressList OBJECT-TYPE
    SYNTAX      DisplayString
    MAX-ACCESS  read-only
    STATUS      current
    DESCRIPTION 
        "IP address list of network management system interfaces."
    ::= { ssmAdminParameters 1020 }

ssmServiceIPAddressList OBJECT-TYPE
    SYNTAX      DisplayString
    MAX-ACCESS  read-only
    STATUS      current
    DESCRIPTION 
        "Service IP Address List."
    ::= { ssmAdminParameters 1030 }

ssmDateOfLastService OBJECT-TYPE
    SYNTAX      DisplayString
    MAX-ACCESS  read-only
    STATUS      current
    DESCRIPTION 
        "Date of last service (Last time the unit got back to normal work
         state)."
    ::= { ssmAdminParameters 1040 }

ssmInterfaces OBJECT IDENTIFIER
    ::= { clavisterSystemStats 2010 }

ssmIfaceGlobal OBJECT IDENTIFIER
    ::= { ssmInterfaces 2010 }

ssmFragsReassTimeout OBJECT-TYPE
    SYNTAX      Counter64
    MAX-ACCESS  read-only
    STATUS      current
    DESCRIPTION 
        "Total number of IP packet reassemblies that has failed due to
         timeout."
    ::= { ssmIfaceGlobal 1020 }

ssmFragsRecv OBJECT-TYPE
    SYNTAX      Counter64
    MAX-ACCESS  read-only
    STATUS      current
    DESCRIPTION 
        "Total number of IP packet fragments received."
    ::= { ssmIfaceGlobal 1025 }

ssmFragsRecvOk OBJECT-TYPE
    SYNTAX      Counter64
    MAX-ACCESS  read-only
    STATUS      current
    DESCRIPTION 
        "Total number of IP packet fragments received OK."
    ::= { ssmIfaceGlobal 1030 }

ssmFragsReassFail OBJECT-TYPE
    SYNTAX      Counter64
    MAX-ACCESS  read-only
    STATUS      current
    DESCRIPTION 
        "Total number of failed IP packet reassemblies."
    ::= { ssmIfaceGlobal 1035 }

ssmFragsReassOK OBJECT-TYPE
    SYNTAX      Counter64
    MAX-ACCESS  read-only
    STATUS      current
    DESCRIPTION 
        "Total number of IP packets reassembled OK."
    ::= { ssmIfaceGlobal 1040 }

ssmIPsecGlobal OBJECT IDENTIFIER
    ::= { ssmIfaceGlobal 2020 }

ssmIKEv2Global OBJECT IDENTIFIER
    ::= { ssmIPsecGlobal 2020 }

ssmIKEv2IKENegsActive OBJECT-TYPE
    SYNTAX      Gauge32
    MAX-ACCESS  read-only
    STATUS      current
    DESCRIPTION 
        "Number of IKEv2 negotiations in progress."
    ::= { ssmIKEv2Global 1005 }

ssmIKEv2IKENegsCompleted OBJECT-TYPE
    SYNTAX      Counter64
    MAX-ACCESS  read-only
    STATUS      current
    DESCRIPTION 
        "Number of completed IKEv2 negotiations."
    ::= { ssmIKEv2Global 1010 }

ssmIKEv2IKENegsFailed OBJECT-TYPE
    SYNTAX      Counter64
    MAX-ACCESS  read-only
    STATUS      current
    DESCRIPTION 
        "Number of failed IKEv2 negotiations."
    ::= { ssmIKEv2Global 1015 }

ssmIKEv2IKERekeysActive OBJECT-TYPE
    SYNTAX      Gauge32
    MAX-ACCESS  read-only
    STATUS      current
    DESCRIPTION 
        "Number of IKEv2 rekeys in progress."
    ::= { ssmIKEv2Global 1020 }

ssmIKEv2IKERekeysCompleted OBJECT-TYPE
    SYNTAX      Counter64
    MAX-ACCESS  read-only
    STATUS      current
    DESCRIPTION 
        "Number of completed IKEv2 rekeys."
    ::= { ssmIKEv2Global 1025 }

ssmIKEv2IKERekeysFailed OBJECT-TYPE
    SYNTAX      Counter64
    MAX-ACCESS  read-only
    STATUS      current
    DESCRIPTION 
        "Number of failed IKEv2 rekeys."
    ::= { ssmIKEv2Global 1030 }

ssmIKEv2IKESAsActive OBJECT-TYPE
    SYNTAX      Gauge32
    MAX-ACCESS  read-only
    STATUS      current
    DESCRIPTION 
        "Number of active IKEv2 SAs."
    ::= { ssmIKEv2Global 1035 }

ssmIKEv2IPsecNegsActive OBJECT-TYPE
    SYNTAX      Gauge32
    MAX-ACCESS  read-only
    STATUS      current
    DESCRIPTION 
        "Number of IPsec negotiations in progress."
    ::= { ssmIKEv2Global 1040 }

ssmIKEv2IPsecNegsCompleted OBJECT-TYPE
    SYNTAX      Counter64
    MAX-ACCESS  read-only
    STATUS      current
    DESCRIPTION 
        "Number of completed IPsec negotiations."
    ::= { ssmIKEv2Global 1045 }

ssmIKEv2IPsecNegsFailed OBJECT-TYPE
    SYNTAX      Counter64
    MAX-ACCESS  read-only
    STATUS      current
    DESCRIPTION 
        "Number of failed IPsec negotiations."
    ::= { ssmIKEv2Global 1050 }

ssmIKEv2IPsecRekeysActive OBJECT-TYPE
    SYNTAX      Gauge32
    MAX-ACCESS  read-only
    STATUS      current
    DESCRIPTION 
        "Number of IPsec rekeys in progress."
    ::= { ssmIKEv2Global 1055 }

ssmIKEv2IPsecRekeysCompleted OBJECT-TYPE
    SYNTAX      Counter64
    MAX-ACCESS  read-only
    STATUS      current
    DESCRIPTION 
        "Number of completed IPsec rekeys."
    ::= { ssmIKEv2Global 1060 }

ssmIKEv2IPsecRekeysFailed OBJECT-TYPE
    SYNTAX      Counter64
    MAX-ACCESS  read-only
    STATUS      current
    DESCRIPTION 
        "Number of failed IPsec rekeys."
    ::= { ssmIKEv2Global 1065 }

ssmIKEv2IPsecSAsActive OBJECT-TYPE
    SYNTAX      Gauge32
    MAX-ACCESS  read-only
    STATUS      current
    DESCRIPTION 
        "Number of active IPsec SAs."
    ::= { ssmIKEv2Global 1070 }

ssmIKEBytesRecv OBJECT-TYPE
    SYNTAX      Counter64
    MAX-ACCESS  read-only
    STATUS      current
    DESCRIPTION 
        "IKEv2 bytes received by the IKE engine."
    ::= { ssmIKEv2Global 1200 }

ssmIKEBytesSent OBJECT-TYPE
    SYNTAX      Counter64
    MAX-ACCESS  read-only
    STATUS      current
    DESCRIPTION 
        "IKEv2 bytes sent by the IKE engine."
    ::= { ssmIKEv2Global 1205 }

ssmIKEPacketsRecv OBJECT-TYPE
    SYNTAX      Counter32
    MAX-ACCESS  read-only
    STATUS      current
    DESCRIPTION 
        "IKEv2 packets received by the IKE engine."
    ::= { ssmIKEv2Global 1210 }

ssmIKEPacketsResent OBJECT-TYPE
    SYNTAX      Counter32
    MAX-ACCESS  read-only
    STATUS      current
    DESCRIPTION 
        "IKEv2 Packets resent by the IKE engine."
    ::= { ssmIKEv2Global 1220 }

ssmIKEPacketsSent OBJECT-TYPE
    SYNTAX      Counter32
    MAX-ACCESS  read-only
    STATUS      current
    DESCRIPTION 
        "IKEv2 packets sent by the IKE engine."
    ::= { ssmIKEv2Global 1225 }

ssmTimedOutNegs OBJECT-TYPE
    SYNTAX      Counter32
    MAX-ACCESS  read-only
    STATUS      current
    DESCRIPTION 
        "Number of timed out IKEv2 negotiations."
    ::= { ssmIKEv2Global 1230 }

ssmDPDDeletedSAs OBJECT-TYPE
    SYNTAX      Counter32
    MAX-ACCESS  read-only
    STATUS      current
    DESCRIPTION 
        "IKEv2 SAs deleted due to DPD."
    ::= { ssmIKEv2Global 1235 }

ssmIKEv1Global OBJECT IDENTIFIER
    ::= { ssmIPsecGlobal 2030 }

ssmIKEv1IKENegsActive OBJECT-TYPE
    SYNTAX      Gauge32
    MAX-ACCESS  read-only
    STATUS      current
    DESCRIPTION 
        "Number of IKEv1 negotiations in progress."
    ::= { ssmIKEv1Global 1005 }

ssmIKEv1IKENegsCompleted OBJECT-TYPE
    SYNTAX      Counter64
    MAX-ACCESS  read-only
    STATUS      current
    DESCRIPTION 
        "Number of completed IKEv1 negotiations."
    ::= { ssmIKEv1Global 1010 }

ssmIKEv1IKENegsFailed OBJECT-TYPE
    SYNTAX      Counter64
    MAX-ACCESS  read-only
    STATUS      current
    DESCRIPTION 
        "Number of failed IKEv1 negotiations."
    ::= { ssmIKEv1Global 1015 }

ssmIKEv1IKERekeysActive OBJECT-TYPE
    SYNTAX      Gauge32
    MAX-ACCESS  read-only
    STATUS      current
    DESCRIPTION 
        "Number of IKEv1 rekeys in progress."
    ::= { ssmIKEv1Global 1020 }

ssmIKEv1IKERekeysCompleted OBJECT-TYPE
    SYNTAX      Counter64
    MAX-ACCESS  read-only
    STATUS      current
    DESCRIPTION 
        "Number of completed IKEv1 rekeys."
    ::= { ssmIKEv1Global 1025 }

ssmIKEv1IKERekeysFailed OBJECT-TYPE
    SYNTAX      Counter64
    MAX-ACCESS  read-only
    STATUS      current
    DESCRIPTION 
        "Number of failed IKEv1 rekeys."
    ::= { ssmIKEv1Global 1030 }

ssmIKEv1IKESAsActive OBJECT-TYPE
    SYNTAX      Gauge32
    MAX-ACCESS  read-only
    STATUS      current
    DESCRIPTION 
        "Number of active IKEv1  SAs."
    ::= { ssmIKEv1Global 1035 }

ssmIKEv1IPsecNegsActive OBJECT-TYPE
    SYNTAX      Gauge32
    MAX-ACCESS  read-only
    STATUS      current
    DESCRIPTION 
        "Number of IPsec negotiations in progress."
    ::= { ssmIKEv1Global 1040 }

ssmIKEv1IPsecNegsCompleted OBJECT-TYPE
    SYNTAX      Counter64
    MAX-ACCESS  read-only
    STATUS      current
    DESCRIPTION 
        "Number of completed IPsec negotiations."
    ::= { ssmIKEv1Global 1045 }

ssmIKEv1IPsecNegsFailed OBJECT-TYPE
    SYNTAX      Counter64
    MAX-ACCESS  read-only
    STATUS      current
    DESCRIPTION 
        "Number of failed IPsec negotiations."
    ::= { ssmIKEv1Global 1050 }

ssmIKEv1IPsecRekeysActive OBJECT-TYPE
    SYNTAX      Gauge32
    MAX-ACCESS  read-only
    STATUS      current
    DESCRIPTION 
        "Number of IPsec rekeys in progress."
    ::= { ssmIKEv1Global 1055 }

ssmIKEv1IPsecRekeysCompleted OBJECT-TYPE
    SYNTAX      Counter64
    MAX-ACCESS  read-only
    STATUS      current
    DESCRIPTION 
        "Number of completed IPsec rekeys."
    ::= { ssmIKEv1Global 1060 }

ssmIKEv1IPsecRekeysFailed OBJECT-TYPE
    SYNTAX      Counter64
    MAX-ACCESS  read-only
    STATUS      current
    DESCRIPTION 
        "Number of failed IPsec rekeys."
    ::= { ssmIKEv1Global 1065 }

ssmIKEv1IPsecSAsActive OBJECT-TYPE
    SYNTAX      Gauge32
    MAX-ACCESS  read-only
    STATUS      current
    DESCRIPTION 
        "Number of active IPsec SAs."
    ::= { ssmIKEv1Global 1070 }

ssmIKEv1BytesRecv OBJECT-TYPE
    SYNTAX      Counter64
    MAX-ACCESS  read-only
    STATUS      current
    DESCRIPTION 
        "IKEv1 bytes received by the IKE engine."
    ::= { ssmIKEv1Global 1200 }

ssmIKEv1BytesSent OBJECT-TYPE
    SYNTAX      Counter64
    MAX-ACCESS  read-only
    STATUS      current
    DESCRIPTION 
        "IKEv1 bytes sent by the IKE engine."
    ::= { ssmIKEv1Global 1205 }

ssmIKEv1PacketsRecv OBJECT-TYPE
    SYNTAX      Counter32
    MAX-ACCESS  read-only
    STATUS      current
    DESCRIPTION 
        "IKEv1 packets received by the IKE engine."
    ::= { ssmIKEv1Global 1210 }

ssmIKEv1PacketsResent OBJECT-TYPE
    SYNTAX      Counter32
    MAX-ACCESS  read-only
    STATUS      current
    DESCRIPTION 
        "IKEv1 packets resent by the IKE engine."
    ::= { ssmIKEv1Global 1220 }

ssmIKEv1PacketsSent OBJECT-TYPE
    SYNTAX      Counter32
    MAX-ACCESS  read-only
    STATUS      current
    DESCRIPTION 
        "IKEv1 packets sent by the IKE engine."
    ::= { ssmIKEv1Global 1225 }

ssmTimedOutIKEv1Negs OBJECT-TYPE
    SYNTAX      Counter32
    MAX-ACCESS  read-only
    STATUS      current
    DESCRIPTION 
        "Number of timed out IKEv1 negotiations."
    ::= { ssmIKEv1Global 1230 }

ssmDPDDeletedIKEv1SAs OBJECT-TYPE
    SYNTAX      Counter32
    MAX-ACCESS  read-only
    STATUS      current
    DESCRIPTION 
        "IKEv1 SAs deleted due to DPD."
    ::= { ssmIKEv1Global 1235 }

ssmSSLVPNGlobal OBJECT IDENTIFIER
    ::= { ssmIfaceGlobal 2030 }

ssmSSLVPNCtrlBytesRecvSys OBJECT-TYPE
    SYNTAX      Counter64
    MAX-ACCESS  read-only
    STATUS      current
    DESCRIPTION 
        "Control channel bytes received."
    ::= { ssmSSLVPNGlobal 1010 }

ssmSSLVPNCtrlBytesSentSys OBJECT-TYPE
    SYNTAX      Counter64
    MAX-ACCESS  read-only
    STATUS      current
    DESCRIPTION 
        "Control channel bytes sent."
    ::= { ssmSSLVPNGlobal 1020 }

ssmSSLVPNCtrlPktsRecvSys OBJECT-TYPE
    SYNTAX      Counter64
    MAX-ACCESS  read-only
    STATUS      current
    DESCRIPTION 
        "Control channel packets received."
    ::= { ssmSSLVPNGlobal 1030 }

ssmSSLVPNCtrlPktsResentSys OBJECT-TYPE
    SYNTAX      Counter64
    MAX-ACCESS  read-only
    STATUS      current
    DESCRIPTION 
        "Control channel packets resent."
    ::= { ssmSSLVPNGlobal 1040 }

ssmSSLVPNCtrlPktsSentSys OBJECT-TYPE
    SYNTAX      Counter64
    MAX-ACCESS  read-only
    STATUS      current
    DESCRIPTION 
        "Control channel packet sent."
    ::= { ssmSSLVPNGlobal 1050 }

ssmSSLVPNDecryptFailsSys OBJECT-TYPE
    SYNTAX      Counter64
    MAX-ACCESS  read-only
    STATUS      current
    DESCRIPTION 
        "Number of packets on data channel which failed to be decrypted."
    ::= { ssmSSLVPNGlobal 1060 }

ssmSSLVPNIntegrityFailsSys OBJECT-TYPE
    SYNTAX      Counter64
    MAX-ACCESS  read-only
    STATUS      current
    DESCRIPTION 
        "Number of packets on data channel which failed integrity check."
    ::= { ssmSSLVPNGlobal 1070 }

ssmSSLVPNInvalidPacketsSys OBJECT-TYPE
    SYNTAX      Counter64
    MAX-ACCESS  read-only
    STATUS      current
    DESCRIPTION 
        "Encapsulated packets on data channel that the system was unable
         to parse."
    ::= { ssmSSLVPNGlobal 1080 }

ssmSSLVPNAntiReplayFailsSys OBJECT-TYPE
    SYNTAX      Counter64
    MAX-ACCESS  read-only
    STATUS      current
    DESCRIPTION 
        "Number of packets on data channel which failed replay protection
         checks."
    ::= { ssmSSLVPNGlobal 1090 }

ssmSSLVPNNegActiveSys OBJECT-TYPE
    SYNTAX      Unsigned32
    MAX-ACCESS  read-only
    STATUS      current
    DESCRIPTION 
        "Number of active data encryption key negotiations."
    ::= { ssmSSLVPNGlobal 1100 }

ssmSSLVPNNegFailedSys OBJECT-TYPE
    SYNTAX      Counter64
    MAX-ACCESS  read-only
    STATUS      current
    DESCRIPTION 
        "Number of failed data encryption key negotiations."
    ::= { ssmSSLVPNGlobal 1110 }

ssmSSLVPNNegSuccessSys OBJECT-TYPE
    SYNTAX      Counter64
    MAX-ACCESS  read-only
    STATUS      current
    DESCRIPTION 
        "Number of successful data encryption key negotiations."
    ::= { ssmSSLVPNGlobal 1120 }

ssmSSLVPNReNegActiveSys OBJECT-TYPE
    SYNTAX      Unsigned32
    MAX-ACCESS  read-only
    STATUS      current
    DESCRIPTION 
        "Number of active data encryption key renegotiations."
    ::= { ssmSSLVPNGlobal 1130 }

ssmSSLVPNReNegFailedSys OBJECT-TYPE
    SYNTAX      Counter64
    MAX-ACCESS  read-only
    STATUS      current
    DESCRIPTION 
        "Number of failed data encryption key negotiations."
    ::= { ssmSSLVPNGlobal 1140 }

ssmSSLVPNReNegSuccessSys OBJECT-TYPE
    SYNTAX      Counter64
    MAX-ACCESS  read-only
    STATUS      current
    DESCRIPTION 
        "Number of successful data encryption key negotiations."
    ::= { ssmSSLVPNGlobal 1150 }

ssmSSLVPNSessCurrAuthSys OBJECT-TYPE
    SYNTAX      Unsigned32
    MAX-ACCESS  read-only
    STATUS      current
    DESCRIPTION 
        "Current authenticated sessions."
    ::= { ssmSSLVPNGlobal 1160 }

ssmSSLVPNSessCurrSys OBJECT-TYPE
    SYNTAX      Unsigned32
    MAX-ACCESS  read-only
    STATUS      current
    DESCRIPTION 
        "Current sessions."
    ::= { ssmSSLVPNGlobal 1170 }

ssmSSLVPNSessTimedOutSys OBJECT-TYPE
    SYNTAX      Counter64
    MAX-ACCESS  read-only
    STATUS      current
    DESCRIPTION 
        "Timed out sessions since start of system."
    ::= { ssmSSLVPNGlobal 1180 }

ssmSSLVPNSessTotalSys OBJECT-TYPE
    SYNTAX      Counter64
    MAX-ACCESS  read-only
    STATUS      current
    DESCRIPTION 
        "Total sessions since start of system."
    ::= { ssmSSLVPNGlobal 1190 }

ssmSSLVPNChallengeActiveSys OBJECT-TYPE
    SYNTAX      Unsigned32
    MAX-ACCESS  read-only
    STATUS      current
    DESCRIPTION 
        "Number of active access-challenges."
    ::= { ssmSSLVPNGlobal 1200 }

ssmSSLVPNChallengeFailedSys OBJECT-TYPE
    SYNTAX      Counter64
    MAX-ACCESS  read-only
    STATUS      current
    DESCRIPTION 
        "Number of failed access-challenges."
    ::= { ssmSSLVPNGlobal 1210 }

ssmSSLVPNChallengeSuccessSys OBJECT-TYPE
    SYNTAX      Counter64
    MAX-ACCESS  read-only
    STATUS      current
    DESCRIPTION 
        "Number of successful access-challenges."
    ::= { ssmSSLVPNGlobal 1220 }

ssmIfStatsTable OBJECT-TYPE
    SYNTAX      SEQUENCE OF SsmIfStatsEntry
    MAX-ACCESS  not-accessible
    STATUS      current
    DESCRIPTION 
        "Interfaces statistics."
    ::= { ssmInterfaces 3010 }

ssmIfStatsEntry OBJECT-TYPE
    SYNTAX      SsmIfStatsEntry
    MAX-ACCESS  not-accessible
    STATUS      current
    DESCRIPTION 
        "Interface statistics entry."
    INDEX       { ssmIfIndex }
    ::= { ssmIfStatsTable 1 }

SsmIfStatsEntry ::= SEQUENCE {
    ssmIfIndex                  Integer32,
    ssmIfName                   DisplayString,
    ssmIfDescription            DisplayString,
    ssmIfAddress                DisplayString,
    ssmIfBytesRecv              Counter64,
    ssmIfBytesSent              Counter64,
    ssmIfFragReassFail          Counter64,
    ssmIfFragsRecv              Counter64,
    ssmIfFragReassOK            Counter64,
    ssmIfMCastPktsRecv          Counter64,
    ssmIfMCastPktsSent          Counter64,
    ssmIfPktsDropped            Counter64,
    ssmIfPktsRecv               Counter64,
    ssmIfPktsSent               Counter64,
    ssmIfSendFails              Counter64,
    ssmIfIpv6BytesRecv          Counter64,
    ssmIfIpv6BytesSent          Counter64,
    ssmIfIpv6PktsRecv           Counter64,
    ssmIfIpv6PktsSent           Counter64
}

ssmIfIndex OBJECT-TYPE
    SYNTAX      Integer32 (1..2147483647)
    MAX-ACCESS  not-accessible
    STATUS      current
    DESCRIPTION 
        "Interface statistics row index."
    ::= { ssmIfStatsEntry 1 }

ssmIfDescription OBJECT-TYPE
    SYNTAX      DisplayString
    MAX-ACCESS  read-only
    STATUS      current
    DESCRIPTION 
        "Interface description/comment."
    ::= { ssmIfStatsEntry 1010 }

ssmIfAddress OBJECT-TYPE
    SYNTAX      DisplayString
    MAX-ACCESS  read-only
    STATUS      current
    DESCRIPTION 
        "Assigned IP addresses for interface."
    ::= { ssmIfStatsEntry 1020 }

ssmIfBytesRecv OBJECT-TYPE
    SYNTAX      Counter64
    MAX-ACCESS  read-only
    STATUS      current
    DESCRIPTION 
        "Number of bytes received."
    ::= { ssmIfStatsEntry 1030 }

ssmIfBytesSent OBJECT-TYPE
    SYNTAX      Counter64
    MAX-ACCESS  read-only
    STATUS      current
    DESCRIPTION 
        "Number of bytes sent."
    ::= { ssmIfStatsEntry 1033 }

ssmIfFragReassFail OBJECT-TYPE
    SYNTAX      Counter64
    MAX-ACCESS  read-only
    STATUS      current
    DESCRIPTION 
        "Number of failed IP fragment reassemblies."
    ::= { ssmIfStatsEntry 1039 }

ssmIfFragsRecv OBJECT-TYPE
    SYNTAX      Counter64
    MAX-ACCESS  read-only
    STATUS      current
    DESCRIPTION 
        "Number of IP packet fragments received on the interface."
    ::= { ssmIfStatsEntry 1042 }

ssmIfFragReassOK OBJECT-TYPE
    SYNTAX      Counter64
    MAX-ACCESS  read-only
    STATUS      current
    DESCRIPTION 
        "Number of successful IP fragment reassemblies."
    ::= { ssmIfStatsEntry 1047 }

ssmIfMCastPktsRecv OBJECT-TYPE
    SYNTAX      Counter64
    MAX-ACCESS  read-only
    STATUS      current
    DESCRIPTION 
        "Number of received multicast packets."
    ::= { ssmIfStatsEntry 1050 }

ssmIfMCastPktsSent OBJECT-TYPE
    SYNTAX      Counter64
    MAX-ACCESS  read-only
    STATUS      current
    DESCRIPTION 
        "Number of sent multicast packets."
    ::= { ssmIfStatsEntry 1053 }

ssmIfPktsDropped OBJECT-TYPE
    SYNTAX      Counter64
    MAX-ACCESS  read-only
    STATUS      current
    DESCRIPTION 
        "Number of packets dropped by the software."
    ::= { ssmIfStatsEntry 1056 }

ssmIfPktsRecv OBJECT-TYPE
    SYNTAX      Counter64
    MAX-ACCESS  read-only
    STATUS      current
    DESCRIPTION 
        "Number of received packets."
    ::= { ssmIfStatsEntry 1059 }

ssmIfPktsSent OBJECT-TYPE
    SYNTAX      Counter64
    MAX-ACCESS  read-only
    STATUS      current
    DESCRIPTION 
        "Number of sent packets."
    ::= { ssmIfStatsEntry 1062 }

ssmIfSendFails OBJECT-TYPE
    SYNTAX      Counter64
    MAX-ACCESS  read-only
    STATUS      current
    DESCRIPTION 
        "Number of send failures (software congestion, rate limit,
         hardware malfunction)."
    ::= { ssmIfStatsEntry 1065 }

ssmIfIpv6BytesRecv OBJECT-TYPE
    SYNTAX      Counter64
    MAX-ACCESS  read-only
    STATUS      current
    DESCRIPTION 
        "Number of IPv6 bytes received."
    ::= { ssmIfStatsEntry 1630 }

ssmIfIpv6BytesSent OBJECT-TYPE
    SYNTAX      Counter64
    MAX-ACCESS  read-only
    STATUS      current
    DESCRIPTION 
        "Number of IPv6 bytes sent."
    ::= { ssmIfStatsEntry 1633 }

ssmIfIpv6PktsRecv OBJECT-TYPE
    SYNTAX      Counter64
    MAX-ACCESS  read-only
    STATUS      current
    DESCRIPTION 
        "Number of IPv6 packets received."
    ::= { ssmIfStatsEntry 1659 }

ssmIfIpv6PktsSent OBJECT-TYPE
    SYNTAX      Counter64
    MAX-ACCESS  read-only
    STATUS      current
    DESCRIPTION 
        "Number of IPv6 packets sent."
    ::= { ssmIfStatsEntry 1662 }

ssmIfName OBJECT-TYPE
    SYNTAX      DisplayString
    MAX-ACCESS  read-only
    STATUS      current
    DESCRIPTION 
        "Name of the interface."
    ::= { ssmIfStatsEntry 2 }

ssmGTPIfStatsTable OBJECT-TYPE
    SYNTAX      SEQUENCE OF SsmGTPIfStatsEntry
    MAX-ACCESS  not-accessible
    STATUS      current
    DESCRIPTION 
        "GTP statistics."
    ::= { ssmInterfaces 3020 }

ssmGTPIfStatsEntry OBJECT-TYPE
    SYNTAX      SsmGTPIfStatsEntry
    MAX-ACCESS  not-accessible
    STATUS      current
    DESCRIPTION 
        "GTP interface statistics entry."
    INDEX       { ssmGTPIfIndex }
    ::= { ssmGTPIfStatsTable 1 }

SsmGTPIfStatsEntry ::= SEQUENCE {
    ssmGTPIfIndex                Integer32,
    ssmGTPIfName                 DisplayString,
    ssmGTPCIfActiveNegotiations    Unsigned32,
    ssmGTPCIfGTPCTunnels         Unsigned32,
    ssmGTPCIfDetectedGTPSrvRestarts    Counter32,
    ssmGTPCIfFailedNegotiations    Counter32,
    ssmGTPCIfFailedSends         Counter32,
    ssmGTPCIfGTPSrvInitiatedDeletes    Counter32,
    ssmGTPCIfIKEInitiatedDeletes    Counter32,
    ssmGTPCIfInvalidLengthIEs    Counter32,
    ssmGTPCIfInvalidMandatoryIEs    Counter32,
    ssmGTPCIfInvalidOptionalIEs    Counter32,
    ssmGTPCIfMissingMandatoryIEs    Counter32,
    ssmGTPCIfTruncatedMsgs       Counter32,
    ssmGTPCIfOutOfSequenceIEs    Counter32,
    ssmGTPCIfRetriesSent         Counter32,
    ssmGTPCIfClientInitiatedDeletes    Counter32,
    ssmGTPCIfUnexpectedMsgs      Counter32,
    ssmGTPCIfUnknownIEs          Counter32,
    ssmGTPCIfUnknownMsgs         Counter32,
    ssmGTPUIfTruncatedMsgs       Counter32,
    ssmGTPUIfInvalidTunnels      Counter32,
    ssmGTPUIfInvalidSeqNum       Counter32,
    ssmGTPUIfGTPUTunnels         Unsigned32,
    ssmGTPUIfUnsupportedExtHdr    Counter32,
    ssmGTPUIfUnsupportedMsgType    Counter32,
    ssmGTPUIfUnsupportedVer      Counter32
}

ssmGTPIfIndex OBJECT-TYPE
    SYNTAX      Integer32 (1..2147483647)
    MAX-ACCESS  not-accessible
    STATUS      current
    DESCRIPTION 
        "Interface statistics row index."
    ::= { ssmGTPIfStatsEntry 1 }

ssmGTPCIfActiveNegotiations OBJECT-TYPE
    SYNTAX      Unsigned32
    MAX-ACCESS  read-only
    STATUS      current
    DESCRIPTION 
        "Number of active GTP negotiations for this interface."
    ::= { ssmGTPIfStatsEntry 1005 }

ssmGTPCIfGTPCTunnels OBJECT-TYPE
    SYNTAX      Unsigned32
    MAX-ACCESS  read-only
    STATUS      current
    DESCRIPTION 
        "Number of established tunnels currently instantiated in GTPC."
    ::= { ssmGTPIfStatsEntry 1010 }

ssmGTPCIfDetectedGTPSrvRestarts OBJECT-TYPE
    SYNTAX      Counter32
    MAX-ACCESS  read-only
    STATUS      current
    DESCRIPTION 
        "Number of detected GTP server restarts."
    ::= { ssmGTPIfStatsEntry 1015 }

ssmGTPCIfFailedNegotiations OBJECT-TYPE
    SYNTAX      Counter32
    MAX-ACCESS  read-only
    STATUS      current
    DESCRIPTION 
        "Number of failed GTP negotiations for this interface."
    ::= { ssmGTPIfStatsEntry 1020 }

ssmGTPCIfFailedSends OBJECT-TYPE
    SYNTAX      Counter32
    MAX-ACCESS  read-only
    STATUS      current
    DESCRIPTION 
        "Number of GTP-C packets for which sending failed."
    ::= { ssmGTPIfStatsEntry 1025 }

ssmGTPCIfGTPSrvInitiatedDeletes OBJECT-TYPE
    SYNTAX      Counter32
    MAX-ACCESS  read-only
    STATUS      current
    DESCRIPTION 
        "Number of GTP server initiated delete requests for this
         interface."
    ::= { ssmGTPIfStatsEntry 1030 }

ssmGTPCIfIKEInitiatedDeletes OBJECT-TYPE
    SYNTAX      Counter32
    MAX-ACCESS  read-only
    STATUS      current
    DESCRIPTION 
        "Number of IKE initiated delete requests for this interface."
    ::= { ssmGTPIfStatsEntry 1035 }

ssmGTPCIfInvalidLengthIEs OBJECT-TYPE
    SYNTAX      Counter32
    MAX-ACCESS  read-only
    STATUS      current
    DESCRIPTION 
        "Number of messages received with an invalid information element
         length for a GTPC interface."
    ::= { ssmGTPIfStatsEntry 1040 }

ssmGTPCIfInvalidMandatoryIEs OBJECT-TYPE
    SYNTAX      Counter32
    MAX-ACCESS  read-only
    STATUS      current
    DESCRIPTION 
        "Number of GTP-C packets with invalid mandatory information
         elements."
    ::= { ssmGTPIfStatsEntry 1045 }

ssmGTPCIfInvalidOptionalIEs OBJECT-TYPE
    SYNTAX      Counter32
    MAX-ACCESS  read-only
    STATUS      current
    DESCRIPTION 
        "Number of GTP-C packets with invalid optional information
         elements."
    ::= { ssmGTPIfStatsEntry 1050 }

ssmGTPCIfMissingMandatoryIEs OBJECT-TYPE
    SYNTAX      Counter32
    MAX-ACCESS  read-only
    STATUS      current
    DESCRIPTION 
        "Number of GTP-C packets with missing mandatory information
         elements."
    ::= { ssmGTPIfStatsEntry 1055 }

ssmGTPCIfTruncatedMsgs OBJECT-TYPE
    SYNTAX      Counter32
    MAX-ACCESS  read-only
    STATUS      current
    DESCRIPTION 
        "Number of GTP-C packets with header indicating too little data
         was received."
    ::= { ssmGTPIfStatsEntry 1060 }

ssmGTPCIfOutOfSequenceIEs OBJECT-TYPE
    SYNTAX      Counter32
    MAX-ACCESS  read-only
    STATUS      current
    DESCRIPTION 
        "Number of GTP-C packets with out of sequence information
         elements."
    ::= { ssmGTPIfStatsEntry 1065 }

ssmGTPCIfRetriesSent OBJECT-TYPE
    SYNTAX      Counter32
    MAX-ACCESS  read-only
    STATUS      current
    DESCRIPTION 
        "Number of send message retries to a GTP server for which no
         response message was received."
    ::= { ssmGTPIfStatsEntry 1070 }

ssmGTPCIfClientInitiatedDeletes OBJECT-TYPE
    SYNTAX      Counter32
    MAX-ACCESS  read-only
    STATUS      current
    DESCRIPTION 
        "Number of GTP client initiated deletes."
    ::= { ssmGTPIfStatsEntry 1075 }

ssmGTPCIfUnexpectedMsgs OBJECT-TYPE
    SYNTAX      Counter32
    MAX-ACCESS  read-only
    STATUS      current
    DESCRIPTION 
        "Number of GTP-C packets containing an unexpected message."
    ::= { ssmGTPIfStatsEntry 1080 }

ssmGTPCIfUnknownIEs OBJECT-TYPE
    SYNTAX      Counter32
    MAX-ACCESS  read-only
    STATUS      current
    DESCRIPTION 
        "Number of GTP-C packets with unknown information elements."
    ::= { ssmGTPIfStatsEntry 1085 }

ssmGTPCIfUnknownMsgs OBJECT-TYPE
    SYNTAX      Counter32
    MAX-ACCESS  read-only
    STATUS      current
    DESCRIPTION 
        "Number of GTP-C packets with unknown signaling messages."
    ::= { ssmGTPIfStatsEntry 1090 }

ssmGTPUIfTruncatedMsgs OBJECT-TYPE
    SYNTAX      Counter32
    MAX-ACCESS  read-only
    STATUS      current
    DESCRIPTION 
        "Number of received truncated messages on a GTPU interface."
    ::= { ssmGTPIfStatsEntry 1190 }

ssmGTPUIfInvalidTunnels OBJECT-TYPE
    SYNTAX      Counter32
    MAX-ACCESS  read-only
    STATUS      current
    DESCRIPTION 
        "Number of messages received for an invalid tunnel on a GTPU
         interface."
    ::= { ssmGTPIfStatsEntry 1195 }

ssmGTPUIfInvalidSeqNum OBJECT-TYPE
    SYNTAX      Counter32
    MAX-ACCESS  read-only
    STATUS      current
    DESCRIPTION 
        "Number of messages received with an invalid sequence number on a
         GTPU interface."
    ::= { ssmGTPIfStatsEntry 1200 }

ssmGTPUIfGTPUTunnels OBJECT-TYPE
    SYNTAX      Unsigned32
    MAX-ACCESS  read-only
    STATUS      current
    DESCRIPTION 
        "Number of established tunnels currently instantiated in GTPU."
    ::= { ssmGTPIfStatsEntry 1205 }

ssmGTPUIfUnsupportedExtHdr OBJECT-TYPE
    SYNTAX      Counter32
    MAX-ACCESS  read-only
    STATUS      current
    DESCRIPTION 
        "Number of messages received with an unsupported extension header
         on a GTPU interface."
    ::= { ssmGTPIfStatsEntry 1210 }

ssmGTPUIfUnsupportedMsgType OBJECT-TYPE
    SYNTAX      Counter32
    MAX-ACCESS  read-only
    STATUS      current
    DESCRIPTION 
        "Number of messages received with an invalid message type on a
         GTPU interface."
    ::= { ssmGTPIfStatsEntry 1215 }

ssmGTPUIfUnsupportedVer OBJECT-TYPE
    SYNTAX      Counter32
    MAX-ACCESS  read-only
    STATUS      current
    DESCRIPTION 
        "Number of messages received with an unsupported version on GTPU
         interfaces."
    ::= { ssmGTPIfStatsEntry 1220 }

ssmGTPIfName OBJECT-TYPE
    SYNTAX      DisplayString
    MAX-ACCESS  read-only
    STATUS      current
    DESCRIPTION 
        "GTP interface name."
    ::= { ssmGTPIfStatsEntry 2 }

ssmIPsecIfStatsTable OBJECT-TYPE
    SYNTAX      SEQUENCE OF SsmIPsecIfStatsEntry
    MAX-ACCESS  not-accessible
    STATUS      current
    DESCRIPTION 
        "IPsec interface statistics."
    ::= { ssmInterfaces 3030 }

ssmIPsecIfStatsEntry OBJECT-TYPE
    SYNTAX      SsmIPsecIfStatsEntry
    MAX-ACCESS  not-accessible
    STATUS      current
    DESCRIPTION 
        "IPsec interface statistics entry."
    INDEX       { ssmIPsecIfIndex }
    ::= { ssmIPsecIfStatsTable 1 }

SsmIPsecIfStatsEntry ::= SEQUENCE {
    ssmIPsecIfIndex                Integer32,
    ssmIPsecIfName                 DisplayString,
    ssmIPsecIfDecryptFails         Counter64,
    ssmIPsecIfAntiReplayFails      Counter64,
    ssmIPsecIfBlockLenFails        Counter64,
    ssmIPsecIfDummyPackets         Counter64,
    ssmIPsecIfEncryptFails         Counter64,
    ssmIPsecIfICVMismatches        Counter64,
    ssmIPsecIfNHMismatches         Counter64,
    ssmIPsecIfPadMismatches        Counter64,
    ssmIPsecIfRuntPackets          Counter64,
    ssmIPsecIfSeqOverflows         Counter64
}

ssmIPsecIfIndex OBJECT-TYPE
    SYNTAX      Integer32 (1..2147483647)
    MAX-ACCESS  not-accessible
    STATUS      current
    DESCRIPTION 
        "IPsec interface statistics entry index."
    ::= { ssmIPsecIfStatsEntry 1 }

ssmIPsecIfDecryptFails OBJECT-TYPE
    SYNTAX      Counter64
    MAX-ACCESS  read-only
    STATUS      current
    DESCRIPTION 
        "Number of decryption failures for the interface."
    ::= { ssmIPsecIfStatsEntry 1010 }

ssmIPsecIfAntiReplayFails OBJECT-TYPE
    SYNTAX      Counter64
    MAX-ACCESS  read-only
    STATUS      current
    DESCRIPTION 
        "Number of packets received on the interface which failed
         anti-replay checking i.e. duplicates or packets with too low
         sequence number."
    ::= { ssmIPsecIfStatsEntry 1015 }

ssmIPsecIfBlockLenFails OBJECT-TYPE
    SYNTAX      Counter64
    MAX-ACCESS  read-only
    STATUS      current
    DESCRIPTION 
        "Number of packets received on the interface where the length of
         the encrypted data was not a multiple of the cipher block length."
    ::= { ssmIPsecIfStatsEntry 1020 }

ssmIPsecIfDummyPackets OBJECT-TYPE
    SYNTAX      Counter64
    MAX-ACCESS  read-only
    STATUS      current
    DESCRIPTION 
        "Number of received dummy packets on the interface."
    ::= { ssmIPsecIfStatsEntry 1025 }

ssmIPsecIfEncryptFails OBJECT-TYPE
    SYNTAX      Counter64
    MAX-ACCESS  read-only
    STATUS      current
    DESCRIPTION 
        "Number of encryption failures for the interface."
    ::= { ssmIPsecIfStatsEntry 1030 }

ssmIPsecIfICVMismatches OBJECT-TYPE
    SYNTAX      Counter64
    MAX-ACCESS  read-only
    STATUS      current
    DESCRIPTION 
        "Number of packets received on the interface that could not be
         authenticated i.e. the integrity check value did not match the
         expected value."
    ::= { ssmIPsecIfStatsEntry 1035 }

ssmIPsecIfNHMismatches OBJECT-TYPE
    SYNTAX      Counter64
    MAX-ACCESS  read-only
    STATUS      current
    DESCRIPTION 
        "Number of packets received on the interface that did not contain
         the expected next layer protocol."
    ::= { ssmIPsecIfStatsEntry 1040 }

ssmIPsecIfPadMismatches OBJECT-TYPE
    SYNTAX      Counter64
    MAX-ACCESS  read-only
    STATUS      current
    DESCRIPTION 
        "Number of packets received on the interface that with bad
         padding."
    ::= { ssmIPsecIfStatsEntry 1045 }

ssmIPsecIfRuntPackets OBJECT-TYPE
    SYNTAX      Counter64
    MAX-ACCESS  read-only
    STATUS      current
    DESCRIPTION 
        "Number of packets received on the interface that was too short."
    ::= { ssmIPsecIfStatsEntry 1050 }

ssmIPsecIfSeqOverflows OBJECT-TYPE
    SYNTAX      Counter64
    MAX-ACCESS  read-only
    STATUS      current
    DESCRIPTION 
        "Number of sequence number overflows for the interface."
    ::= { ssmIPsecIfStatsEntry 1055 }

ssmIPsecIfName OBJECT-TYPE
    SYNTAX      DisplayString
    MAX-ACCESS  read-only
    STATUS      current
    DESCRIPTION 
        "Name of the interface."
    ::= { ssmIPsecIfStatsEntry 2 }

ssmSSLVPNIfStatsTable OBJECT-TYPE
    SYNTAX      SEQUENCE OF SsmSSLVPNIfStatsEntry
    MAX-ACCESS  not-accessible
    STATUS      current
    DESCRIPTION 
        "SSLVPN interface statistics."
    ::= { ssmInterfaces 3040 }

ssmSSLVPNIfStatsEntry OBJECT-TYPE
    SYNTAX      SsmSSLVPNIfStatsEntry
    MAX-ACCESS  not-accessible
    STATUS      current
    DESCRIPTION 
        "SSLVPN interface statistics entry."
    INDEX       { ssmSSLVPNIfIndex }
    ::= { ssmSSLVPNIfStatsTable 1 }

SsmSSLVPNIfStatsEntry ::= SEQUENCE {
    ssmSSLVPNIfIndex              Integer32,
    ssmSSLVPNIfName               DisplayString,
    ssmSSLVPNCtrlBytesRecv        Counter64,
    ssmSSLVPNCtrlBytesSent        Counter64,
    ssmSSLVPNCtrlPktsRecv         Counter64,
    ssmSSLVPNCtrlPktsResent       Counter64,
    ssmSSLVPNCtrlPktsSent         Counter64,
    ssmSSLVPNDataDecryptFails     Counter64,
    ssmSSLVPNDataIntegrityFails    Counter64,
    ssmSSLVPNDataInvalidPkts      Counter64,
    ssmSSLVPNDataReplayFails      Counter64,
    ssmSSLVPNNegActive            Unsigned32,
    ssmSSLVPNNegFailed            Counter64,
    ssmSSLVPNNegSuccess           Counter64,
    ssmSSLVPNReNegActive          Unsigned32,
    ssmSSLVPNReNegFailed          Counter64,
    ssmSSLVPNReNegSuccess         Counter64,
    ssmSSLVPNSessCur              Unsigned32,
    ssmSSLVPNSessCurrAuth         Unsigned32,
    ssmSSLVPNSessTimedOut         Counter64,
    ssmSSLVPNSessTotal            Counter64,
    ssmSSLVPNChallengeActive      Unsigned32,
    ssmSSLVPNChallengeFailed      Counter64,
    ssmSSLVPNChallengeSuccess     Counter64
}

ssmSSLVPNIfIndex OBJECT-TYPE
    SYNTAX      Integer32 (1..2147483647)
    MAX-ACCESS  not-accessible
    STATUS      current
    DESCRIPTION 
        "SSLVPN interface statistics entry index."
    ::= { ssmSSLVPNIfStatsEntry 1 }

ssmSSLVPNCtrlBytesRecv OBJECT-TYPE
    SYNTAX      Counter64
    MAX-ACCESS  read-only
    STATUS      current
    DESCRIPTION 
        "Control channel bytes received."
    ::= { ssmSSLVPNIfStatsEntry 1010 }

ssmSSLVPNCtrlBytesSent OBJECT-TYPE
    SYNTAX      Counter64
    MAX-ACCESS  read-only
    STATUS      current
    DESCRIPTION 
        "Control channel bytes sent."
    ::= { ssmSSLVPNIfStatsEntry 1020 }

ssmSSLVPNCtrlPktsRecv OBJECT-TYPE
    SYNTAX      Counter64
    MAX-ACCESS  read-only
    STATUS      current
    DESCRIPTION 
        "Control channel packets received."
    ::= { ssmSSLVPNIfStatsEntry 1030 }

ssmSSLVPNCtrlPktsResent OBJECT-TYPE
    SYNTAX      Counter64
    MAX-ACCESS  read-only
    STATUS      current
    DESCRIPTION 
        "Control channel packets that were retransmitted due to not being
         acknowledged by peer."
    ::= { ssmSSLVPNIfStatsEntry 1040 }

ssmSSLVPNCtrlPktsSent OBJECT-TYPE
    SYNTAX      Counter64
    MAX-ACCESS  read-only
    STATUS      current
    DESCRIPTION 
        "Control channel packets sent."
    ::= { ssmSSLVPNIfStatsEntry 1050 }

ssmSSLVPNDataDecryptFails OBJECT-TYPE
    SYNTAX      Counter64
    MAX-ACCESS  read-only
    STATUS      current
    DESCRIPTION 
        "Number of packets on data channel which failed to be decrypted."
    ::= { ssmSSLVPNIfStatsEntry 1060 }

ssmSSLVPNDataIntegrityFails OBJECT-TYPE
    SYNTAX      Counter64
    MAX-ACCESS  read-only
    STATUS      current
    DESCRIPTION 
        "Number of packets on data channel which failed integrity check."
    ::= { ssmSSLVPNIfStatsEntry 1070 }

ssmSSLVPNDataInvalidPkts OBJECT-TYPE
    SYNTAX      Counter64
    MAX-ACCESS  read-only
    STATUS      current
    DESCRIPTION 
        "Encapsulated packets on data channel that the system was unable
         to parse."
    ::= { ssmSSLVPNIfStatsEntry 1080 }

ssmSSLVPNDataReplayFails OBJECT-TYPE
    SYNTAX      Counter64
    MAX-ACCESS  read-only
    STATUS      current
    DESCRIPTION 
        "Number of packets on data channel which failed replay protection
         checks."
    ::= { ssmSSLVPNIfStatsEntry 1090 }

ssmSSLVPNNegActive OBJECT-TYPE
    SYNTAX      Unsigned32
    MAX-ACCESS  read-only
    STATUS      current
    DESCRIPTION 
        "Number of active data encryption key negotiations."
    ::= { ssmSSLVPNIfStatsEntry 1120 }

ssmSSLVPNNegFailed OBJECT-TYPE
    SYNTAX      Counter64
    MAX-ACCESS  read-only
    STATUS      current
    DESCRIPTION 
        "Number of data encryption key negotiations that failed."
    ::= { ssmSSLVPNIfStatsEntry 1130 }

ssmSSLVPNNegSuccess OBJECT-TYPE
    SYNTAX      Counter64
    MAX-ACCESS  read-only
    STATUS      current
    DESCRIPTION 
        "Number of data encryption key negotiations that were successful."
    ::= { ssmSSLVPNIfStatsEntry 1140 }

ssmSSLVPNReNegActive OBJECT-TYPE
    SYNTAX      Unsigned32
    MAX-ACCESS  read-only
    STATUS      current
    DESCRIPTION 
        "Number of active data encryption key renegotiations."
    ::= { ssmSSLVPNIfStatsEntry 1150 }

ssmSSLVPNReNegFailed OBJECT-TYPE
    SYNTAX      Counter64
    MAX-ACCESS  read-only
    STATUS      current
    DESCRIPTION 
        "Number of data encryption key renegotiations that failed."
    ::= { ssmSSLVPNIfStatsEntry 1160 }

ssmSSLVPNReNegSuccess OBJECT-TYPE
    SYNTAX      Counter64
    MAX-ACCESS  read-only
    STATUS      current
    DESCRIPTION 
        "Number of data encryption key renegotiations that were
         successful."
    ::= { ssmSSLVPNIfStatsEntry 1170 }

ssmSSLVPNSessCur OBJECT-TYPE
    SYNTAX      Unsigned32
    MAX-ACCESS  read-only
    STATUS      current
    DESCRIPTION 
        "Current sessions on server."
    ::= { ssmSSLVPNIfStatsEntry 1180 }

ssmSSLVPNSessCurrAuth OBJECT-TYPE
    SYNTAX      Unsigned32
    MAX-ACCESS  read-only
    STATUS      current
    DESCRIPTION 
        "Current authenticated sessions on server."
    ::= { ssmSSLVPNIfStatsEntry 1190 }

ssmSSLVPNSessTimedOut OBJECT-TYPE
    SYNTAX      Counter64
    MAX-ACCESS  read-only
    STATUS      current
    DESCRIPTION 
        "Timed out sessions on server since server start."
    ::= { ssmSSLVPNIfStatsEntry 1200 }

ssmSSLVPNSessTotal OBJECT-TYPE
    SYNTAX      Counter64
    MAX-ACCESS  read-only
    STATUS      current
    DESCRIPTION 
        "Total sessions on server since server start."
    ::= { ssmSSLVPNIfStatsEntry 1210 }

ssmSSLVPNChallengeActive OBJECT-TYPE
    SYNTAX      Unsigned32
    MAX-ACCESS  read-only
    STATUS      current
    DESCRIPTION 
        "Number of active access-challenges."
    ::= { ssmSSLVPNIfStatsEntry 1220 }

ssmSSLVPNChallengeFailed OBJECT-TYPE
    SYNTAX      Counter64
    MAX-ACCESS  read-only
    STATUS      current
    DESCRIPTION 
        "Number of access-challenges that failed."
    ::= { ssmSSLVPNIfStatsEntry 1230 }

ssmSSLVPNChallengeSuccess OBJECT-TYPE
    SYNTAX      Counter64
    MAX-ACCESS  read-only
    STATUS      current
    DESCRIPTION 
        "Number of access-challenges that were successful."
    ::= { ssmSSLVPNIfStatsEntry 1240 }

ssmSSLVPNIfName OBJECT-TYPE
    SYNTAX      DisplayString
    MAX-ACCESS  read-only
    STATUS      current
    DESCRIPTION 
        "Name of the SSLVPN interface."
    ::= { ssmSSLVPNIfStatsEntry 2 }

ssmApplicationControl OBJECT IDENTIFIER
    ::= { clavisterSystemStats 2015 }

ssmAppCtrlAnalyzedBytes OBJECT-TYPE
    SYNTAX      Counter64
    MAX-ACCESS  read-only
    STATUS      current
    DESCRIPTION 
        "Analyzed bytes."
    ::= { ssmApplicationControl 1010 }

ssmAppCtrlAnalyzedPkts OBJECT-TYPE
    SYNTAX      Counter64
    MAX-ACCESS  read-only
    STATUS      current
    DESCRIPTION 
        "Analyzed packets."
    ::= { ssmApplicationControl 1015 }

ssmAppCtrlApps OBJECT-TYPE
    SYNTAX      Unsigned32
    MAX-ACCESS  read-only
    STATUS      current
    DESCRIPTION 
        "Number of applications."
    ::= { ssmApplicationControl 1020 }

ssmAppCtrlFlowsActive OBJECT-TYPE
    SYNTAX      Unsigned32
    MAX-ACCESS  read-only
    STATUS      current
    DESCRIPTION 
        "Number of flows being actively analyzed."
    ::= { ssmApplicationControl 1040 }

ssmAppCtrlFlowsClassified OBJECT-TYPE
    SYNTAX      Unsigned32
    MAX-ACCESS  read-only
    STATUS      current
    DESCRIPTION 
        "Number of flows in the system that have received their final
         classification and have been offloaded."
    ::= { ssmApplicationControl 1045 }

ssmAppCtrlFlowsUnclassified OBJECT-TYPE
    SYNTAX      Unsigned32
    MAX-ACCESS  read-only
    STATUS      current
    DESCRIPTION 
        "Number of inspected flows that are pending classification."
    ::= { ssmApplicationControl 1050 }

ssmAppCtrlReclassifications OBJECT-TYPE
    SYNTAX      Counter64
    MAX-ACCESS  read-only
    STATUS      current
    DESCRIPTION 
        "Reclassifications."
    ::= { ssmApplicationControl 1070 }

ssmAppCtrlTotBytes OBJECT-TYPE
    SYNTAX      Counter64
    MAX-ACCESS  read-only
    STATUS      current
    DESCRIPTION 
        "Total bytes."
    ::= { ssmApplicationControl 1080 }

ssmAppCtrlTotPkts OBJECT-TYPE
    SYNTAX      Counter64
    MAX-ACCESS  read-only
    STATUS      current
    DESCRIPTION 
        "Total packets."
    ::= { ssmApplicationControl 1085 }

ssmAppCtrlUnclBytes OBJECT-TYPE
    SYNTAX      Counter64
    MAX-ACCESS  read-only
    STATUS      current
    DESCRIPTION 
        "Bytes forwarded while initial classification is pending."
    ::= { ssmApplicationControl 1090 }

ssmAppCtrlUnclPkts OBJECT-TYPE
    SYNTAX      Counter64
    MAX-ACCESS  read-only
    STATUS      current
    DESCRIPTION 
        "Packets forwarded while initial classification is pending."
    ::= { ssmApplicationControl 1095 }

ssmAppCtrlStatsTable OBJECT-TYPE
    SYNTAX      SEQUENCE OF SsmAppCtrlStatsEntry
    MAX-ACCESS  not-accessible
    STATUS      current
    DESCRIPTION 
        "Application statistics."
    ::= { ssmApplicationControl 3010 }

ssmAppCtrlStatsEntry OBJECT-TYPE
    SYNTAX      SsmAppCtrlStatsEntry
    MAX-ACCESS  not-accessible
    STATUS      current
    DESCRIPTION 
        "Application control statistics entry."
    INDEX       { ssmAppCtrlAppIndex }
    ::= { ssmAppCtrlStatsTable 1 }

SsmAppCtrlStatsEntry ::= SEQUENCE {
    ssmAppCtrlAppIndex    Integer32,
    ssmAppCtrlAppName    DisplayString,
    ssmAppCtrlAppBytes    Counter64,
    ssmAppCtrlAppPkts    Counter64,
    ssmAppCtrlAppIdentified    Counter64
}

ssmAppCtrlAppIndex OBJECT-TYPE
    SYNTAX      Integer32 (1..2147483647)
    MAX-ACCESS  not-accessible
    STATUS      current
    DESCRIPTION 
        "Application control row index."
    ::= { ssmAppCtrlStatsEntry 1 }

ssmAppCtrlAppBytes OBJECT-TYPE
    SYNTAX      Counter64
    MAX-ACCESS  read-only
    STATUS      current
    DESCRIPTION 
        "Number of bytes forwarded for this application."
    ::= { ssmAppCtrlStatsEntry 1010 }

ssmAppCtrlAppPkts OBJECT-TYPE
    SYNTAX      Counter64
    MAX-ACCESS  read-only
    STATUS      current
    DESCRIPTION 
        "Number of packets forwarded for this application."
    ::= { ssmAppCtrlStatsEntry 1020 }

ssmAppCtrlAppIdentified OBJECT-TYPE
    SYNTAX      Counter64
    MAX-ACCESS  read-only
    STATUS      current
    DESCRIPTION 
        "Number of times the application has been classified."
    ::= { ssmAppCtrlStatsEntry 1030 }

ssmAppCtrlAppName OBJECT-TYPE
    SYNTAX      DisplayString
    MAX-ACCESS  read-only
    STATUS      current
    DESCRIPTION 
        "Application name."
    ::= { ssmAppCtrlStatsEntry 2 }

ssmAuthentication OBJECT IDENTIFIER
    ::= { clavisterSystemStats 2030 }

ssmAuthenticationSystem OBJECT IDENTIFIER
    ::= { ssmAuthentication 2010 }

ssmSysActiveEapAkaUsers OBJECT-TYPE
    SYNTAX      Unsigned32
    MAX-ACCESS  read-only
    STATUS      current
    DESCRIPTION 
        "Current number of active EAP-AKA users system wide."
    ::= { ssmAuthenticationSystem 1005 }

ssmSysActiveEapMd5Users OBJECT-TYPE
    SYNTAX      Unsigned32
    MAX-ACCESS  read-only
    STATUS      current
    DESCRIPTION 
        "Current number of active EAP-MD5 users system wide."
    ::= { ssmAuthenticationSystem 1006 }

ssmSysActiveEapSimUsers OBJECT-TYPE
    SYNTAX      Unsigned32
    MAX-ACCESS  read-only
    STATUS      current
    DESCRIPTION 
        "Current number of active EAP-SIM users system wide."
    ::= { ssmAuthenticationSystem 1010 }

ssmSysActiveUsers OBJECT-TYPE
    SYNTAX      Unsigned32
    MAX-ACCESS  read-only
    STATUS      current
    DESCRIPTION 
        "Current number of active users system wide."
    ::= { ssmAuthenticationSystem 1015 }

ssmSysAuthsFailed OBJECT-TYPE
    SYNTAX      Counter32
    MAX-ACCESS  read-only
    STATUS      current
    DESCRIPTION 
        "Number of failed authentication attempts system wide."
    ::= { ssmAuthenticationSystem 1020 }

ssmSysAuthsRejected OBJECT-TYPE
    SYNTAX      Counter32
    MAX-ACCESS  read-only
    STATUS      current
    DESCRIPTION 
        "Number of rejected authentication attempts system wide."
    ::= { ssmAuthenticationSystem 1025 }

ssmSysAuthsStarted OBJECT-TYPE
    SYNTAX      Counter32
    MAX-ACCESS  read-only
    STATUS      current
    DESCRIPTION 
        "Number of started authentications."
    ::= { ssmAuthenticationSystem 1030 }

ssmSysAuthsEapAkaSucceeded OBJECT-TYPE
    SYNTAX      Counter32
    MAX-ACCESS  read-only
    STATUS      current
    DESCRIPTION 
        "Number of successful EAP-AKA authentications."
    ::= { ssmAuthenticationSystem 1035 }

ssmSysAuthsEapMd5Succeeded OBJECT-TYPE
    SYNTAX      Counter32
    MAX-ACCESS  read-only
    STATUS      current
    DESCRIPTION 
        "Number of successful EAP-AKA authentications system wide."
    ::= { ssmAuthenticationSystem 1036 }

ssmSysAuthsEapSimSucceeded OBJECT-TYPE
    SYNTAX      Counter32
    MAX-ACCESS  read-only
    STATUS      current
    DESCRIPTION 
        "Number of successful EAP-SIM authentications."
    ::= { ssmAuthenticationSystem 1040 }

ssmSysAuthsSucceeded OBJECT-TYPE
    SYNTAX      Counter32
    MAX-ACCESS  read-only
    STATUS      current
    DESCRIPTION 
        "Number of successful authentications resulting in a logged in
         user."
    ::= { ssmAuthenticationSystem 1045 }

ssmSysBruteForceAttacks OBJECT-TYPE
    SYNTAX      Counter32
    MAX-ACCESS  read-only
    STATUS      current
    DESCRIPTION 
        "Number of brute force attack preventions system wide."
    ::= { ssmAuthenticationSystem 1050 }

ssmSysRejectedUsername OBJECT-TYPE
    SYNTAX      Counter32
    MAX-ACCESS  read-only
    STATUS      current
    DESCRIPTION 
        "Number of rejected authentication attempts due to username
         already logged in system wide."
    ::= { ssmAuthenticationSystem 1055 }

ssmSysReplacedUsers OBJECT-TYPE
    SYNTAX      Counter32
    MAX-ACCESS  read-only
    STATUS      current
    DESCRIPTION 
        "Number of replaced logged in users system wide."
    ::= { ssmAuthenticationSystem 1060 }

ssmSysSourceTimeouts OBJECT-TYPE
    SYNTAX      Counter32
    MAX-ACCESS  read-only
    STATUS      current
    DESCRIPTION 
        "Number of times an authentication source has failed to respond
         in time system wide."
    ::= { ssmAuthenticationSystem 1065 }

ssmSysUserIdleTimeouts OBJECT-TYPE
    SYNTAX      Counter32
    MAX-ACCESS  read-only
    STATUS      current
    DESCRIPTION 
        "Number of user that has been logged out due to idle timeout
         system wide."
    ::= { ssmAuthenticationSystem 1070 }

ssmSysUserSessionTimeouts OBJECT-TYPE
    SYNTAX      Counter32
    MAX-ACCESS  read-only
    STATUS      current
    DESCRIPTION 
        "Number of users logged out due to session timeout system wide."
    ::= { ssmAuthenticationSystem 1075 }

ssmRADIUS OBJECT IDENTIFIER
    ::= { ssmAuthentication 2060 }

ssmRadiusPktsParseFail OBJECT-TYPE
    SYNTAX      Counter32
    MAX-ACCESS  read-only
    STATUS      current
    DESCRIPTION 
        "Number of incoming Radius packets that could not be parsed."
    ::= { ssmRADIUS 1015 }

ssmRadiusNonRespServer OBJECT-TYPE
    SYNTAX      Counter32
    MAX-ACCESS  read-only
    STATUS      current
    DESCRIPTION 
        "Number of times a Radius server has failed to answer to Access
         Request after all configured resends have been sent."
    ::= { ssmRADIUS 1020 }

ssmRadiusAcceptPktsRecv OBJECT-TYPE
    SYNTAX      Counter32
    MAX-ACCESS  read-only
    STATUS      current
    DESCRIPTION 
        "Number of received Radius Access-Accept packets."
    ::= { ssmRADIUS 1025 }

ssmRadiusRejectPktsRecv OBJECT-TYPE
    SYNTAX      Counter32
    MAX-ACCESS  read-only
    STATUS      current
    DESCRIPTION 
        "Number of received Radius Access-Reject packets."
    ::= { ssmRADIUS 1030 }

ssmRadiusReqPktResends OBJECT-TYPE
    SYNTAX      Counter32
    MAX-ACCESS  read-only
    STATUS      current
    DESCRIPTION 
        "Number of Access Request packet resends."
    ::= { ssmRADIUS 1035 }

ssmRadiusReqPktsSent OBJECT-TYPE
    SYNTAX      Counter32
    MAX-ACCESS  read-only
    STATUS      current
    DESCRIPTION 
        "Number of sent Radius Access-Request packets."
    ::= { ssmRADIUS 1040 }

ssmAuthProfilesTable OBJECT-TYPE
    SYNTAX      SEQUENCE OF SsmAuthProfilesEntry
    MAX-ACCESS  not-accessible
    STATUS      current
    DESCRIPTION 
        "Authentication profile statistics."
    ::= { ssmAuthentication 3000 }

ssmAuthProfilesEntry OBJECT-TYPE
    SYNTAX      SsmAuthProfilesEntry
    MAX-ACCESS  not-accessible
    STATUS      current
    DESCRIPTION 
        "The row in a table of profile statistics."
    INDEX       { ssmProfileIndex }
    ::= { ssmAuthProfilesTable 1 }

SsmAuthProfilesEntry ::= SEQUENCE {
    ssmProfileIndex                             Integer32,
    ssmProfileName                              DisplayString,
    ssmActiveEapAkaUsers                        Unsigned32,
    ssmActiveEapMd5Users                        Unsigned32,
    ssmActiveEapSimUsers                        Unsigned32,
    ssmActiveUsers                              Unsigned32,
    ssmAuthsFailed                              Counter32,
    ssmAuthsRejected                            Counter32,
    ssmAuthsStarted                             Counter32,
    ssmAuthsEapAkaSucceeded                     Counter32,
    ssmAuthsEapMd5Succeeded                     Counter32,
    ssmAuthsEapSimSucceeded                     Counter32,
    ssmAuthsSucceeded                           Counter32,
    ssmBruteForceAttacks                        Counter32,
    ssmRejectedUsername                         Counter32,
    ssmReplacedUsers                            Counter32,
    ssmUserIdleTimeouts                         Counter32,
    ssmUserSessionTimeouts                      Counter32,
    ssmProfileSourceTimeouts                    Counter32
}

ssmProfileIndex OBJECT-TYPE
    SYNTAX      Integer32 (1..2147483647)
    MAX-ACCESS  not-accessible
    STATUS      current
    DESCRIPTION 
        "Authentication profile row index."
    ::= { ssmAuthProfilesEntry 1 }

ssmActiveEapAkaUsers OBJECT-TYPE
    SYNTAX      Unsigned32
    MAX-ACCESS  read-only
    STATUS      current
    DESCRIPTION 
        "Current number of active EAP-AKA users."
    ::= { ssmAuthProfilesEntry 1010 }

ssmActiveEapMd5Users OBJECT-TYPE
    SYNTAX      Unsigned32
    MAX-ACCESS  read-only
    STATUS      current
    DESCRIPTION 
        "Current number of active EAP-MD5 users."
    ::= { ssmAuthProfilesEntry 1011 }

ssmActiveEapSimUsers OBJECT-TYPE
    SYNTAX      Unsigned32
    MAX-ACCESS  read-only
    STATUS      current
    DESCRIPTION 
        "Current number of active EAP-SIM users."
    ::= { ssmAuthProfilesEntry 1015 }

ssmActiveUsers OBJECT-TYPE
    SYNTAX      Unsigned32
    MAX-ACCESS  read-only
    STATUS      current
    DESCRIPTION 
        "Current number of active users."
    ::= { ssmAuthProfilesEntry 1020 }

ssmAuthsFailed OBJECT-TYPE
    SYNTAX      Counter32
    MAX-ACCESS  read-only
    STATUS      current
    DESCRIPTION 
        "Number of failed authentications."
    ::= { ssmAuthProfilesEntry 1025 }

ssmAuthsRejected OBJECT-TYPE
    SYNTAX      Counter32
    MAX-ACCESS  read-only
    STATUS      current
    DESCRIPTION 
        "Number of rejected authentications."
    ::= { ssmAuthProfilesEntry 1030 }

ssmAuthsStarted OBJECT-TYPE
    SYNTAX      Counter32
    MAX-ACCESS  read-only
    STATUS      current
    DESCRIPTION 
        "Number of started authentications."
    ::= { ssmAuthProfilesEntry 1035 }

ssmAuthsEapAkaSucceeded OBJECT-TYPE
    SYNTAX      Counter32
    MAX-ACCESS  read-only
    STATUS      current
    DESCRIPTION 
        "Number of successful EAP-AKA authentications."
    ::= { ssmAuthProfilesEntry 1040 }

ssmAuthsEapMd5Succeeded OBJECT-TYPE
    SYNTAX      Counter32
    MAX-ACCESS  read-only
    STATUS      current
    DESCRIPTION 
        "Number of successful EAP-MD5 authentications."
    ::= { ssmAuthProfilesEntry 1041 }

ssmAuthsEapSimSucceeded OBJECT-TYPE
    SYNTAX      Counter32
    MAX-ACCESS  read-only
    STATUS      current
    DESCRIPTION 
        "Number of successful EAP-SIM authentications."
    ::= { ssmAuthProfilesEntry 1045 }

ssmAuthsSucceeded OBJECT-TYPE
    SYNTAX      Counter32
    MAX-ACCESS  read-only
    STATUS      current
    DESCRIPTION 
        "Number of successful authentications resulting in a logged in
         user."
    ::= { ssmAuthProfilesEntry 1050 }

ssmBruteForceAttacks OBJECT-TYPE
    SYNTAX      Counter32
    MAX-ACCESS  read-only
    STATUS      current
    DESCRIPTION 
        "Number of brute force attack preventions."
    ::= { ssmAuthProfilesEntry 1055 }

ssmRejectedUsername OBJECT-TYPE
    SYNTAX      Counter32
    MAX-ACCESS  read-only
    STATUS      current
    DESCRIPTION 
        "Number of rejected authentication attempts due to username
         already logged in."
    ::= { ssmAuthProfilesEntry 1060 }

ssmReplacedUsers OBJECT-TYPE
    SYNTAX      Counter32
    MAX-ACCESS  read-only
    STATUS      current
    DESCRIPTION 
        "Number of replaced logged in users."
    ::= { ssmAuthProfilesEntry 1065 }

ssmUserIdleTimeouts OBJECT-TYPE
    SYNTAX      Counter32
    MAX-ACCESS  read-only
    STATUS      current
    DESCRIPTION 
        "Number users logged out due to idle timeout."
    ::= { ssmAuthProfilesEntry 1070 }

ssmUserSessionTimeouts OBJECT-TYPE
    SYNTAX      Counter32
    MAX-ACCESS  read-only
    STATUS      current
    DESCRIPTION 
        "Number of users logged out due to session timeout."
    ::= { ssmAuthProfilesEntry 1075 }

ssmProfileSourceTimeouts OBJECT-TYPE
    SYNTAX      Counter32
    MAX-ACCESS  read-only
    STATUS      current
    DESCRIPTION 
        "Number of times an authentication source has failed to respond
         in time."
    ::= { ssmAuthProfilesEntry 1080 }

ssmProfileName OBJECT-TYPE
    SYNTAX      DisplayString
    MAX-ACCESS  read-only
    STATUS      current
    DESCRIPTION 
        "Authentication profile name."
    ::= { ssmAuthProfilesEntry 2 }

ssmInternal OBJECT IDENTIFIER
    ::= { clavisterSystemStats 2040 }

ssmHAInternal OBJECT IDENTIFIER
    ::= { ssmInternal 2010 }

ssmHAIntHBDelay OBJECT-TYPE
    SYNTAX      Unsigned32
    MAX-ACCESS  read-only
    STATUS      current
    DESCRIPTION 
        "Current maximum delay of HA heart-beats in internal queues in
         milliseconds."
    ::= { ssmHAInternal 1005 }

ssmHAIntMessagesToCtrlPlane OBJECT-TYPE
    SYNTAX      Unsigned32
    MAX-ACCESS  read-only
    STATUS      current
    DESCRIPTION 
        "Number of HA messages sent from data plane to control plane."
    ::= { ssmHAInternal 1010 }

ssmHAIntDep OBJECT IDENTIFIER
    ::= { ssmHAInternal 2010 }

ssmHAIntDepDirectResolved OBJECT-TYPE
    SYNTAX      Unsigned32
    MAX-ACCESS  read-only
    STATUS      current
    DESCRIPTION 
        "HA objects with dependencies that could be resolved directly by
         querying the cache."
    ::= { ssmHAIntDep 1005 }

ssmHAIntDepDelayedResolved OBJECT-TYPE
    SYNTAX      Unsigned32
    MAX-ACCESS  read-only
    STATUS      current
    DESCRIPTION 
        "HA objects delayed due to dependencies that later resolved
         successfully."
    ::= { ssmHAIntDep 1010 }

ssmHAIntDepTimeout OBJECT-TYPE
    SYNTAX      Unsigned32
    MAX-ACCESS  read-only
    STATUS      current
    DESCRIPTION 
        "HA objects that timed out while waiting for dependencies to be
         resolved."
    ::= { ssmHAIntDep 1015 }

ssmHAIntDepDropped OBJECT-TYPE
    SYNTAX      Unsigned32
    MAX-ACCESS  read-only
    STATUS      current
    DESCRIPTION 
        "Number of HA objects dropped due to resource shortage in the
         dependency system."
    ::= { ssmHAIntDep 1020 }

ssmHAIntDepReplaced OBJECT-TYPE
    SYNTAX      Unsigned32
    MAX-ACCESS  read-only
    STATUS      current
    DESCRIPTION 
        "Number of HA objects replaced while waiting for dependencies to
         be resolved."
    ::= { ssmHAIntDep 1025 }

ssmPktAccTable OBJECT-TYPE
    SYNTAX      SEQUENCE OF SsmPktAccEntry
    MAX-ACCESS  not-accessible
    STATUS      current
    DESCRIPTION 
        "Packet account statistics table."
    ::= { ssmInternal 3010 }

ssmPktAccEntry OBJECT-TYPE
    SYNTAX      SsmPktAccEntry
    MAX-ACCESS  not-accessible
    STATUS      current
    DESCRIPTION 
        "An entry in the packet account statistics table."
    INDEX       { ssmPktAccIndex }
    ::= { ssmPktAccTable 1 }

SsmPktAccEntry ::= SEQUENCE {
    ssmPktAccIndex      Integer32,
    ssmPktAccName       DisplayString,
    ssmPktAccUsage      Integer32
}

ssmPktAccIndex OBJECT-TYPE
    SYNTAX      Integer32 (1..2147483647)
    MAX-ACCESS  not-accessible
    STATUS      current
    DESCRIPTION 
        "Packet account entry index."
    ::= { ssmPktAccEntry 1 }

ssmPktAccUsage OBJECT-TYPE
    SYNTAX      Integer32
    MAX-ACCESS  read-only
    STATUS      current
    DESCRIPTION 
        "Packet account usage."
    ::= { ssmPktAccEntry 1010 }

ssmPktAccName OBJECT-TYPE
    SYNTAX      DisplayString
    MAX-ACCESS  read-only
    STATUS      current
    DESCRIPTION 
        "Packet account name."
    ::= { ssmPktAccEntry 2 }

ssmMonitoring OBJECT IDENTIFIER
    ::= { clavisterSystemStats 2050 }

ssmHWmon OBJECT IDENTIFIER
    ::= { ssmMonitoring 2030 }

ssmHWSensorTable OBJECT-TYPE
    SYNTAX      SEQUENCE OF SsmHWSensorEntry
    MAX-ACCESS  not-accessible
    STATUS      current
    DESCRIPTION 
        "Sensor monitoring table."
    ::= { ssmHWmon 3040 }

ssmHWSensorEntry OBJECT-TYPE
    SYNTAX      SsmHWSensorEntry
    MAX-ACCESS  not-accessible
    STATUS      current
    DESCRIPTION 
        "Sensor monitoring entry."
    INDEX       { ssmHWSensorIndex }
    ::= { ssmHWSensorTable 1 }

SsmHWSensorEntry ::= SEQUENCE {
    ssmHWSensorIndex         Integer32,
    ssmHWSensorName          DisplayString,
    ssmHWSensorValue         Integer32,
    ssmHWSensorStatus        DisplayString,
    ssmHWSensorType          DisplayString,
    ssmHWSensorUnitType      DisplayString,
    ssmHWSensorHighest       Integer32,
    ssmHWSensorLowest        Integer32,
    ssmHWSensorHighCount     Unsigned32,
    ssmHWSensorLowCount      Unsigned32
}

ssmHWSensorIndex OBJECT-TYPE
    SYNTAX      Integer32 (1..2147483647)
    MAX-ACCESS  not-accessible
    STATUS      current
    DESCRIPTION 
        "Sensor table index."
    ::= { ssmHWSensorEntry 1 }

ssmHWSensorValue OBJECT-TYPE
    SYNTAX      Integer32
    MAX-ACCESS  read-only
    STATUS      current
    DESCRIPTION 
        "Sensor read value."
    ::= { ssmHWSensorEntry 1010 }

ssmHWSensorStatus OBJECT-TYPE
    SYNTAX      DisplayString
    MAX-ACCESS  read-only
    STATUS      current
    DESCRIPTION 
        "Sensor operational status."
    ::= { ssmHWSensorEntry 1020 }

ssmHWSensorType OBJECT-TYPE
    SYNTAX      DisplayString
    MAX-ACCESS  read-only
    STATUS      current
    DESCRIPTION 
        "Type of sensor."
    ::= { ssmHWSensorEntry 1030 }

ssmHWSensorUnitType OBJECT-TYPE
    SYNTAX      DisplayString
    MAX-ACCESS  read-only
    STATUS      current
    DESCRIPTION 
        "Sensor unit type representation."
    ::= { ssmHWSensorEntry 1040 }

ssmHWSensorHighest OBJECT-TYPE
    SYNTAX      Integer32
    MAX-ACCESS  read-only
    STATUS      current
    DESCRIPTION 
        "Sensor highest recorded value."
    ::= { ssmHWSensorEntry 1050 }

ssmHWSensorLowest OBJECT-TYPE
    SYNTAX      Integer32
    MAX-ACCESS  read-only
    STATUS      current
    DESCRIPTION 
        "Sensor lowest recorded value."
    ::= { ssmHWSensorEntry 1060 }

ssmHWSensorHighCount OBJECT-TYPE
    SYNTAX      Unsigned32
    MAX-ACCESS  read-only
    STATUS      current
    DESCRIPTION 
        "Number of times the sensor was above the high threshold since
         last hwmon restart."
    ::= { ssmHWSensorEntry 1070 }

ssmHWSensorLowCount OBJECT-TYPE
    SYNTAX      Unsigned32
    MAX-ACCESS  read-only
    STATUS      current
    DESCRIPTION 
        "Number of times the sensor was below the low threshold since
         last hwmon restart."
    ::= { ssmHWSensorEntry 1080 }

ssmHWSensorName OBJECT-TYPE
    SYNTAX      DisplayString
    MAX-ACCESS  read-only
    STATUS      current
    DESCRIPTION 
        "Sensor name."
    ::= { ssmHWSensorEntry 2 }

ssmLogs OBJECT IDENTIFIER
    ::= { ssmMonitoring 2040 }

ssmLogsFromControlPlane OBJECT-TYPE
    SYNTAX      Counter64
    MAX-ACCESS  read-only
    STATUS      current
    DESCRIPTION 
        "Number of log messages originated from control plane."
    ::= { ssmLogs 1005 }

ssmLogsFromDataPlane OBJECT-TYPE
    SYNTAX      Counter64
    MAX-ACCESS  read-only
    STATUS      current
    DESCRIPTION 
        "Number of log messages originated from data plane."
    ::= { ssmLogs 1010 }

ssmCLILog OBJECT IDENTIFIER
    ::= { ssmLogs 2010 }

ssmCLILogIPCFail OBJECT-TYPE
    SYNTAX      Counter64
    MAX-ACCESS  read-only
    STATUS      current
    DESCRIPTION 
        "Number of CLI log messages discarded due to internal
         communication failure."
    ::= { ssmCLILog 1005 }

ssmCLILogMemAllocFail OBJECT-TYPE
    SYNTAX      Counter64
    MAX-ACCESS  read-only
    STATUS      current
    DESCRIPTION 
        "Number of CLI log messages discarded due to failure to allocate
         memory."
    ::= { ssmCLILog 1010 }

ssmCLILogThrottled OBJECT-TYPE
    SYNTAX      Counter64
    MAX-ACCESS  read-only
    STATUS      current
    DESCRIPTION 
        "Number of CLI log messages discarded due to exceeding the
         specified rate limit."
    ::= { ssmCLILog 1015 }

ssmCLILogSent OBJECT-TYPE
    SYNTAX      Counter64
    MAX-ACCESS  read-only
    STATUS      current
    DESCRIPTION 
        "Number of log messages sent to the CLI."
    ::= { ssmCLILog 1020 }

ssmSNMPTrapLog OBJECT IDENTIFIER
    ::= { ssmLogs 2015 }

ssmSnmpTrapLogIPCFail OBJECT-TYPE
    SYNTAX      Counter64
    MAX-ACCESS  read-only
    STATUS      current
    DESCRIPTION 
        "Number of snmptrap messages discarded due to internal
         communication failure."
    ::= { ssmSNMPTrapLog 1005 }

ssmSnmpTrapLogMemAllocFail OBJECT-TYPE
    SYNTAX      Counter64
    MAX-ACCESS  read-only
    STATUS      current
    DESCRIPTION 
        "Number of snmptrap messages discarded due to failure to allocate
         memory."
    ::= { ssmSNMPTrapLog 1010 }

ssmSnmpTrapLogThrottled OBJECT-TYPE
    SYNTAX      Counter64
    MAX-ACCESS  read-only
    STATUS      current
    DESCRIPTION 
        "Number of snmptrap messages discarded due to exceeding the
         specified rate limit."
    ::= { ssmSNMPTrapLog 1015 }

ssmSnmpTrapLogSent OBJECT-TYPE
    SYNTAX      Counter64
    MAX-ACCESS  read-only
    STATUS      current
    DESCRIPTION 
        "Number of snmptrap messages sent to snmptrap receivers."
    ::= { ssmSNMPTrapLog 1020 }

ssmSyslog OBJECT IDENTIFIER
    ::= { ssmLogs 2050 }

ssmSyslogIPCFail OBJECT-TYPE
    SYNTAX      Counter64
    MAX-ACCESS  read-only
    STATUS      current
    DESCRIPTION 
        "Number of syslog messages discarded due to internal
         communication failure."
    ::= { ssmSyslog 1005 }

ssmSyslogMemAllocFail OBJECT-TYPE
    SYNTAX      Counter64
    MAX-ACCESS  read-only
    STATUS      current
    DESCRIPTION 
        "Number of syslog messages discarded due to failure to allocate
         memory."
    ::= { ssmSyslog 1010 }

ssmSyslogThrottled OBJECT-TYPE
    SYNTAX      Counter64
    MAX-ACCESS  read-only
    STATUS      current
    DESCRIPTION 
        "Number of syslog messages discarded due to exceeding the
         specified rate limit."
    ::= { ssmSyslog 1015 }

ssmSyslogSent OBJECT-TYPE
    SYNTAX      Counter64
    MAX-ACCESS  read-only
    STATUS      current
    DESCRIPTION 
        "Number of log messages sent to syslog receivers."
    ::= { ssmSyslog 1020 }

ssmLogReceiverTable OBJECT-TYPE
    SYNTAX      SEQUENCE OF SsmLogReceiverEntry
    MAX-ACCESS  not-accessible
    STATUS      current
    DESCRIPTION 
        "Log receiver statistics."
    ::= { ssmLogs 3050 }

ssmLogReceiverEntry OBJECT-TYPE
    SYNTAX      SsmLogReceiverEntry
    MAX-ACCESS  not-accessible
    STATUS      current
    DESCRIPTION 
        "Log receiver statistics entry."
    INDEX       { ssmLogReceiverIndex }
    ::= { ssmLogReceiverTable 1 }

SsmLogReceiverEntry ::= SEQUENCE {
    ssmLogReceiverIndex      Integer32,
    ssmLogReceiverName       DisplayString,
    ssmLogReceiverType       DisplayString,
    ssmLogReceiverLogsSent    Counter64,
    ssmLogReceiverLogsThrottled    Counter64,
    ssmLogReceiverLogsFailed    Counter64
}

ssmLogReceiverIndex OBJECT-TYPE
    SYNTAX      Integer32 (1..2147483647)
    MAX-ACCESS  not-accessible
    STATUS      current
    DESCRIPTION 
        "Log receiver statistics row index."
    ::= { ssmLogReceiverEntry 1 }

ssmLogReceiverType OBJECT-TYPE
    SYNTAX      DisplayString
    MAX-ACCESS  read-only
    STATUS      current
    DESCRIPTION 
        "Log receiver type."
    ::= { ssmLogReceiverEntry 1010 }

ssmLogReceiverLogsSent OBJECT-TYPE
    SYNTAX      Counter64
    MAX-ACCESS  read-only
    STATUS      current
    DESCRIPTION 
        "Number of log messages sent to the receiver."
    ::= { ssmLogReceiverEntry 1020 }

ssmLogReceiverLogsThrottled OBJECT-TYPE
    SYNTAX      Counter64
    MAX-ACCESS  read-only
    STATUS      current
    DESCRIPTION 
        "Number of logs discarded due to exceeding the rate limit
         configured on the receiver."
    ::= { ssmLogReceiverEntry 1030 }

ssmLogReceiverLogsFailed OBJECT-TYPE
    SYNTAX      Counter64
    MAX-ACCESS  read-only
    STATUS      current
    DESCRIPTION 
        "Number of logs discarded due to failures while formatting or
         sending the log."
    ::= { ssmLogReceiverEntry 1040 }

ssmLogReceiverName OBJECT-TYPE
    SYNTAX      DisplayString
    MAX-ACCESS  read-only
    STATUS      current
    DESCRIPTION 
        "Log receiver name."
    ::= { ssmLogReceiverEntry 2 }

ssmSNMP OBJECT IDENTIFIER
    ::= { ssmMonitoring 2050 }

ssmSnmpPktsRecv OBJECT-TYPE
    SYNTAX      Counter32
    MAX-ACCESS  read-only
    STATUS      current
    DESCRIPTION 
        "Number of received SNMP requests."
    ::= { ssmSNMP 1 }

ssmSnmpSuccessfulRequests OBJECT-TYPE
    SYNTAX      Counter32
    MAX-ACCESS  read-only
    STATUS      current
    DESCRIPTION 
        "Number of received SNMP requests, that were successfully replied
         to."
    ::= { ssmSNMP 1005 }

ssmSnmpFailedRequests OBJECT-TYPE
    SYNTAX      Counter32
    MAX-ACCESS  read-only
    STATUS      current
    DESCRIPTION 
        "Number of received SNMP requests, that we failed to respond to.
         The reason could be failure to fetch a corresponding statistical
         value or failure to send a response. Statistics counted by
         SilentDrops-counter is not included in this count."
    ::= { ssmSNMP 1010 }

ssmSnmpThrottledRequests OBJECT-TYPE
    SYNTAX      Counter32
    MAX-ACCESS  read-only
    STATUS      current
    DESCRIPTION 
        "Number of received SNMP requests, that were dropped due to
         exceeding the configured request limit."
    ::= { ssmSNMP 1015 }

ssmSnmpUnsupportedSecLevels OBJECT-TYPE
    SYNTAX      Counter32
    MAX-ACCESS  read-only
    STATUS      current
    DESCRIPTION 
        "Total number of packets received by the SNMP engine which were
         dropped because they requested a securityLevel that was unknown
         to the SNMP engine or otherwise unavailable."
    ::= { ssmSNMP 1020 }

ssmSnmpNotInTimeWindows OBJECT-TYPE
    SYNTAX      Counter32
    MAX-ACCESS  read-only
    STATUS      current
    DESCRIPTION 
        "Total number of packets received by the SNMP engine which were
         dropped because they appeared outside of the authoritative SNMP
         engine's window."
    ::= { ssmSNMP 1024 }

ssmSnmpUnknownUserNames OBJECT-TYPE
    SYNTAX      Counter32
    MAX-ACCESS  read-only
    STATUS      current
    DESCRIPTION 
        "Total number of packets received by the SNMP engine which were
         dropped because they referenced a user that was not known to the
         SNMP engine."
    ::= { ssmSNMP 1030 }

ssmSnmpUnknownEngineIDs OBJECT-TYPE
    SYNTAX      Counter32
    MAX-ACCESS  read-only
    STATUS      current
    DESCRIPTION 
        "Total number of packets received by the SNMP engine which were
         dropped because they referenced an snmpEngineID that was not
         known to the SNMP engine."
    ::= { ssmSNMP 1035 }

ssmSnmpWrongDigests OBJECT-TYPE
    SYNTAX      Counter32
    MAX-ACCESS  read-only
    STATUS      current
    DESCRIPTION 
        "Total number of packets received by the SNMP engine which were
         dropped because they didn't contain the expected digest value."
    ::= { ssmSNMP 1040 }

ssmSnmpDecryptionErrors OBJECT-TYPE
    SYNTAX      Counter32
    MAX-ACCESS  read-only
    STATUS      current
    DESCRIPTION 
        "Total number of packets received by the SNMP engine which were
         dropped because they could not be decrypted."
    ::= { ssmSNMP 1045 }

ssmSnmpdEngineBoots OBJECT-TYPE
    SYNTAX      Integer32
    MAX-ACCESS  read-only
    STATUS      current
    DESCRIPTION 
        "Number of times SNMP engine has re-initialized itself since
         snmpEngineID was last configured."
    ::= { ssmSNMP 1050 }

ssmSnmpBadVersion OBJECT-TYPE
    SYNTAX      Counter32
    MAX-ACCESS  read-only
    STATUS      current
    DESCRIPTION 
        "Number of SNMP requests for an unsupported SNMP version."
    ::= { ssmSNMP 3 }

ssmSnmpSilentDrops OBJECT-TYPE
    SYNTAX      Counter32
    MAX-ACCESS  read-only
    STATUS      current
    DESCRIPTION 
        "Number of PDUs received and silently dropped because an minimal
         response PDU would exceed the maximum message size."
    ::= { ssmSNMP 31 }

ssmSnmpBadCommunityName OBJECT-TYPE
    SYNTAX      Counter32
    MAX-ACCESS  read-only
    STATUS      current
    DESCRIPTION 
        "Number of SNMP requests with incorrect community name."
    ::= { ssmSNMP 4 }

ssmSnmpBadCommunityUse OBJECT-TYPE
    SYNTAX      Counter32
    MAX-ACCESS  read-only
    STATUS      current
    DESCRIPTION 
        "Number of SNMP requests that represent a disallowed SNMP
         operation."
    ::= { ssmSNMP 5 }

ssmSnmpASNParseErrors OBJECT-TYPE
    SYNTAX      Counter32
    MAX-ACCESS  read-only
    STATUS      current
    DESCRIPTION 
        "Number of SNMP requests containing ASN.1/BER errors."
    ::= { ssmSNMP 6 }

ssmRouting OBJECT IDENTIFIER
    ::= { clavisterSystemStats 2060 }

ssmDynRoutesCreated OBJECT-TYPE
    SYNTAX      Counter32
    MAX-ACCESS  read-only
    STATUS      current
    DESCRIPTION 
        "Number of dynamic route additions in system."
    ::= { ssmRouting 1005 }

ssmDynRoutesCurrent OBJECT-TYPE
    SYNTAX      Gauge32
    MAX-ACCESS  read-only
    STATUS      current
    DESCRIPTION 
        "Current number of dynamic routes in system."
    ::= { ssmRouting 1010 }

ssmDynRoutesMax OBJECT-TYPE
    SYNTAX      Unsigned32
    MAX-ACCESS  read-only
    STATUS      current
    DESCRIPTION 
        "Maximum number of dynamic routes in system."
    ::= { ssmRouting 1015 }

ssmStaticRoutes OBJECT-TYPE
    SYNTAX      Gauge32
    MAX-ACCESS  read-only
    STATUS      current
    DESCRIPTION 
        "Current number of static routes in system."
    ::= { ssmRouting 1020 }

ssmOSPF OBJECT IDENTIFIER
    ::= { ssmRouting 2010 }

ssmOspfPktParamErrors OBJECT-TYPE
    SYNTAX      Counter32
    MAX-ACCESS  read-only
    STATUS      current
    DESCRIPTION 
        "Number of packets with parameter errors."
    ::= { ssmOSPF 1005 }

ssmOspfProcTable OBJECT-TYPE
    SYNTAX      SEQUENCE OF SsmOspfProcEntry
    MAX-ACCESS  not-accessible
    STATUS      current
    DESCRIPTION 
        "OSPF statistics table."
    ::= { ssmOSPF 3010 }

ssmOspfProcEntry OBJECT-TYPE
    SYNTAX      SsmOspfProcEntry
    MAX-ACCESS  not-accessible
    STATUS      current
    DESCRIPTION 
        "OSPF process statistics."
    INDEX       { ssmOspfProcIndex }
    ::= { ssmOspfProcTable 1 }

SsmOspfProcEntry ::= SEQUENCE {
    ssmOspfProcIndex          Integer32,
    ssmOspfProcName           DisplayString,
    ssmOspfExportedRoutes     Unsigned32,
    ssmOspfCurrentRoutes      Gauge32,
    ssmOspfMaxRoutes          Unsigned32,
    ssmOspfCurrentLSA         Gauge32,
    ssmOspfMaxLsa             Unsigned32,
    ssmOspfCurrentRouters     Gauge32,
    ssmOspfMaxRouters         Unsigned32,
    ssmOspfFailedAdjacencies    Counter32,
    ssmOspfLsaErrors          Counter32
}

ssmOspfProcIndex OBJECT-TYPE
    SYNTAX      Integer32 (1..2147483647)
    MAX-ACCESS  not-accessible
    STATUS      current
    DESCRIPTION 
        "OSPF process in table index."
    ::= { ssmOspfProcEntry 1 }

ssmOspfExportedRoutes OBJECT-TYPE
    SYNTAX      Unsigned32
    MAX-ACCESS  read-only
    STATUS      current
    DESCRIPTION 
        "Number of routes that have been exported from the OSPF process
         into the system."
    ::= { ssmOspfProcEntry 1005 }

ssmOspfCurrentRoutes OBJECT-TYPE
    SYNTAX      Gauge32
    MAX-ACCESS  read-only
    STATUS      current
    DESCRIPTION 
        "Current number of routes originating from the OSPF process."
    ::= { ssmOspfProcEntry 1010 }

ssmOspfMaxRoutes OBJECT-TYPE
    SYNTAX      Unsigned32
    MAX-ACCESS  read-only
    STATUS      current
    DESCRIPTION 
        "Maximum number of routes that have been originated from the OSPF
         process."
    ::= { ssmOspfProcEntry 1015 }

ssmOspfCurrentLSA OBJECT-TYPE
    SYNTAX      Gauge32
    MAX-ACCESS  read-only
    STATUS      current
    DESCRIPTION 
        "Current number of LSAs that are held by the OSPF process."
    ::= { ssmOspfProcEntry 1020 }

ssmOspfMaxLsa OBJECT-TYPE
    SYNTAX      Unsigned32
    MAX-ACCESS  read-only
    STATUS      current
    DESCRIPTION 
        "Maximum number of LSAs that has been held by this OSPF process."
    ::= { ssmOspfProcEntry 1025 }

ssmOspfCurrentRouters OBJECT-TYPE
    SYNTAX      Gauge32
    MAX-ACCESS  read-only
    STATUS      current
    DESCRIPTION 
        "Number of routers that currently are connected to the OSPF
         process."
    ::= { ssmOspfProcEntry 1030 }

ssmOspfMaxRouters OBJECT-TYPE
    SYNTAX      Unsigned32
    MAX-ACCESS  read-only
    STATUS      current
    DESCRIPTION 
        "Maximum number of routers that have been connected to this OSPF
         process."
    ::= { ssmOspfProcEntry 1035 }

ssmOspfFailedAdjacencies OBJECT-TYPE
    SYNTAX      Counter32
    MAX-ACCESS  read-only
    STATUS      current
    DESCRIPTION 
        "Number of adjacencies that have failed to form."
    ::= { ssmOspfProcEntry 1040 }

ssmOspfLsaErrors OBJECT-TYPE
    SYNTAX      Counter32
    MAX-ACCESS  read-only
    STATUS      current
    DESCRIPTION 
        "Number of LSA that failed the interpretation validation check."
    ::= { ssmOspfProcEntry 1045 }

ssmOspfProcName OBJECT-TYPE
    SYNTAX      DisplayString
    MAX-ACCESS  read-only
    STATUS      current
    DESCRIPTION 
        "OSPF process name."
    ::= { ssmOspfProcEntry 2 }

ssmRoutingOriginatorTable OBJECT-TYPE
    SYNTAX      SEQUENCE OF SsmRoutingOriginatorEntry
    MAX-ACCESS  not-accessible
    STATUS      current
    DESCRIPTION 
        "Routing originators statistics."
    ::= { ssmRouting 2060 }

ssmRoutingOriginatorEntry OBJECT-TYPE
    SYNTAX      SsmRoutingOriginatorEntry
    MAX-ACCESS  not-accessible
    STATUS      current
    DESCRIPTION 
        "Routing originator entry statistics."
    INDEX       { ssmOriginatorDynRoutesIndex }
    ::= { ssmRoutingOriginatorTable 1 }

SsmRoutingOriginatorEntry ::= SEQUENCE {
    ssmOriginatorDynRoutesIndex      Integer32,
    ssmOriginatorDynRoutesName       DisplayString,
    ssmOriginatorDynRoutesCreated    Counter32,
    ssmOriginatorDynRoutesCurrent    Gauge32,
    ssmOriginatorDynRoutesMax        Unsigned32
}

ssmOriginatorDynRoutesIndex OBJECT-TYPE
    SYNTAX      Integer32 (1..2147483647)
    MAX-ACCESS  not-accessible
    STATUS      current
    DESCRIPTION 
        "Originator statistics row index."
    ::= { ssmRoutingOriginatorEntry 1 }

ssmOriginatorDynRoutesCreated OBJECT-TYPE
    SYNTAX      Counter32
    MAX-ACCESS  read-only
    STATUS      current
    DESCRIPTION 
        "Number of dynamic route additions by originator."
    ::= { ssmRoutingOriginatorEntry 1015 }

ssmOriginatorDynRoutesCurrent OBJECT-TYPE
    SYNTAX      Gauge32
    MAX-ACCESS  read-only
    STATUS      current
    DESCRIPTION 
        "Current number of dynamic routes by originator."
    ::= { ssmRoutingOriginatorEntry 1020 }

ssmOriginatorDynRoutesMax OBJECT-TYPE
    SYNTAX      Unsigned32
    MAX-ACCESS  read-only
    STATUS      current
    DESCRIPTION 
        "Maximum number of dynamic routes by originator."
    ::= { ssmRoutingOriginatorEntry 1025 }

ssmOriginatorDynRoutesName OBJECT-TYPE
    SYNTAX      DisplayString
    MAX-ACCESS  read-only
    STATUS      current
    DESCRIPTION 
        "Name of routing originator."
    ::= { ssmRoutingOriginatorEntry 2 }

ssmRouteMonitoring OBJECT IDENTIFIER
    ::= { ssmRouting 2070 }

ssmRouteMonNumMonitored OBJECT-TYPE
    SYNTAX      Unsigned32
    MAX-ACCESS  read-only
    STATUS      current
    DESCRIPTION 
        "Number of routes with monitoring enabled."
    ::= { ssmRouteMonitoring 1000 }

ssmRouteMonNumDisabled OBJECT-TYPE
    SYNTAX      Unsigned32
    MAX-ACCESS  read-only
    STATUS      current
    DESCRIPTION 
        "Number of monitored routes currently disabled."
    ::= { ssmRouteMonitoring 1010 }

ssmRouteMonTable OBJECT-TYPE
    SYNTAX      SEQUENCE OF SsmRouteMonEntry
    MAX-ACCESS  not-accessible
    STATUS      current
    DESCRIPTION 
        "Route statistics."
    ::= { ssmRouteMonitoring 3000 }

ssmRouteMonEntry OBJECT-TYPE
    SYNTAX      SsmRouteMonEntry
    MAX-ACCESS  not-accessible
    STATUS      current
    DESCRIPTION 
        "Route entry."
    INDEX       { ssmRouteMonIndex }
    ::= { ssmRouteMonTable 1 }

SsmRouteMonEntry ::= SEQUENCE {
    ssmRouteMonIndex         Integer32,
    ssmRouteMonName          DisplayString,
    ssmRouteMonRoutingTable    DisplayString,
    ssmRouteMonInterface     DisplayString,
    ssmRouteMonNetwork       DisplayString,
    ssmRouteMonDisables      Counter32,
    ssmRouteMonStatus        DisplayString,
    ssmRouteMonFailReason    DisplayString
}

ssmRouteMonIndex OBJECT-TYPE
    SYNTAX      Integer32 (1..2147483647)
    MAX-ACCESS  not-accessible
    STATUS      current
    DESCRIPTION 
        "Route monitor instance statistics row index."
    ::= { ssmRouteMonEntry 1 }

ssmRouteMonRoutingTable OBJECT-TYPE
    SYNTAX      DisplayString
    MAX-ACCESS  read-only
    STATUS      current
    DESCRIPTION 
        "Routing table containing the route."
    ::= { ssmRouteMonEntry 1000 }

ssmRouteMonInterface OBJECT-TYPE
    SYNTAX      DisplayString
    MAX-ACCESS  read-only
    STATUS      current
    DESCRIPTION 
        "Interface of the route."
    ::= { ssmRouteMonEntry 1010 }

ssmRouteMonNetwork OBJECT-TYPE
    SYNTAX      DisplayString
    MAX-ACCESS  read-only
    STATUS      current
    DESCRIPTION 
        "Network range of the route."
    ::= { ssmRouteMonEntry 1020 }

ssmRouteMonDisables OBJECT-TYPE
    SYNTAX      Counter32
    MAX-ACCESS  read-only
    STATUS      current
    DESCRIPTION 
        "Number of times the route have been disabled."
    ::= { ssmRouteMonEntry 1030 }

ssmRouteMonStatus OBJECT-TYPE
    SYNTAX      DisplayString
    MAX-ACCESS  read-only
    STATUS      current
    DESCRIPTION 
        "Current route status (enabled/disabled)."
    ::= { ssmRouteMonEntry 1040 }

ssmRouteMonFailReason OBJECT-TYPE
    SYNTAX      DisplayString
    MAX-ACCESS  read-only
    STATUS      current
    DESCRIPTION 
        "Reason for the route being disabled."
    ::= { ssmRouteMonEntry 1050 }

ssmRouteMonName OBJECT-TYPE
    SYNTAX      DisplayString
    MAX-ACCESS  read-only
    STATUS      current
    DESCRIPTION 
        "Route monitor instance description."
    ::= { ssmRouteMonEntry 2 }

ssmRoutingTableTable OBJECT-TYPE
    SYNTAX      SEQUENCE OF SsmRoutingTableEntry
    MAX-ACCESS  not-accessible
    STATUS      current
    DESCRIPTION 
        "Routing table statistics."
    ::= { ssmRouting 3050 }

ssmRoutingTableEntry OBJECT-TYPE
    SYNTAX      SsmRoutingTableEntry
    MAX-ACCESS  not-accessible
    STATUS      current
    DESCRIPTION 
        "Routing table entry statistics."
    INDEX       { ssmRoutingTableIndex }
    ::= { ssmRoutingTableTable 1 }

SsmRoutingTableEntry ::= SEQUENCE {
    ssmRoutingTableIndex           Integer32,
    ssmRoutingTableName            DisplayString,
    ssmRoutingTableDynRoutesCreated    Counter32,
    ssmRoutingTableDynRoutesCurrent    Gauge32,
    ssmRoutingTableDynRoutesMax    Unsigned32,
    ssmRoutingTableStaticRoutes    Gauge32
}

ssmRoutingTableIndex OBJECT-TYPE
    SYNTAX      Integer32 (1..2147483647)
    MAX-ACCESS  not-accessible
    STATUS      current
    DESCRIPTION 
        "Routing table statistics row index."
    ::= { ssmRoutingTableEntry 1 }

ssmRoutingTableDynRoutesCreated OBJECT-TYPE
    SYNTAX      Counter32
    MAX-ACCESS  read-only
    STATUS      current
    DESCRIPTION 
        "Number of dynamic route additions in routing table."
    ::= { ssmRoutingTableEntry 1015 }

ssmRoutingTableDynRoutesCurrent OBJECT-TYPE
    SYNTAX      Gauge32
    MAX-ACCESS  read-only
    STATUS      current
    DESCRIPTION 
        "Current number of dynamic routes in routing table."
    ::= { ssmRoutingTableEntry 1020 }

ssmRoutingTableDynRoutesMax OBJECT-TYPE
    SYNTAX      Unsigned32
    MAX-ACCESS  read-only
    STATUS      current
    DESCRIPTION 
        "Maximum number of dynamic routes in routing table."
    ::= { ssmRoutingTableEntry 1025 }

ssmRoutingTableStaticRoutes OBJECT-TYPE
    SYNTAX      Gauge32
    MAX-ACCESS  read-only
    STATUS      current
    DESCRIPTION 
        "Current number of static routes in routing table."
    ::= { ssmRoutingTableEntry 1030 }

ssmRoutingTableName OBJECT-TYPE
    SYNTAX      DisplayString
    MAX-ACCESS  read-only
    STATUS      current
    DESCRIPTION 
        "Name of routing table."
    ::= { ssmRoutingTableEntry 2 }

ssmRules OBJECT IDENTIFIER
    ::= { clavisterSystemStats 2070 }

ssmIPRuleStatsTable OBJECT-TYPE
    SYNTAX      SEQUENCE OF SsmIPRuleStatsEntry
    MAX-ACCESS  not-accessible
    STATUS      current
    DESCRIPTION 
        "IP rule statistics table."
    ::= { ssmRules 2010 }

ssmIPRuleStatsEntry OBJECT-TYPE
    SYNTAX      SsmIPRuleStatsEntry
    MAX-ACCESS  not-accessible
    STATUS      current
    DESCRIPTION 
        "IP rule statistics entry."
    INDEX       { ssmIPRuleSetIndex,ssmIPRuleIndex }
    ::= { ssmIPRuleStatsTable 1 }

SsmIPRuleStatsEntry ::= SEQUENCE {
    ssmIPRuleIndex      Integer32,
    ssmIPRuleName       DisplayString,
    ssmIPRuleMatched    Counter32,
    ssmIPRuleLastReset    TimeTicks
}

ssmIPRuleIndex OBJECT-TYPE
    SYNTAX      Integer32 (1..2147483647)
    MAX-ACCESS  not-accessible
    STATUS      current
    DESCRIPTION 
        "IP rule index."
    ::= { ssmIPRuleStatsEntry 1 }

ssmIPRuleMatched OBJECT-TYPE
    SYNTAX      Counter32
    MAX-ACCESS  read-only
    STATUS      current
    DESCRIPTION 
        "Number of times this IP rule matched incoming traffic (flow
         setup requests)."
    ::= { ssmIPRuleStatsEntry 1010 }

ssmIPRuleLastReset OBJECT-TYPE
    SYNTAX      TimeTicks
    MAX-ACCESS  read-only
    STATUS      current
    DESCRIPTION 
        "Time (in hundredths of a second, counting since the system was
         last booted) when the rule was last modified."
    ::= { ssmIPRuleStatsEntry 1040 }

ssmIPRuleName OBJECT-TYPE
    SYNTAX      DisplayString
    MAX-ACCESS  read-only
    STATUS      current
    DESCRIPTION 
        "Name of the IP rule."
    ::= { ssmIPRuleStatsEntry 2 }

ssmIPRuleSetTable OBJECT-TYPE
    SYNTAX      SEQUENCE OF SsmIPRuleSetEntry
    MAX-ACCESS  not-accessible
    STATUS      current
    DESCRIPTION 
        "IP RuleSet statistics table."
    ::= { ssmRules 2020 }

ssmIPRuleSetEntry OBJECT-TYPE
    SYNTAX      SsmIPRuleSetEntry
    MAX-ACCESS  not-accessible
    STATUS      current
    DESCRIPTION 
        "IP RuleSet statistics entry."
    INDEX       { ssmIPRuleSetIndex }
    ::= { ssmIPRuleSetTable 1 }

SsmIPRuleSetEntry ::= SEQUENCE {
    ssmIPRuleSetIndex    Integer32,
    ssmIPRuleSetName    DisplayString
}

ssmIPRuleSetIndex OBJECT-TYPE
    SYNTAX      Integer32 (1..2147483647)
    MAX-ACCESS  not-accessible
    STATUS      current
    DESCRIPTION 
        "Index of IPRuleSet."
    ::= { ssmIPRuleSetEntry 1 }

ssmIPRuleSetName OBJECT-TYPE
    SYNTAX      DisplayString
    MAX-ACCESS  read-only
    STATUS      current
    DESCRIPTION 
        "Name of the IPRuleSet."
    ::= { ssmIPRuleSetEntry 2 }

ssmThresholdRuleStatsTable OBJECT-TYPE
    SYNTAX      SEQUENCE OF SsmThresholdRuleStatsEntry
    MAX-ACCESS  not-accessible
    STATUS      current
    DESCRIPTION 
        "Threshold rule statistics table."
    ::= { ssmRules 2030 }

ssmThresholdRuleStatsEntry OBJECT-TYPE
    SYNTAX      SsmThresholdRuleStatsEntry
    MAX-ACCESS  not-accessible
    STATUS      current
    DESCRIPTION 
        "Threshold rule statistics entry."
    INDEX       { ssmThresholdRuleSetIndex,ssmThresholdRuleIndex }
    ::= { ssmThresholdRuleStatsTable 1 }

SsmThresholdRuleStatsEntry ::= SEQUENCE {
    ssmThresholdRuleIndex            Integer32,
    ssmThresholdRuleName             DisplayString,
    ssmThresholdRuleMatched          Counter32,
    ssmThresholdRuleLastReset        TimeTicks,
    ssmThresholdRuleTotalTrigged     Counter32,
    ssmThresholdRuleTotalDrops       Counter32
}

ssmThresholdRuleIndex OBJECT-TYPE
    SYNTAX      Integer32 (1..2147483647)
    MAX-ACCESS  not-accessible
    STATUS      current
    DESCRIPTION 
        "Threshold rule index."
    ::= { ssmThresholdRuleStatsEntry 1 }

ssmThresholdRuleMatched OBJECT-TYPE
    SYNTAX      Counter32
    MAX-ACCESS  read-only
    STATUS      current
    DESCRIPTION 
        "Number of times this Threshold rule matched incoming traffic
         (flow setup requests)."
    ::= { ssmThresholdRuleStatsEntry 1010 }

ssmThresholdRuleLastReset OBJECT-TYPE
    SYNTAX      TimeTicks
    MAX-ACCESS  read-only
    STATUS      current
    DESCRIPTION 
        "Time (in hundredths of a second, counting since the system was
         last booted) when the rule was last modified."
    ::= { ssmThresholdRuleStatsEntry 1040 }

ssmThresholdRuleTotalTrigged OBJECT-TYPE
    SYNTAX      Counter32
    MAX-ACCESS  read-only
    STATUS      current
    DESCRIPTION 
        "Number of times that some action in the given rule has triggered."
    ::= { ssmThresholdRuleStatsEntry 1110 }

ssmThresholdRuleTotalDrops OBJECT-TYPE
    SYNTAX      Counter32
    MAX-ACCESS  read-only
    STATUS      current
    DESCRIPTION 
        "Number of times that some action in the given rule has dropped a
         flow setup attempt."
    ::= { ssmThresholdRuleStatsEntry 1120 }

ssmThresholdRuleName OBJECT-TYPE
    SYNTAX      DisplayString
    MAX-ACCESS  read-only
    STATUS      current
    DESCRIPTION 
        "Name of the Threshold rule."
    ::= { ssmThresholdRuleStatsEntry 2 }

ssmThresholdRuleSetTable OBJECT-TYPE
    SYNTAX      SEQUENCE OF SsmThresholdRuleSetEntry
    MAX-ACCESS  not-accessible
    STATUS      current
    DESCRIPTION 
        "Threshold RuleSet statistics table."
    ::= { ssmRules 2040 }

ssmThresholdRuleSetEntry OBJECT-TYPE
    SYNTAX      SsmThresholdRuleSetEntry
    MAX-ACCESS  not-accessible
    STATUS      current
    DESCRIPTION 
        "Threshold RuleSet statistics entry."
    INDEX       { ssmThresholdRuleSetIndex }
    ::= { ssmThresholdRuleSetTable 1 }

SsmThresholdRuleSetEntry ::= SEQUENCE {
    ssmThresholdRuleSetIndex    Integer32,
    ssmThresholdRuleSetName    DisplayString
}

ssmThresholdRuleSetIndex OBJECT-TYPE
    SYNTAX      Integer32 (1..2147483647)
    MAX-ACCESS  not-accessible
    STATUS      current
    DESCRIPTION 
        "Index of ThresholdRuleSet."
    ::= { ssmThresholdRuleSetEntry 1 }

ssmThresholdRuleSetName OBJECT-TYPE
    SYNTAX      DisplayString
    MAX-ACCESS  read-only
    STATUS      current
    DESCRIPTION 
        "Name of the ThresholdRuleSet."
    ::= { ssmThresholdRuleSetEntry 2 }

ssmIPSRuleStatsTable OBJECT-TYPE
    SYNTAX      SEQUENCE OF SsmIPSRuleStatsEntry
    MAX-ACCESS  not-accessible
    STATUS      current
    DESCRIPTION 
        "IPS rule statistics table."
    ::= { ssmRules 2050 }

ssmIPSRuleStatsEntry OBJECT-TYPE
    SYNTAX      SsmIPSRuleStatsEntry
    MAX-ACCESS  not-accessible
    STATUS      current
    DESCRIPTION 
        "IPS rule statistics entry."
    INDEX       { ssmIPSRuleMatchIndex }
    ::= { ssmIPSRuleStatsTable 1 }

SsmIPSRuleStatsEntry ::= SEQUENCE {
    ssmIPSRuleMatchIndex    Integer32,
    ssmIPSRuleMatchName    DisplayString,
    ssmIPSRuleMatched     Counter32,
    ssmIPSRuleLastReset    TimeTicks
}

ssmIPSRuleMatchIndex OBJECT-TYPE
    SYNTAX      Integer32 (1..2147483647)
    MAX-ACCESS  not-accessible
    STATUS      current
    DESCRIPTION 
        "IPS rule index."
    ::= { ssmIPSRuleStatsEntry 1 }

ssmIPSRuleMatched OBJECT-TYPE
    SYNTAX      Counter32
    MAX-ACCESS  read-only
    STATUS      current
    DESCRIPTION 
        "Number of times this IPS rule matched incoming traffic (flow
         setup requests)."
    ::= { ssmIPSRuleStatsEntry 1010 }

ssmIPSRuleLastReset OBJECT-TYPE
    SYNTAX      TimeTicks
    MAX-ACCESS  read-only
    STATUS      current
    DESCRIPTION 
        "Time (in hundredths of a second, counting since the system was
         last booted) when the rule was last modified."
    ::= { ssmIPSRuleStatsEntry 1040 }

ssmIPSRuleMatchName OBJECT-TYPE
    SYNTAX      DisplayString
    MAX-ACCESS  read-only
    STATUS      current
    DESCRIPTION 
        "Name of the IPS rule."
    ::= { ssmIPSRuleStatsEntry 2 }

ssmServices OBJECT IDENTIFIER
    ::= { clavisterSystemStats 2080 }

ssmARP OBJECT IDENTIFIER
    ::= { ssmServices 2 }

ssmProxiedReplies OBJECT-TYPE
    SYNTAX      Counter32
    MAX-ACCESS  read-only
    STATUS      current
    DESCRIPTION 
        "Number of ARP requests that have been handled using ProxyARP."
    ::= { ssmARP 1005 }

ssmDHCPClient OBJECT IDENTIFIER
    ::= { ssmServices 2010 }

ssmDHCPClientTable OBJECT-TYPE
    SYNTAX      SEQUENCE OF SsmDHCPClientEntry
    MAX-ACCESS  not-accessible
    STATUS      current
    DESCRIPTION 
        "DHCP Client Table."
    ::= { ssmDHCPClient 3001 }

ssmDHCPClientEntry OBJECT-TYPE
    SYNTAX      SsmDHCPClientEntry
    MAX-ACCESS  not-accessible
    STATUS      current
    DESCRIPTION 
        "DHCP Client interface entry."
    INDEX       { ssmDHCPClientIfaceIndex }
    ::= { ssmDHCPClientTable 1 }

SsmDHCPClientEntry ::= SEQUENCE {
    ssmDHCPClientIfaceIndex         Integer32,
    ssmDHCPClientIfaceName          DisplayString,
    ssmDHCPClientLeaseAquired       Unsigned32,
    ssmDHCPClientState              DisplayString,
    ssmDHCPClientLeaseTimeTotal     Unsigned32,
    ssmDHCPClientLeaseTimeUsed      Unsigned32,
    ssmDHCPClientLeaseTTL           Unsigned32,
    ssmDHCPClientAddressAge         Unsigned32,
    ssmDHCPClientDiscoveriesSent    Unsigned32,
    ssmDHCPClientRequestsSent       Unsigned32,
    ssmDHCPClientReleasesSent       Unsigned32,
    ssmDHCPClientDeclinesSent       Unsigned32,
    ssmDHCPClientOffersReceived     Unsigned32,
    ssmDHCPClientAcksReceived       Unsigned32,
    ssmDHCPClientNacksReceived      Unsigned32,
    ssmDHCPClientDiscoveriesResent    Unsigned32,
    ssmDHCPClientRequestsResent     Unsigned32
}

ssmDHCPClientIfaceIndex OBJECT-TYPE
    SYNTAX      Integer32 (1..2147483647)
    MAX-ACCESS  not-accessible
    STATUS      current
    DESCRIPTION 
        "Interface row index."
    ::= { ssmDHCPClientEntry 1 }

ssmDHCPClientLeaseAquired OBJECT-TYPE
    SYNTAX      Unsigned32
    MAX-ACCESS  read-only
    STATUS      current
    DESCRIPTION 
        "Client has an active lease (0=no lease, 1=valid lease)."
    ::= { ssmDHCPClientEntry 1005 }

ssmDHCPClientState OBJECT-TYPE
    SYNTAX      DisplayString
    MAX-ACCESS  read-only
    STATUS      current
    DESCRIPTION 
        "Current DHCP state."
    ::= { ssmDHCPClientEntry 1010 }

ssmDHCPClientLeaseTimeTotal OBJECT-TYPE
    SYNTAX      Unsigned32
    MAX-ACCESS  read-only
    STATUS      current
    DESCRIPTION 
        "Total lease time from DHCP server."
    ::= { ssmDHCPClientEntry 1015 }

ssmDHCPClientLeaseTimeUsed OBJECT-TYPE
    SYNTAX      Unsigned32
    MAX-ACCESS  read-only
    STATUS      current
    DESCRIPTION 
        "How long time this lease has been used."
    ::= { ssmDHCPClientEntry 1020 }

ssmDHCPClientLeaseTTL OBJECT-TYPE
    SYNTAX      Unsigned32
    MAX-ACCESS  read-only
    STATUS      current
    DESCRIPTION 
        "Time until lease expires."
    ::= { ssmDHCPClientEntry 1025 }

ssmDHCPClientAddressAge OBJECT-TYPE
    SYNTAX      Unsigned32
    MAX-ACCESS  read-only
    STATUS      current
    DESCRIPTION 
        "How long this interface has had this address."
    ::= { ssmDHCPClientEntry 1030 }

ssmDHCPClientDiscoveriesSent OBJECT-TYPE
    SYNTAX      Unsigned32
    MAX-ACCESS  read-only
    STATUS      current
    DESCRIPTION 
        "Number of discover messages sent."
    ::= { ssmDHCPClientEntry 1035 }

ssmDHCPClientRequestsSent OBJECT-TYPE
    SYNTAX      Unsigned32
    MAX-ACCESS  read-only
    STATUS      current
    DESCRIPTION 
        "Number of request messages sent."
    ::= { ssmDHCPClientEntry 1040 }

ssmDHCPClientReleasesSent OBJECT-TYPE
    SYNTAX      Unsigned32
    MAX-ACCESS  read-only
    STATUS      current
    DESCRIPTION 
        "Number of release messages sent."
    ::= { ssmDHCPClientEntry 1045 }

ssmDHCPClientDeclinesSent OBJECT-TYPE
    SYNTAX      Unsigned32
    MAX-ACCESS  read-only
    STATUS      current
    DESCRIPTION 
        "Number of decline messages sent."
    ::= { ssmDHCPClientEntry 1050 }

ssmDHCPClientOffersReceived OBJECT-TYPE
    SYNTAX      Unsigned32
    MAX-ACCESS  read-only
    STATUS      current
    DESCRIPTION 
        "Number of offer messages received."
    ::= { ssmDHCPClientEntry 1055 }

ssmDHCPClientAcksReceived OBJECT-TYPE
    SYNTAX      Unsigned32
    MAX-ACCESS  read-only
    STATUS      current
    DESCRIPTION 
        "Number of ack messages received."
    ::= { ssmDHCPClientEntry 1060 }

ssmDHCPClientNacksReceived OBJECT-TYPE
    SYNTAX      Unsigned32
    MAX-ACCESS  read-only
    STATUS      current
    DESCRIPTION 
        "Number of nack messages received."
    ::= { ssmDHCPClientEntry 1065 }

ssmDHCPClientDiscoveriesResent OBJECT-TYPE
    SYNTAX      Unsigned32
    MAX-ACCESS  read-only
    STATUS      current
    DESCRIPTION 
        "Number of discover messages re-sent."
    ::= { ssmDHCPClientEntry 1070 }

ssmDHCPClientRequestsResent OBJECT-TYPE
    SYNTAX      Unsigned32
    MAX-ACCESS  read-only
    STATUS      current
    DESCRIPTION 
        "Number of request messages re-sent."
    ::= { ssmDHCPClientEntry 1075 }

ssmDHCPClientIfaceName OBJECT-TYPE
    SYNTAX      DisplayString
    MAX-ACCESS  read-only
    STATUS      current
    DESCRIPTION 
        "DHCP Client interface name."
    ::= { ssmDHCPClientEntry 2 }

ssmNATPool OBJECT IDENTIFIER
    ::= { ssmServices 2080 }

ssmNATPoolTable OBJECT-TYPE
    SYNTAX      SEQUENCE OF SsmNATPoolEntry
    MAX-ACCESS  not-accessible
    STATUS      current
    DESCRIPTION 
        "NATPool Table."
    ::= { ssmNATPool 3010 }

ssmNATPoolEntry OBJECT-TYPE
    SYNTAX      SsmNATPoolEntry
    MAX-ACCESS  not-accessible
    STATUS      current
    DESCRIPTION 
        "NATPool table entry."
    INDEX       { ssmNATPoolIndex }
    ::= { ssmNATPoolTable 1 }

SsmNATPoolEntry ::= SEQUENCE {
    ssmNATPoolIndex                           Integer32,
    ssmNATPoolName                            DisplayString,
    ssmNATPoolDetBlocksInUseTCP               Unsigned32,
    ssmNATPoolDetBlocksInUseSCTP              Unsigned32,
    ssmNATPoolDetBlocksInUseUDP               Unsigned32,
    ssmNATPoolDetBlocksFreeTCP                Unsigned32,
    ssmNATPoolDetBlocksFreeSCTP               Unsigned32,
    ssmNATPoolDetBlocksFreeUDP                Unsigned32,
    ssmNATPoolDynBlocksInUseTCP               Unsigned32,
    ssmNATPoolDynBlocksInUseSCTP              Unsigned32,
    ssmNATPoolDynBlocksInUseUDP               Unsigned32,
    ssmNATPoolDynBlocksFreeTCP                Unsigned32,
    ssmNATPoolDynBlocksFreeSCTP               Unsigned32,
    ssmNATPoolDynBlocksFreeUDP                Unsigned32,
    ssmNATPoolDetBlockDepletedCtrTCP          Counter32,
    ssmNATPoolDetBlockDepletdCtrSCTP          Counter32,
    ssmNATPoolDetBlockDepletedCtrUDP          Counter32,
    ssmNATPoolPortsDepletedCtrTCP             Counter32,
    ssmNATPoolPortsDepletedCtrSCTP            Counter32,
    ssmNATPoolPortsDepletedCtrUDP             Counter32,
    ssmNATPoolDynBlockAllocLimitCtr           Counter32,
    ssmNATPoolAvgFlowsPerDetBlockTCP          Unsigned32,
    ssmNATPoolAvgFlowsPerDetBlckSCTP          Unsigned32,
    ssmNATPoolAvgFlowsPerDetBlockUDP          Unsigned32,
    ssmNATPoolAvgFlowsPerDynBlockTCP          Unsigned32,
    ssmNATPoolAvgFlowsPerDynBlckSCTP          Unsigned32,
    ssmNATPoolAvgFlowsPerDynBlockUDP          Unsigned32,
    ssmNATPoolMaxDetFlowsTCP                  Unsigned32,
    ssmNATPoolMaxDetFlowsSCTP                 Unsigned32,
    ssmNATPoolMaxDetFlowsUDP                  Unsigned32,
    ssmNATPoolMaxDynFlowsTCP                  Unsigned32,
    ssmNATPoolMaxDynFlowsSCTP                 Unsigned32,
    ssmNATPoolMaxDynFlowsUDP                  Unsigned32,
    ssmNATPoolTotalStates                     Unsigned32,
    ssmNATPoolActiveStates                    Unsigned32,
    ssmNATPoolLingeringStates                 Unsigned32,
    ssmNATPoolActiveStatesChanged             Counter64,
    ssmNATPoolLingerStatesChanged             Counter64,
    ssmNATPoolActiveStatesReplaced            Counter64,
    ssmNATPoolLingerStatesReplaced            Counter64,
    ssmNATPoolMaxStatesAllowed                Unsigned32,
    ssmNATPoolMaxStatesUsed                   Unsigned32
}

ssmNATPoolIndex OBJECT-TYPE
    SYNTAX      Integer32 (1..2147483647)
    MAX-ACCESS  not-accessible
    STATUS      current
    DESCRIPTION 
        "NATPool row index."
    ::= { ssmNATPoolEntry 1 }

ssmNATPoolDetBlocksInUseTCP OBJECT-TYPE
    SYNTAX      Unsigned32
    MAX-ACCESS  read-only
    STATUS      current
    DESCRIPTION 
        "Number of active TCP clients in this rule."
    ::= { ssmNATPoolEntry 1005 }

ssmNATPoolDetBlocksInUseSCTP OBJECT-TYPE
    SYNTAX      Unsigned32
    MAX-ACCESS  read-only
    STATUS      current
    DESCRIPTION 
        "Number of active SCTP clients in this rule."
    ::= { ssmNATPoolEntry 1007 }

ssmNATPoolDetBlocksInUseUDP OBJECT-TYPE
    SYNTAX      Unsigned32
    MAX-ACCESS  read-only
    STATUS      current
    DESCRIPTION 
        "Number of active UDP clients in this rule."
    ::= { ssmNATPoolEntry 1010 }

ssmNATPoolDetBlocksFreeTCP OBJECT-TYPE
    SYNTAX      Unsigned32
    MAX-ACCESS  read-only
    STATUS      current
    DESCRIPTION 
        "Number of TCP deterministic blocks free."
    ::= { ssmNATPoolEntry 1015 }

ssmNATPoolDetBlocksFreeSCTP OBJECT-TYPE
    SYNTAX      Unsigned32
    MAX-ACCESS  read-only
    STATUS      current
    DESCRIPTION 
        "Number of SCTP deterministic blocks free."
    ::= { ssmNATPoolEntry 1017 }

ssmNATPoolDetBlocksFreeUDP OBJECT-TYPE
    SYNTAX      Unsigned32
    MAX-ACCESS  read-only
    STATUS      current
    DESCRIPTION 
        "Number of UDP deterministic blocks free."
    ::= { ssmNATPoolEntry 1020 }

ssmNATPoolDynBlocksInUseTCP OBJECT-TYPE
    SYNTAX      Unsigned32
    MAX-ACCESS  read-only
    STATUS      current
    DESCRIPTION 
        "Number of TCP dynamic blocks in use."
    ::= { ssmNATPoolEntry 1025 }

ssmNATPoolDynBlocksInUseSCTP OBJECT-TYPE
    SYNTAX      Unsigned32
    MAX-ACCESS  read-only
    STATUS      current
    DESCRIPTION 
        "Number of SCTP dynamic blocks in use."
    ::= { ssmNATPoolEntry 1027 }

ssmNATPoolDynBlocksInUseUDP OBJECT-TYPE
    SYNTAX      Unsigned32
    MAX-ACCESS  read-only
    STATUS      current
    DESCRIPTION 
        "Number of UDP dynamic blocks in use."
    ::= { ssmNATPoolEntry 1030 }

ssmNATPoolDynBlocksFreeTCP OBJECT-TYPE
    SYNTAX      Unsigned32
    MAX-ACCESS  read-only
    STATUS      current
    DESCRIPTION 
        "Number of TCP dynamic blocks free."
    ::= { ssmNATPoolEntry 1035 }

ssmNATPoolDynBlocksFreeSCTP OBJECT-TYPE
    SYNTAX      Unsigned32
    MAX-ACCESS  read-only
    STATUS      current
    DESCRIPTION 
        "Number of SCTP dynamic blocks free."
    ::= { ssmNATPoolEntry 1037 }

ssmNATPoolDynBlocksFreeUDP OBJECT-TYPE
    SYNTAX      Unsigned32
    MAX-ACCESS  read-only
    STATUS      current
    DESCRIPTION 
        "Number of UDP dynamic blocks free."
    ::= { ssmNATPoolEntry 1040 }

ssmNATPoolDetBlockDepletedCtrTCP OBJECT-TYPE
    SYNTAX      Counter32
    MAX-ACCESS  read-only
    STATUS      current
    DESCRIPTION 
        "Number of times deterministic TCP block have been depleted."
    ::= { ssmNATPoolEntry 1065 }

ssmNATPoolDetBlockDepletdCtrSCTP OBJECT-TYPE
    SYNTAX      Counter32
    MAX-ACCESS  read-only
    STATUS      current
    DESCRIPTION 
        "Number of times deterministic SCTP block have been depleted."
    ::= { ssmNATPoolEntry 1067 }

ssmNATPoolDetBlockDepletedCtrUDP OBJECT-TYPE
    SYNTAX      Counter32
    MAX-ACCESS  read-only
    STATUS      current
    DESCRIPTION 
        "Number of times deterministic UDP block have been depleted."
    ::= { ssmNATPoolEntry 1070 }

ssmNATPoolPortsDepletedCtrTCP OBJECT-TYPE
    SYNTAX      Counter32
    MAX-ACCESS  read-only
    STATUS      current
    DESCRIPTION 
        "Number of times port manager has run out of TCP ports."
    ::= { ssmNATPoolEntry 1075 }

ssmNATPoolPortsDepletedCtrSCTP OBJECT-TYPE
    SYNTAX      Counter32
    MAX-ACCESS  read-only
    STATUS      current
    DESCRIPTION 
        "Number of times port manager has run out of SCTP ports."
    ::= { ssmNATPoolEntry 1077 }

ssmNATPoolPortsDepletedCtrUDP OBJECT-TYPE
    SYNTAX      Counter32
    MAX-ACCESS  read-only
    STATUS      current
    DESCRIPTION 
        "Number of times port manager has run out of UDP ports."
    ::= { ssmNATPoolEntry 1080 }

ssmNATPoolDynBlockAllocLimitCtr OBJECT-TYPE
    SYNTAX      Counter32
    MAX-ACCESS  read-only
    STATUS      current
    DESCRIPTION 
        "Number of times dynamic block limit has been hit."
    ::= { ssmNATPoolEntry 1085 }

ssmNATPoolAvgFlowsPerDetBlockTCP OBJECT-TYPE
    SYNTAX      Unsigned32
    MAX-ACCESS  read-only
    STATUS      current
    DESCRIPTION 
        "Average TCP flow count per deterministic block."
    ::= { ssmNATPoolEntry 1090 }

ssmNATPoolAvgFlowsPerDetBlckSCTP OBJECT-TYPE
    SYNTAX      Unsigned32
    MAX-ACCESS  read-only
    STATUS      current
    DESCRIPTION 
        "Average SCTP flow count per deterministic block."
    ::= { ssmNATPoolEntry 1092 }

ssmNATPoolAvgFlowsPerDetBlockUDP OBJECT-TYPE
    SYNTAX      Unsigned32
    MAX-ACCESS  read-only
    STATUS      current
    DESCRIPTION 
        "Average UDP flow count per deterministic block."
    ::= { ssmNATPoolEntry 1095 }

ssmNATPoolAvgFlowsPerDynBlockTCP OBJECT-TYPE
    SYNTAX      Unsigned32
    MAX-ACCESS  read-only
    STATUS      current
    DESCRIPTION 
        "Average TCP flow count per dynamic block."
    ::= { ssmNATPoolEntry 1100 }

ssmNATPoolAvgFlowsPerDynBlckSCTP OBJECT-TYPE
    SYNTAX      Unsigned32
    MAX-ACCESS  read-only
    STATUS      current
    DESCRIPTION 
        "Average SCTP flow count per dynamic block."
    ::= { ssmNATPoolEntry 1102 }

ssmNATPoolAvgFlowsPerDynBlockUDP OBJECT-TYPE
    SYNTAX      Unsigned32
    MAX-ACCESS  read-only
    STATUS      current
    DESCRIPTION 
        "Average UDP flow count per dynamic block."
    ::= { ssmNATPoolEntry 1105 }

ssmNATPoolMaxDetFlowsTCP OBJECT-TYPE
    SYNTAX      Unsigned32
    MAX-ACCESS  read-only
    STATUS      current
    DESCRIPTION 
        "Maximum TCP flow count registered on a deterministic block."
    ::= { ssmNATPoolEntry 1110 }

ssmNATPoolMaxDetFlowsSCTP OBJECT-TYPE
    SYNTAX      Unsigned32
    MAX-ACCESS  read-only
    STATUS      current
    DESCRIPTION 
        "Maximum SCTP flow count registered on a deterministic block."
    ::= { ssmNATPoolEntry 1112 }

ssmNATPoolMaxDetFlowsUDP OBJECT-TYPE
    SYNTAX      Unsigned32
    MAX-ACCESS  read-only
    STATUS      current
    DESCRIPTION 
        "Maximum UDP flow count registered on a deterministic block."
    ::= { ssmNATPoolEntry 1115 }

ssmNATPoolMaxDynFlowsTCP OBJECT-TYPE
    SYNTAX      Unsigned32
    MAX-ACCESS  read-only
    STATUS      current
    DESCRIPTION 
        "Maximum TCP flow count registered on a dynamic block."
    ::= { ssmNATPoolEntry 1120 }

ssmNATPoolMaxDynFlowsSCTP OBJECT-TYPE
    SYNTAX      Unsigned32
    MAX-ACCESS  read-only
    STATUS      current
    DESCRIPTION 
        "Maximum SCTP flow count registered on a dynamic block."
    ::= { ssmNATPoolEntry 1122 }

ssmNATPoolMaxDynFlowsUDP OBJECT-TYPE
    SYNTAX      Unsigned32
    MAX-ACCESS  read-only
    STATUS      current
    DESCRIPTION 
        "Maximum UDP flow count registered on a dynamic block."
    ::= { ssmNATPoolEntry 1125 }

ssmNATPoolTotalStates OBJECT-TYPE
    SYNTAX      Unsigned32
    MAX-ACCESS  read-only
    STATUS      current
    DESCRIPTION 
        "Number of states in a stateful NAT pool."
    ::= { ssmNATPoolEntry 1200 }

ssmNATPoolActiveStates OBJECT-TYPE
    SYNTAX      Unsigned32
    MAX-ACCESS  read-only
    STATUS      current
    DESCRIPTION 
        "Number of active states in a stateful NAT pool."
    ::= { ssmNATPoolEntry 1205 }

ssmNATPoolLingeringStates OBJECT-TYPE
    SYNTAX      Unsigned32
    MAX-ACCESS  read-only
    STATUS      current
    DESCRIPTION 
        "Number of lingering states in a stateful NAT pool."
    ::= { ssmNATPoolEntry 1210 }

ssmNATPoolActiveStatesChanged OBJECT-TYPE
    SYNTAX      Counter64
    MAX-ACCESS  read-only
    STATUS      current
    DESCRIPTION 
        "Number of times an active state (a state with active flows) has
         been changed to point to a different external IP in a stateful
         NAT pool."
    ::= { ssmNATPoolEntry 1215 }

ssmNATPoolLingerStatesChanged OBJECT-TYPE
    SYNTAX      Counter64
    MAX-ACCESS  read-only
    STATUS      current
    DESCRIPTION 
        "Number of times a lingering state (a state currently without any
         active flows) has been changed to point to a different external
         IP in a stateful NAT pool."
    ::= { ssmNATPoolEntry 1220 }

ssmNATPoolActiveStatesReplaced OBJECT-TYPE
    SYNTAX      Counter64
    MAX-ACCESS  read-only
    STATUS      current
    DESCRIPTION 
        "Number of times an active state (a state with active flows) has
         been replaced to make room for a new state for a different
         internal IP in a stateful NAT pool."
    ::= { ssmNATPoolEntry 1225 }

ssmNATPoolLingerStatesReplaced OBJECT-TYPE
    SYNTAX      Counter64
    MAX-ACCESS  read-only
    STATUS      current
    DESCRIPTION 
        "Number of times a lingering state (a state currently without any
         active flows) has been replaced to make room for a new state for
         a different internal IP in a stateful NAT pool."
    ::= { ssmNATPoolEntry 1230 }

ssmNATPoolMaxStatesAllowed OBJECT-TYPE
    SYNTAX      Unsigned32
    MAX-ACCESS  read-only
    STATUS      current
    DESCRIPTION 
        "Maximum number of states allowed in a stateful NAT pool."
    ::= { ssmNATPoolEntry 1235 }

ssmNATPoolMaxStatesUsed OBJECT-TYPE
    SYNTAX      Unsigned32
    MAX-ACCESS  read-only
    STATUS      current
    DESCRIPTION 
        "Maximum number of states used in a stateful NAT pool."
    ::= { ssmNATPoolEntry 1240 }

ssmNATPoolName OBJECT-TYPE
    SYNTAX      DisplayString
    MAX-ACCESS  read-only
    STATUS      current
    DESCRIPTION 
        "NATPool name."
    ::= { ssmNATPoolEntry 2 }

ssmTimeSync OBJECT IDENTIFIER
    ::= { ssmServices 2090 }

ssmNTPActiveServers OBJECT-TYPE
    SYNTAX      Unsigned32
    MAX-ACCESS  read-only
    STATUS      current
    DESCRIPTION 
        "Current number of active timeservers."
    ::= { ssmTimeSync 1005 }

ssmNTPClockSynchronizations OBJECT-TYPE
    SYNTAX      Counter32
    MAX-ACCESS  read-only
    STATUS      current
    DESCRIPTION 
        "Number of times the system clock has been synchronized."
    ::= { ssmTimeSync 1010 }

ssmNTPLastSynchronization OBJECT-TYPE
    SYNTAX      Unsigned32
    MAX-ACCESS  read-only
    STATUS      current
    DESCRIPTION 
        "Seconds since startup when clock synchronization was last done."
    ::= { ssmTimeSync 1015 }

ssmNTPLatestTimeDrift OBJECT-TYPE
    SYNTAX      Unsigned32
    MAX-ACCESS  read-only
    STATUS      current
    DESCRIPTION 
        "Size of latest adjusted time drift."
    ::= { ssmTimeSync 1020 }

ssmNTPMaximumTimeDrift OBJECT-TYPE
    SYNTAX      Unsigned32
    MAX-ACCESS  read-only
    STATUS      current
    DESCRIPTION 
        "Maximum time drift that has been adjusted."
    ::= { ssmTimeSync 1025 }

ssmNTPNextSynchronization OBJECT-TYPE
    SYNTAX      Integer32
    MAX-ACCESS  read-only
    STATUS      current
    DESCRIPTION 
        "Seconds until it is time for next clock synchronization."
    ::= { ssmTimeSync 1030 }

ssmNTPResponsesDiscarded OBJECT-TYPE
    SYNTAX      Counter32
    MAX-ACCESS  read-only
    STATUS      current
    DESCRIPTION 
        "Number of packets that has been discarded due to too big time
         drift."
    ::= { ssmTimeSync 1035 }

ssmNTPResponsesReceived OBJECT-TYPE
    SYNTAX      Counter32
    MAX-ACCESS  read-only
    STATUS      current
    DESCRIPTION 
        "Number of received packets."
    ::= { ssmTimeSync 1040 }

ssmNTPRequestsSent OBJECT-TYPE
    SYNTAX      Counter32
    MAX-ACCESS  read-only
    STATUS      current
    DESCRIPTION 
        "Number of sent packets."
    ::= { ssmTimeSync 1045 }

ssmNTPTimeBefore OBJECT-TYPE
    SYNTAX      DisplayString
    MAX-ACCESS  read-only
    STATUS      current
    DESCRIPTION 
        "Time just before last clock adjust."
    ::= { ssmTimeSync 1055 }

ssmNTPTimeAfter OBJECT-TYPE
    SYNTAX      DisplayString
    MAX-ACCESS  read-only
    STATUS      current
    DESCRIPTION 
        "Time after last clock adjust."
    ::= { ssmTimeSync 1060 }

ssmNTPLasySyncTime OBJECT-TYPE
    SYNTAX      DisplayString
    MAX-ACCESS  read-only
    STATUS      current
    DESCRIPTION 
        "Last synchronization time."
    ::= { ssmTimeSync 1065 }

ssmNTPLastError OBJECT-TYPE
    SYNTAX      DisplayString
    MAX-ACCESS  read-only
    STATUS      current
    DESCRIPTION 
        "NTP server last error."
    ::= { ssmTimeSync 1075 }

ssmNTPServerAddress OBJECT-TYPE
    SYNTAX      DisplayString
    MAX-ACCESS  read-only
    STATUS      current
    DESCRIPTION 
        "NTP server IP address."
    ::= { ssmTimeSync 1080 }

ssmNTPUpdateMethod OBJECT-TYPE
    SYNTAX      DisplayString
    MAX-ACCESS  read-only
    STATUS      current
    DESCRIPTION 
        "System clock update method."
    ::= { ssmTimeSync 1085 }

ssmDHCPServer OBJECT IDENTIFIER
    ::= { ssmServices 2100 }

ssmDHCPServerRejected OBJECT-TYPE
    SYNTAX      Unsigned32
    MAX-ACCESS  read-only
    STATUS      current
    DESCRIPTION 
        "DHCPServer Rejected."
    ::= { ssmDHCPServer 1005 }

ssmDHCPServerRuleTable OBJECT-TYPE
    SYNTAX      SEQUENCE OF SsmDHCPServerRuleEntry
    MAX-ACCESS  not-accessible
    STATUS      current
    DESCRIPTION 
        "DHCP Server Table."
    ::= { ssmDHCPServer 3001 }

ssmDHCPServerRuleEntry OBJECT-TYPE
    SYNTAX      SsmDHCPServerRuleEntry
    MAX-ACCESS  not-accessible
    STATUS      current
    DESCRIPTION 
        "DHCP Server rule entry."
    INDEX       { ssmDHCPServerRuleIndex }
    ::= { ssmDHCPServerRuleTable 1 }

SsmDHCPServerRuleEntry ::= SEQUENCE {
    ssmDHCPServerRuleIndex           Integer32,
    ssmDHCPServerRuleName            DisplayString,
    ssmDHCPServerRuleActiveClients    Unsigned32,
    ssmDHCPServerRuleActiveClientsP    Unsigned32,
    ssmDHCPServerRuleUsage           Unsigned32,
    ssmDHCPServerRuleUsageP          Unsigned32,
    ssmDHCPServerRuleIpPool          DisplayString,
    ssmDHCPServerRulePoolSize        Unsigned32,
    ssmDHCPServerRuleRejected        Unsigned32
}

ssmDHCPServerRuleIndex OBJECT-TYPE
    SYNTAX      Integer32 (1..2147483647)
    MAX-ACCESS  not-accessible
    STATUS      current
    DESCRIPTION 
        "Rule row index."
    ::= { ssmDHCPServerRuleEntry 1 }

ssmDHCPServerRuleActiveClients OBJECT-TYPE
    SYNTAX      Unsigned32
    MAX-ACCESS  read-only
    STATUS      current
    DESCRIPTION 
        "Number of active clients in this rule."
    ::= { ssmDHCPServerRuleEntry 1001 }

ssmDHCPServerRuleActiveClientsP OBJECT-TYPE
    SYNTAX      Unsigned32
    MAX-ACCESS  read-only
    STATUS      current
    DESCRIPTION 
        "Percentage of active clients in this rule."
    ::= { ssmDHCPServerRuleEntry 1011 }

ssmDHCPServerRuleUsage OBJECT-TYPE
    SYNTAX      Unsigned32
    MAX-ACCESS  read-only
    STATUS      current
    DESCRIPTION 
        "DHCP Server rule usage."
    ::= { ssmDHCPServerRuleEntry 1021 }

ssmDHCPServerRuleUsageP OBJECT-TYPE
    SYNTAX      Unsigned32
    MAX-ACCESS  read-only
    STATUS      current
    DESCRIPTION 
        "DHCPServ rule usage percent."
    ::= { ssmDHCPServerRuleEntry 1031 }

ssmDHCPServerRuleIpPool OBJECT-TYPE
    SYNTAX      DisplayString
    MAX-ACCESS  read-only
    STATUS      current
    DESCRIPTION 
        "List of IP addresses within the DHCP pool."
    ::= { ssmDHCPServerRuleEntry 1036 }

ssmDHCPServerRulePoolSize OBJECT-TYPE
    SYNTAX      Unsigned32
    MAX-ACCESS  read-only
    STATUS      current
    DESCRIPTION 
        "DHCPServ Rule Pool Size."
    ::= { ssmDHCPServerRuleEntry 1041 }

ssmDHCPServerRuleRejected OBJECT-TYPE
    SYNTAX      Unsigned32
    MAX-ACCESS  read-only
    STATUS      current
    DESCRIPTION 
        "DHCPServ Rule Rejected."
    ::= { ssmDHCPServerRuleEntry 1051 }

ssmDHCPServerRuleName OBJECT-TYPE
    SYNTAX      DisplayString
    MAX-ACCESS  read-only
    STATUS      current
    DESCRIPTION 
        "DHCP Server rule name."
    ::= { ssmDHCPServerRuleEntry 2 }

ssmNDP OBJECT IDENTIFIER
    ::= { ssmServices 2110 }

ssmNDPNeighbor OBJECT IDENTIFIER
    ::= { ssmNDP 2005 }

ssmNDPNeighborAdvsRecv OBJECT-TYPE
    SYNTAX      Counter64
    MAX-ACCESS  read-only
    STATUS      current
    DESCRIPTION 
        "Number of neighbor advertisements received."
    ::= { ssmNDPNeighbor 1005 }

ssmNDPNeighborAdvsSent OBJECT-TYPE
    SYNTAX      Counter64
    MAX-ACCESS  read-only
    STATUS      current
    DESCRIPTION 
        "Number of neighbor advertisements sent."
    ::= { ssmNDPNeighbor 1010 }

ssmNDPNeighborSolicsRecv OBJECT-TYPE
    SYNTAX      Counter64
    MAX-ACCESS  read-only
    STATUS      current
    DESCRIPTION 
        "Number of neighbor solicitations received."
    ::= { ssmNDPNeighbor 1015 }

ssmNDPNeighborSolicsSent OBJECT-TYPE
    SYNTAX      Counter64
    MAX-ACCESS  read-only
    STATUS      current
    DESCRIPTION 
        "Number of neighbor solicitations sent."
    ::= { ssmNDPNeighbor 1020 }

ssmNDPRouter OBJECT IDENTIFIER
    ::= { ssmNDP 2010 }

ssmNDPRouterAdvsRecv OBJECT-TYPE
    SYNTAX      Counter64
    MAX-ACCESS  read-only
    STATUS      current
    DESCRIPTION 
        "Number of router advertisements received."
    ::= { ssmNDPRouter 1005 }

ssmNDPRouterAdvsSent OBJECT-TYPE
    SYNTAX      Counter64
    MAX-ACCESS  read-only
    STATUS      current
    DESCRIPTION 
        "Number of router advertisements sent."
    ::= { ssmNDPRouter 1010 }

ssmNDPRouterSolicsRecv OBJECT-TYPE
    SYNTAX      Counter64
    MAX-ACCESS  read-only
    STATUS      current
    DESCRIPTION 
        "Number of router solicitations received."
    ::= { ssmNDPRouter 1015 }

ssmNDPRouterSolicsSent OBJECT-TYPE
    SYNTAX      Counter64
    MAX-ACCESS  read-only
    STATUS      current
    DESCRIPTION 
        "Number of router solicitations sent."
    ::= { ssmNDPRouter 1020 }

ssmNDPInterfaceTable OBJECT-TYPE
    SYNTAX      SEQUENCE OF SsmNDPInterfaceEntry
    MAX-ACCESS  not-accessible
    STATUS      current
    DESCRIPTION 
        "NDP interface table."
    ::= { ssmNDP 3001 }

ssmNDPInterfaceEntry OBJECT-TYPE
    SYNTAX      SsmNDPInterfaceEntry
    MAX-ACCESS  not-accessible
    STATUS      current
    DESCRIPTION 
        "."
    INDEX       { ssmNDPIfaceIndex }
    ::= { ssmNDPInterfaceTable 1 }

SsmNDPInterfaceEntry ::= SEQUENCE {
    ssmNDPIfaceIndex                  Integer32,
    ssmNDPIfaceName                   DisplayString,
    ssmNDPIfaceNeighborAdvsRecv       Counter64,
    ssmNDPIfaceNeighborAdvsSent       Counter64,
    ssmNDPIfaceNeighborSolicsRecv     Counter64,
    ssmNDPIfaceNeighborSolicsSent     Counter64,
    ssmNDPIfaceRouterAdvsRecv         Counter64,
    ssmNDPIfaceRouterAdvsSent         Counter64,
    ssmNDPIfaceRouterSolicsRecv       Counter64,
    ssmNDPIfaceRouterSolicsSent       Counter64,
    ssmNDPMinPrefixLifetime           Unsigned32,
    ssmNDPMinPrefixLifetimeRemaining    Unsigned32,
    ssmNDPNumPrefixes                 Unsigned32,
    ssmNDPNumPrefixesOnLink           Unsigned32
}

ssmNDPIfaceIndex OBJECT-TYPE
    SYNTAX      Integer32 (1..2147483647)
    MAX-ACCESS  not-accessible
    STATUS      current
    DESCRIPTION 
        "Interface row index."
    ::= { ssmNDPInterfaceEntry 1 }

ssmNDPIfaceNeighborAdvsRecv OBJECT-TYPE
    SYNTAX      Counter64
    MAX-ACCESS  read-only
    STATUS      current
    DESCRIPTION 
        "Number of neighbor advertisements received."
    ::= { ssmNDPInterfaceEntry 1005 }

ssmNDPIfaceNeighborAdvsSent OBJECT-TYPE
    SYNTAX      Counter64
    MAX-ACCESS  read-only
    STATUS      current
    DESCRIPTION 
        "Number of neighbor advertisements sent."
    ::= { ssmNDPInterfaceEntry 1010 }

ssmNDPIfaceNeighborSolicsRecv OBJECT-TYPE
    SYNTAX      Counter64
    MAX-ACCESS  read-only
    STATUS      current
    DESCRIPTION 
        "Number of neighbor solicitations received."
    ::= { ssmNDPInterfaceEntry 1015 }

ssmNDPIfaceNeighborSolicsSent OBJECT-TYPE
    SYNTAX      Counter64
    MAX-ACCESS  read-only
    STATUS      current
    DESCRIPTION 
        "Number of neighbor solicitations sent."
    ::= { ssmNDPInterfaceEntry 1020 }

ssmNDPIfaceRouterAdvsRecv OBJECT-TYPE
    SYNTAX      Counter64
    MAX-ACCESS  read-only
    STATUS      current
    DESCRIPTION 
        "Number of router advertisements received."
    ::= { ssmNDPInterfaceEntry 1025 }

ssmNDPIfaceRouterAdvsSent OBJECT-TYPE
    SYNTAX      Counter64
    MAX-ACCESS  read-only
    STATUS      current
    DESCRIPTION 
        "Number of router advertisements sent."
    ::= { ssmNDPInterfaceEntry 1030 }

ssmNDPIfaceRouterSolicsRecv OBJECT-TYPE
    SYNTAX      Counter64
    MAX-ACCESS  read-only
    STATUS      current
    DESCRIPTION 
        "Number of router solicitations received."
    ::= { ssmNDPInterfaceEntry 1035 }

ssmNDPIfaceRouterSolicsSent OBJECT-TYPE
    SYNTAX      Counter64
    MAX-ACCESS  read-only
    STATUS      current
    DESCRIPTION 
        "Number of router solicitations sent."
    ::= { ssmNDPInterfaceEntry 1040 }

ssmNDPMinPrefixLifetime OBJECT-TYPE
    SYNTAX      Unsigned32
    MAX-ACCESS  read-only
    STATUS      current
    DESCRIPTION 
        "Shortest prefix lifetime received from routers."
    ::= { ssmNDPInterfaceEntry 1045 }

ssmNDPMinPrefixLifetimeRemaining OBJECT-TYPE
    SYNTAX      Unsigned32
    MAX-ACCESS  read-only
    STATUS      current
    DESCRIPTION 
        "Shortest remaining prefix lifetime received from routers."
    ::= { ssmNDPInterfaceEntry 1050 }

ssmNDPNumPrefixes OBJECT-TYPE
    SYNTAX      Unsigned32
    MAX-ACCESS  read-only
    STATUS      current
    DESCRIPTION 
        "Number of prefixes received."
    ::= { ssmNDPInterfaceEntry 1055 }

ssmNDPNumPrefixesOnLink OBJECT-TYPE
    SYNTAX      Unsigned32
    MAX-ACCESS  read-only
    STATUS      current
    DESCRIPTION 
        "Number of on-link prefixes received."
    ::= { ssmNDPInterfaceEntry 1060 }

ssmNDPIfaceName OBJECT-TYPE
    SYNTAX      DisplayString
    MAX-ACCESS  read-only
    STATUS      current
    DESCRIPTION 
        "NDP interface name."
    ::= { ssmNDPInterfaceEntry 2 }

ssmThreatPrevention OBJECT IDENTIFIER
    ::= { clavisterSystemStats 2085 }

ssmIPS OBJECT IDENTIFIER
    ::= { ssmThreatPrevention 2010 }

ssmIPSVendorSignatures OBJECT-TYPE
    SYNTAX      Unsigned32
    MAX-ACCESS  read-only
    STATUS      current
    DESCRIPTION 
        "Total number of vendor signatures available to the system."
    ::= { ssmIPS 1010 }

ssmIPSCustomSignatures OBJECT-TYPE
    SYNTAX      Unsigned32
    MAX-ACCESS  read-only
    STATUS      current
    DESCRIPTION 
        "Total number of custom signatures available to the system."
    ::= { ssmIPS 1015 }

ssmIPSRejectedSignatures OBJECT-TYPE
    SYNTAX      Unsigned32
    MAX-ACCESS  read-only
    STATUS      current
    DESCRIPTION 
        "Total number of signatures rejected by the system due to bad
         formatting."
    ::= { ssmIPS 1020 }

ssmIPSSignatureDBVersion OBJECT-TYPE
    SYNTAX      DisplayString
    MAX-ACCESS  read-only
    STATUS      current
    DESCRIPTION 
        "Version number of vendor signature database."
    ::= { ssmIPS 1025 }

ssmIPSSignatureDBDate OBJECT-TYPE
    SYNTAX      DisplayString
    MAX-ACCESS  read-only
    STATUS      current
    DESCRIPTION 
        "Modified date of vendor signature database."
    ::= { ssmIPS 1030 }

ssmIPSThreatsDetected OBJECT-TYPE
    SYNTAX      Counter64
    MAX-ACCESS  read-only
    STATUS      current
    DESCRIPTION 
        "Total number of times the system has detected a potential threat."
    ::= { ssmIPS 1040 }

ssmIPSThreatsProtected OBJECT-TYPE
    SYNTAX      Counter64
    MAX-ACCESS  read-only
    STATUS      current
    DESCRIPTION 
        "Total number of times the system has protected against a
         potential threat."
    ::= { ssmIPS 1045 }

ssmIPSInvalidUTF8URL OBJECT-TYPE
    SYNTAX      Counter64
    MAX-ACCESS  read-only
    STATUS      current
    DESCRIPTION 
        "Total number of times HTTP Normalization has found an URL with
         invalid UTF8 format."
    ::= { ssmIPS 1050 }

ssmIPSInvalidHEXURL OBJECT-TYPE
    SYNTAX      Counter64
    MAX-ACCESS  read-only
    STATUS      current
    DESCRIPTION 
        "Total number of times HTTP Normalization has found an URL with
         invalid HEX encoding."
    ::= { ssmIPS 1055 }

ssmIPSDoubleEncodingURL OBJECT-TYPE
    SYNTAX      Counter64
    MAX-ACCESS  read-only
    STATUS      current
    DESCRIPTION 
        "Total number of times HTTP Normalization has found an URL with
         double encoding."
    ::= { ssmIPS 1060 }

ssmIPSInspectionErrors OBJECT-TYPE
    SYNTAX      Counter64
    MAX-ACCESS  read-only
    STATUS      current
    DESCRIPTION 
        "Total number of inspection errors seen in the inspection engine."
    ::= { ssmIPS 1070 }

ssmIPSFlowsScanned OBJECT-TYPE
    SYNTAX      Counter64
    MAX-ACCESS  read-only
    STATUS      current
    DESCRIPTION 
        "Total number of flows scanned by the IPS engine."
    ::= { ssmIPS 1075 }

ssmIPSScanLimitExceeded OBJECT-TYPE
    SYNTAX      Counter64
    MAX-ACCESS  read-only
    STATUS      current
    DESCRIPTION 
        "Total number of times the scan limit has been exceeded,
         resulting in terminated IPS scanning for a flow."
    ::= { ssmIPS 1080 }

ssmIPSRulesTable OBJECT-TYPE
    SYNTAX      SEQUENCE OF SsmIPSRulesEntry
    MAX-ACCESS  not-accessible
    STATUS      current
    DESCRIPTION 
        "IPS per rule statistics."
    ::= { ssmIPS 3010 }

ssmIPSRulesEntry OBJECT-TYPE
    SYNTAX      SsmIPSRulesEntry
    MAX-ACCESS  not-accessible
    STATUS      current
    DESCRIPTION 
        "The row in a table of IPS rule statistics."
    INDEX       { ssmIPSRuleIndex }
    ::= { ssmIPSRulesTable 1 }

SsmIPSRulesEntry ::= SEQUENCE {
    ssmIPSRuleIndex              Integer32,
    ssmIPSRuleName               DisplayString,
    ssmIPSRuleSignaturesSelected    Unsigned32,
    ssmIPSRuleSignaturesUsed     Unsigned32,
    ssmIPSRuleThreatsDetected    Counter64,
    ssmIPSRuleThreatsProtected    Counter64,
    ssmIPSRuleInvalidUTF8URL     Counter64,
    ssmIPSRuleInvalidHEXURL      Counter64,
    ssmIPSRuleDoubleEncodingURL    Counter64,
    ssmIPSRuleInspectionErrors    Counter64,
    ssmIPSRuleScanLimitExceeded    Counter64
}

ssmIPSRuleIndex OBJECT-TYPE
    SYNTAX      Integer32 (1..2147483647)
    MAX-ACCESS  not-accessible
    STATUS      current
    DESCRIPTION 
        "IPS Rule row index."
    ::= { ssmIPSRulesEntry 1 }

ssmIPSRuleSignaturesSelected OBJECT-TYPE
    SYNTAX      Unsigned32
    MAX-ACCESS  read-only
    STATUS      current
    DESCRIPTION 
        "Number of signatures selected by the rule."
    ::= { ssmIPSRulesEntry 1005 }

ssmIPSRuleSignaturesUsed OBJECT-TYPE
    SYNTAX      Unsigned32
    MAX-ACCESS  read-only
    STATUS      current
    DESCRIPTION 
        "Number of signatures actually used by the rule, not counting
         signatures rejected due to port, service etc."
    ::= { ssmIPSRulesEntry 1010 }

ssmIPSRuleThreatsDetected OBJECT-TYPE
    SYNTAX      Counter64
    MAX-ACCESS  read-only
    STATUS      current
    DESCRIPTION 
        "Number of times the system has detected a potential threat using
         this rule."
    ::= { ssmIPSRulesEntry 1040 }

ssmIPSRuleThreatsProtected OBJECT-TYPE
    SYNTAX      Counter64
    MAX-ACCESS  read-only
    STATUS      current
    DESCRIPTION 
        "Number of times the system has protected against a potential
         threat using this rule."
    ::= { ssmIPSRulesEntry 1045 }

ssmIPSRuleInvalidUTF8URL OBJECT-TYPE
    SYNTAX      Counter64
    MAX-ACCESS  read-only
    STATUS      current
    DESCRIPTION 
        "Number of times HTTP Normalization has found an URL with invalid
         UTF8 format using this rule."
    ::= { ssmIPSRulesEntry 1050 }

ssmIPSRuleInvalidHEXURL OBJECT-TYPE
    SYNTAX      Counter64
    MAX-ACCESS  read-only
    STATUS      current
    DESCRIPTION 
        "Number of times HTTP Normalization has found an URL with invalid
         HEX encoding using this rule."
    ::= { ssmIPSRulesEntry 1055 }

ssmIPSRuleDoubleEncodingURL OBJECT-TYPE
    SYNTAX      Counter64
    MAX-ACCESS  read-only
    STATUS      current
    DESCRIPTION 
        "Number of times HTTP Normalization has found an URL with double
         encoding using this rule."
    ::= { ssmIPSRulesEntry 1060 }

ssmIPSRuleInspectionErrors OBJECT-TYPE
    SYNTAX      Counter64
    MAX-ACCESS  read-only
    STATUS      current
    DESCRIPTION 
        "Number of inspection errors seen in the inspection engine using
         this rule."
    ::= { ssmIPSRulesEntry 1070 }

ssmIPSRuleScanLimitExceeded OBJECT-TYPE
    SYNTAX      Counter64
    MAX-ACCESS  read-only
    STATUS      current
    DESCRIPTION 
        "Number of times the scan limit has been exceeded, resulting in
         terminated IPS scanning for a flow using this rule."
    ::= { ssmIPSRulesEntry 1080 }

ssmIPSRuleName OBJECT-TYPE
    SYNTAX      DisplayString
    MAX-ACCESS  read-only
    STATUS      current
    DESCRIPTION 
        "IPS rule name."
    ::= { ssmIPSRulesEntry 2 }

ssmSSLInspection OBJECT IDENTIFIER
    ::= { ssmThreatPrevention 2020 }

ssmSSLInspFailedIntercepts OBJECT-TYPE
    SYNTAX      Counter32
    MAX-ACCESS  read-only
    STATUS      current
    DESCRIPTION 
        "Total number of failed interceptions."
    ::= { ssmSSLInspection 1005 }

ssmSSLInspSuccessfulIntercepts OBJECT-TYPE
    SYNTAX      Counter32
    MAX-ACCESS  read-only
    STATUS      current
    DESCRIPTION 
        "Total number of successful interceptions."
    ::= { ssmSSLInspection 1010 }

ssmSSLInspectionProfileTable OBJECT-TYPE
    SYNTAX      SEQUENCE OF SsmSSLInspectionProfileEntry
    MAX-ACCESS  not-accessible
    STATUS      current
    DESCRIPTION 
        "SSL Inspection per profile statistics."
    ::= { ssmSSLInspection 3010 }

ssmSSLInspectionProfileEntry OBJECT-TYPE
    SYNTAX      SsmSSLInspectionProfileEntry
    MAX-ACCESS  not-accessible
    STATUS      current
    DESCRIPTION 
        "The row in a table of SSL Inspection profile statistics."
    INDEX       { ssmSSLInspectionProfileIndex }
    ::= { ssmSSLInspectionProfileTable 1 }

SsmSSLInspectionProfileEntry ::= SEQUENCE {
    ssmSSLInspectionProfileIndex           Integer32,
    ssmSSLInspectionProfileName            DisplayString,
    ssmClientFailedTLS                     Counter32,
    ssmServerFailedTLS                     Counter32,
    ssmClientSuccessfulTLS                 Counter32,
    ssmServerSuccessfulTLS                 Counter32
}

ssmSSLInspectionProfileIndex OBJECT-TYPE
    SYNTAX      Integer32 (1..2147483647)
    MAX-ACCESS  not-accessible
    STATUS      current
    DESCRIPTION 
        "SSL Inspection profile row index."
    ::= { ssmSSLInspectionProfileEntry 1 }

ssmClientFailedTLS OBJECT-TYPE
    SYNTAX      Counter32
    MAX-ACCESS  read-only
    STATUS      current
    DESCRIPTION 
        "Number of failed client TLS connections for this profile."
    ::= { ssmSSLInspectionProfileEntry 1005 }

ssmServerFailedTLS OBJECT-TYPE
    SYNTAX      Counter32
    MAX-ACCESS  read-only
    STATUS      current
    DESCRIPTION 
        "Number of failed server TLS connections for this profile."
    ::= { ssmSSLInspectionProfileEntry 1010 }

ssmClientSuccessfulTLS OBJECT-TYPE
    SYNTAX      Counter32
    MAX-ACCESS  read-only
    STATUS      current
    DESCRIPTION 
        "Number of successful client TLS connections for this profile."
    ::= { ssmSSLInspectionProfileEntry 1015 }

ssmServerSuccessfulTLS OBJECT-TYPE
    SYNTAX      Counter32
    MAX-ACCESS  read-only
    STATUS      current
    DESCRIPTION 
        "Number of successful server TLS connections for this profile."
    ::= { ssmSSLInspectionProfileEntry 1020 }

ssmSSLInspectionProfileName OBJECT-TYPE
    SYNTAX      DisplayString
    MAX-ACCESS  read-only
    STATUS      current
    DESCRIPTION 
        "SSL Inspection profile name."
    ::= { ssmSSLInspectionProfileEntry 2 }

ssmTrafficManagement OBJECT IDENTIFIER
    ::= { clavisterSystemStats 2090 }

ssmPipeStatsTable OBJECT-TYPE
    SYNTAX      SEQUENCE OF SsmPipeStatsEntry
    MAX-ACCESS  not-accessible
    STATUS      current
    DESCRIPTION 
        "Pipe object statistics module."
    ::= { ssmTrafficManagement 3010 }

ssmPipeStatsEntry OBJECT-TYPE
    SYNTAX      SsmPipeStatsEntry
    MAX-ACCESS  not-accessible
    STATUS      current
    DESCRIPTION 
        "Pipe object statistics entry."
    INDEX       { ssmPipeIndex }
    ::= { ssmPipeStatsTable 1 }

SsmPipeStatsEntry ::= SEQUENCE {
    ssmPipeIndex                 Integer32,
    ssmPipeName                  DisplayString,
    ssmPipeStatsAvgInterval      Unsigned32,
    ssmPipeStatsGroupsTotal      Gauge32,
    ssmPipeStatsGroupsActive     Gauge32,
    ssmPipeStatsTotalByteRecv    Counter64,
    ssmPipeStatsTotalByteSent    Counter64,
    ssmPipeStatsTotalPktsRecv    Counter64,
    ssmPipeStatsTotalPktsSent    Counter64,
    ssmPipeStatsTotalBpsRecv     CounterBasedGauge64,
    ssmPipeStatsTotalBpsSent     CounterBasedGauge64,
    ssmPipeStatsTotalPpsRecv     CounterBasedGauge64,
    ssmPipeStatsTotalPpsSent     CounterBasedGauge64,
    ssmPipeStatsAvgTotalBpsRecv    CounterBasedGauge64,
    ssmPipeStatsAvgTotalBpsSent    CounterBasedGauge64,
    ssmPipeStatsAvgTotalPpsRecv    CounterBasedGauge64,
    ssmPipeStatsAvgTotalPpsSent    CounterBasedGauge64,
    ssmPipeStatsGroupLimitBps    CounterBasedGauge64,
    ssmPipeStatsGroupLimitPps    CounterBasedGauge64
}

ssmPipeIndex OBJECT-TYPE
    SYNTAX      Integer32 (1..2147483647)
    MAX-ACCESS  not-accessible
    STATUS      current
    DESCRIPTION 
        "Pipe object statistics row index."
    ::= { ssmPipeStatsEntry 1 }

ssmPipeStatsAvgInterval OBJECT-TYPE
    SYNTAX      Unsigned32
    MAX-ACCESS  read-only
    STATUS      current
    DESCRIPTION 
        "Number of seconds elapsed since the statistics were last reset
         for this pipe object. Average and total values are valid for
         this interval."
    ::= { ssmPipeStatsEntry 1010 }

ssmPipeStatsGroupsTotal OBJECT-TYPE
    SYNTAX      Gauge32
    MAX-ACCESS  read-only
    STATUS      current
    DESCRIPTION 
        "Total number of user groups for which this pipe has state."
    ::= { ssmPipeStatsEntry 1050 }

ssmPipeStatsGroupsActive OBJECT-TYPE
    SYNTAX      Gauge32
    MAX-ACCESS  read-only
    STATUS      current
    DESCRIPTION 
        "Number of user groups for which the pipe is actively forwarding
         traffic."
    ::= { ssmPipeStatsEntry 1060 }

ssmPipeStatsTotalByteRecv OBJECT-TYPE
    SYNTAX      Counter64
    MAX-ACCESS  read-only
    STATUS      current
    DESCRIPTION 
        "Total number of bytes having been received by the pipe object."
    ::= { ssmPipeStatsEntry 1210 }

ssmPipeStatsTotalByteSent OBJECT-TYPE
    SYNTAX      Counter64
    MAX-ACCESS  read-only
    STATUS      current
    DESCRIPTION 
        "Total number of bytes having been forwarded by the pipe object."
    ::= { ssmPipeStatsEntry 1220 }

ssmPipeStatsTotalPktsRecv OBJECT-TYPE
    SYNTAX      Counter64
    MAX-ACCESS  read-only
    STATUS      current
    DESCRIPTION 
        "Total number of packets having been received by the pipe object."
    ::= { ssmPipeStatsEntry 1230 }

ssmPipeStatsTotalPktsSent OBJECT-TYPE
    SYNTAX      Counter64
    MAX-ACCESS  read-only
    STATUS      current
    DESCRIPTION 
        "Total number of packets having been forwarded by the pipe object."
    ::= { ssmPipeStatsEntry 1240 }

ssmPipeStatsTotalBpsRecv OBJECT-TYPE
    SYNTAX      CounterBasedGauge64
    MAX-ACCESS  read-only
    STATUS      current
    DESCRIPTION 
        "Total number of bits per second currently being received by the
         pipe object."
    ::= { ssmPipeStatsEntry 1410 }

ssmPipeStatsTotalBpsSent OBJECT-TYPE
    SYNTAX      CounterBasedGauge64
    MAX-ACCESS  read-only
    STATUS      current
    DESCRIPTION 
        "Total number of bits per second currently being forwarded by the
         pipe object."
    ::= { ssmPipeStatsEntry 1420 }

ssmPipeStatsTotalPpsRecv OBJECT-TYPE
    SYNTAX      CounterBasedGauge64
    MAX-ACCESS  read-only
    STATUS      current
    DESCRIPTION 
        "Total number of packets per second currently being received by
         the pipe object."
    ::= { ssmPipeStatsEntry 1430 }

ssmPipeStatsTotalPpsSent OBJECT-TYPE
    SYNTAX      CounterBasedGauge64
    MAX-ACCESS  read-only
    STATUS      current
    DESCRIPTION 
        "Total number of packets per second currently being forwarded by
         the pipe object."
    ::= { ssmPipeStatsEntry 1440 }

ssmPipeStatsAvgTotalBpsRecv OBJECT-TYPE
    SYNTAX      CounterBasedGauge64
    MAX-ACCESS  read-only
    STATUS      current
    DESCRIPTION 
        "Number of bits per second received on average, by the whole pipe
         object."
    ::= { ssmPipeStatsEntry 1610 }

ssmPipeStatsAvgTotalBpsSent OBJECT-TYPE
    SYNTAX      CounterBasedGauge64
    MAX-ACCESS  read-only
    STATUS      current
    DESCRIPTION 
        "Number of bits per second forwarded on average, by the whole
         pipe object."
    ::= { ssmPipeStatsEntry 1620 }

ssmPipeStatsAvgTotalPpsRecv OBJECT-TYPE
    SYNTAX      CounterBasedGauge64
    MAX-ACCESS  read-only
    STATUS      current
    DESCRIPTION 
        "Number of packets per second received on average, by the whole
         pipe object."
    ::= { ssmPipeStatsEntry 1630 }

ssmPipeStatsAvgTotalPpsSent OBJECT-TYPE
    SYNTAX      CounterBasedGauge64
    MAX-ACCESS  read-only
    STATUS      current
    DESCRIPTION 
        "Number of packets per second forwarded on average, by the whole
         pipe object."
    ::= { ssmPipeStatsEntry 1640 }

ssmPipeStatsGroupLimitBps OBJECT-TYPE
    SYNTAX      CounterBasedGauge64
    MAX-ACCESS  read-only
    STATUS      current
    DESCRIPTION 
        "Dynamic limit in bits per second for each active group."
    ::= { ssmPipeStatsEntry 1810 }

ssmPipeStatsGroupLimitPps OBJECT-TYPE
    SYNTAX      CounterBasedGauge64
    MAX-ACCESS  read-only
    STATUS      current
    DESCRIPTION 
        "Dynamic limit in packets per second for each active group."
    ::= { ssmPipeStatsEntry 1820 }

ssmPipeName OBJECT-TYPE
    SYNTAX      DisplayString
    MAX-ACCESS  read-only
    STATUS      current
    DESCRIPTION 
        "Name of the pipe object."
    ::= { ssmPipeStatsEntry 2 }

ssmPipeStatsPrecedenceTable OBJECT-TYPE
    SYNTAX      SEQUENCE OF SsmPipeStatsPrecedenceEntry
    MAX-ACCESS  not-accessible
    STATUS      current
    DESCRIPTION 
        "Pipe object precedence statistics module."
    ::= { ssmTrafficManagement 3020 }

ssmPipeStatsPrecedenceEntry OBJECT-TYPE
    SYNTAX      SsmPipeStatsPrecedenceEntry
    MAX-ACCESS  not-accessible
    STATUS      current
    DESCRIPTION 
        "Pipe object precedence statistics entry."
    INDEX       { ssmPipeIndex,ssmPipePrecIndex }
    ::= { ssmPipeStatsPrecedenceTable 1 }

SsmPipeStatsPrecedenceEntry ::= SEQUENCE {
    ssmPipePrecIndex                  Integer32,
    ssmPipePrecName                   DisplayString,
    ssmPipePrecByteRecv               Counter64,
    ssmPipePrecByteSent               Counter64,
    ssmPipePrecPktsRecv               Counter64,
    ssmPipePrecPktsSent               Counter64,
    ssmPipePrecBpsRecv                CounterBasedGauge64,
    ssmPipePrecBpsSent                CounterBasedGauge64,
    ssmPipePrecPpsRecv                CounterBasedGauge64,
    ssmPipePrecPpsSent                CounterBasedGauge64,
    ssmPipePrecAvgBpsRecv             CounterBasedGauge64,
    ssmPipePrecAvgBpsSent             CounterBasedGauge64,
    ssmPipePrecAvgPpsRecv             CounterBasedGauge64,
    ssmPipePrecAvgPpsSent             CounterBasedGauge64,
    ssmPipePrecGroupLimitBps          CounterBasedGauge64,
    ssmPipePrecGroupLimitPps          CounterBasedGauge64
}

ssmPipePrecIndex OBJECT-TYPE
    SYNTAX      Integer32 (1..2147483647)
    MAX-ACCESS  not-accessible
    STATUS      current
    DESCRIPTION 
        "Pipe object precedence statistics row index."
    ::= { ssmPipeStatsPrecedenceEntry 1 }

ssmPipePrecByteRecv OBJECT-TYPE
    SYNTAX      Counter64
    MAX-ACCESS  read-only
    STATUS      current
    DESCRIPTION 
        "Accumulated number of bytes with the given precedence, having
         been received by the pipe object."
    ::= { ssmPipeStatsPrecedenceEntry 1210 }

ssmPipePrecByteSent OBJECT-TYPE
    SYNTAX      Counter64
    MAX-ACCESS  read-only
    STATUS      current
    DESCRIPTION 
        "Accumulated number of bytes with the given precedence, having
         been forwarded by the pipe object."
    ::= { ssmPipeStatsPrecedenceEntry 1220 }

ssmPipePrecPktsRecv OBJECT-TYPE
    SYNTAX      Counter64
    MAX-ACCESS  read-only
    STATUS      current
    DESCRIPTION 
        "Accumulated number of packets with the given precedence, having
         been received by the pipe object."
    ::= { ssmPipeStatsPrecedenceEntry 1230 }

ssmPipePrecPktsSent OBJECT-TYPE
    SYNTAX      Counter64
    MAX-ACCESS  read-only
    STATUS      current
    DESCRIPTION 
        "Accumulated number of packets with the given precedence, having
         been forwarded by the pipe object."
    ::= { ssmPipeStatsPrecedenceEntry 1240 }

ssmPipePrecBpsRecv OBJECT-TYPE
    SYNTAX      CounterBasedGauge64
    MAX-ACCESS  read-only
    STATUS      current
    DESCRIPTION 
        "Number of bits per second with the given precedence, currently
         being received by the pipe object."
    ::= { ssmPipeStatsPrecedenceEntry 1410 }

ssmPipePrecBpsSent OBJECT-TYPE
    SYNTAX      CounterBasedGauge64
    MAX-ACCESS  read-only
    STATUS      current
    DESCRIPTION 
        "Number of bits per second with the given precedence, currently
         being forwarded by the pipe object."
    ::= { ssmPipeStatsPrecedenceEntry 1420 }

ssmPipePrecPpsRecv OBJECT-TYPE
    SYNTAX      CounterBasedGauge64
    MAX-ACCESS  read-only
    STATUS      current
    DESCRIPTION 
        "Number of packets per second with the given precedence,
         currently being received by the pipe object."
    ::= { ssmPipeStatsPrecedenceEntry 1430 }

ssmPipePrecPpsSent OBJECT-TYPE
    SYNTAX      CounterBasedGauge64
    MAX-ACCESS  read-only
    STATUS      current
    DESCRIPTION 
        "Number of packets per second with the given precedence,
         currently being forwarded by the pipe object."
    ::= { ssmPipeStatsPrecedenceEntry 1440 }

ssmPipePrecAvgBpsRecv OBJECT-TYPE
    SYNTAX      CounterBasedGauge64
    MAX-ACCESS  read-only
    STATUS      current
    DESCRIPTION 
        "Average number of bits per second with the given precedence,
         received by the pipe object,."
    ::= { ssmPipeStatsPrecedenceEntry 1610 }

ssmPipePrecAvgBpsSent OBJECT-TYPE
    SYNTAX      CounterBasedGauge64
    MAX-ACCESS  read-only
    STATUS      current
    DESCRIPTION 
        "Average number of bits per second with the given precedence,
         forwarded by the pipe object."
    ::= { ssmPipeStatsPrecedenceEntry 1620 }

ssmPipePrecAvgPpsRecv OBJECT-TYPE
    SYNTAX      CounterBasedGauge64
    MAX-ACCESS  read-only
    STATUS      current
    DESCRIPTION 
        "Average number of packets per second with the given precedence,
         received by the pipe object."
    ::= { ssmPipeStatsPrecedenceEntry 1630 }

ssmPipePrecAvgPpsSent OBJECT-TYPE
    SYNTAX      CounterBasedGauge64
    MAX-ACCESS  read-only
    STATUS      current
    DESCRIPTION 
        "Average number of packets per second with the given precedence,
         forwarded by the pipe object."
    ::= { ssmPipeStatsPrecedenceEntry 1640 }

ssmPipePrecGroupLimitBps OBJECT-TYPE
    SYNTAX      CounterBasedGauge64
    MAX-ACCESS  read-only
    STATUS      current
    DESCRIPTION 
        "Dynamic limit in bits per second for the given precedence and
         each active group."
    ::= { ssmPipeStatsPrecedenceEntry 1810 }

ssmPipePrecGroupLimitPps OBJECT-TYPE
    SYNTAX      CounterBasedGauge64
    MAX-ACCESS  read-only
    STATUS      current
    DESCRIPTION 
        "Dynamic limit in packets per second for the given precedence and
         each active group."
    ::= { ssmPipeStatsPrecedenceEntry 1820 }

ssmPipePrecName OBJECT-TYPE
    SYNTAX      DisplayString
    MAX-ACCESS  read-only
    STATUS      current
    DESCRIPTION 
        "Name of the pipe object precedence statistic row."
    ::= { ssmPipeStatsPrecedenceEntry 2 }

ssmThreshold OBJECT IDENTIFIER
    ::= { ssmTrafficManagement 3030 }

ssmThresholdTotalGroups OBJECT-TYPE
    SYNTAX      Gauge32
    MAX-ACCESS  read-only
    STATUS      current
    DESCRIPTION 
        "Grand total of currently maintained threshold groups."
    ::= { ssmThreshold 1010 }

ssmThresholdTotalActiveGroups OBJECT-TYPE
    SYNTAX      Gauge32
    MAX-ACCESS  read-only
    STATUS      current
    DESCRIPTION 
        "Grand total of currently active threshold groups."
    ::= { ssmThreshold 1020 }

ssmThresholdTotalOffendingGroups OBJECT-TYPE
    SYNTAX      Gauge32
    MAX-ACCESS  read-only
    STATUS      current
    DESCRIPTION 
        "Grand total of threshold groups currently violating a threshold
         limit."
    ::= { ssmThreshold 1030 }

ssmThresholdTotalGroupExceeded OBJECT-TYPE
    SYNTAX      Counter32
    MAX-ACCESS  read-only
    STATUS      current
    DESCRIPTION 
        "Grand historical count of how many times any group has violated
         a threshold."
    ::= { ssmThreshold 1040 }

ssmThresholdTotalActionNone OBJECT-TYPE
    SYNTAX      Counter32
    MAX-ACCESS  read-only
    STATUS      current
    DESCRIPTION 
        "Grand historical count of how many times the action 'none' has
         been executed."
    ::= { ssmThreshold 2010 }

ssmThresholdTotalActionRndDrop OBJECT-TYPE
    SYNTAX      Counter32
    MAX-ACCESS  read-only
    STATUS      current
    DESCRIPTION 
        "Grand historical count of how many times the action 'random
         drop' has been executed."
    ::= { ssmThreshold 2030 }

ssmThresholdTotalActRndDropDeny OBJECT-TYPE
    SYNTAX      Counter32
    MAX-ACCESS  read-only
    STATUS      current
    DESCRIPTION 
        "Grand historical count of how many times the action 'random
         drop' has denied a connection attempt."
    ::= { ssmThreshold 2050 }

ssmThresholdTotalActionReject OBJECT-TYPE
    SYNTAX      Counter32
    MAX-ACCESS  read-only
    STATUS      current
    DESCRIPTION 
        "Grand historical count of how many times the action 'reject' has
         been executed."
    ::= { ssmThreshold 2070 }

ssmThresholdTotalActionDrop OBJECT-TYPE
    SYNTAX      Counter32
    MAX-ACCESS  read-only
    STATUS      current
    DESCRIPTION 
        "Grand historical count of how many times the action 'drop' has
         been executed."
    ::= { ssmThreshold 2080 }

ssmThresholdTotalActionBlacklist OBJECT-TYPE
    SYNTAX      Counter32
    MAX-ACCESS  read-only
    STATUS      current
    DESCRIPTION 
        "Grand historical count of how many times the action 'blacklist'
         has been executed."
    ::= { ssmThreshold 2090 }

ssmThresholdRuleActionTable OBJECT-TYPE
    SYNTAX      SEQUENCE OF SsmThresholdRuleActionEntry
    MAX-ACCESS  not-accessible
    STATUS      current
    DESCRIPTION 
        "Threshold action statistics module."
    ::= { ssmThreshold 3010 }

ssmThresholdRuleActionEntry OBJECT-TYPE
    SYNTAX      SsmThresholdRuleActionEntry
    MAX-ACCESS  not-accessible
    STATUS      current
    DESCRIPTION 
        "Threshold action statistics entry."
    INDEX       { ssmThresholdRuleSetIndex,ssmThresholdRuleIndex,ssmThresholdActionIndex }
    ::= { ssmThresholdRuleActionTable 1 }

SsmThresholdRuleActionEntry ::= SEQUENCE {
    ssmThresholdActionIndex     Integer32,
    ssmThresholdActionName      DisplayString,
    ssmThresholdActionTrigged    Counter32
}

ssmThresholdActionIndex OBJECT-TYPE
    SYNTAX      Integer32 (1..2147483647)
    MAX-ACCESS  not-accessible
    STATUS      current
    DESCRIPTION 
        "Index of threshold action whithin threshold rule."
    ::= { ssmThresholdRuleActionEntry 1 }

ssmThresholdActionTrigged OBJECT-TYPE
    SYNTAX      Counter32
    MAX-ACCESS  read-only
    STATUS      current
    DESCRIPTION 
        "Number of times that the action has triggered."
    ::= { ssmThresholdRuleActionEntry 1010 }

ssmThresholdActionName OBJECT-TYPE
    SYNTAX      DisplayString
    MAX-ACCESS  read-only
    STATUS      current
    DESCRIPTION 
        "Name of threshold action whithin threshold rule."
    ::= { ssmThresholdRuleActionEntry 2 }

ssmThresholdActionLimitTable OBJECT-TYPE
    SYNTAX      SEQUENCE OF SsmThresholdActionLimitEntry
    MAX-ACCESS  not-accessible
    STATUS      current
    DESCRIPTION 
        "Threshold definition statistics module."
    ::= { ssmThreshold 3020 }

ssmThresholdActionLimitEntry OBJECT-TYPE
    SYNTAX      SsmThresholdActionLimitEntry
    MAX-ACCESS  not-accessible
    STATUS      current
    DESCRIPTION 
        "Threshold definition statistics entry."
    INDEX       { ssmThresholdRuleSetIndex,ssmThresholdRuleIndex,ssmThresholdActionIndex,ssmThresholdActionLimitIndex }
    ::= { ssmThresholdActionLimitTable 1 }

SsmThresholdActionLimitEntry ::= SEQUENCE {
    ssmThresholdActionLimitIndex    Integer32,
    ssmThresholdActionLimitName    DisplayString,
    ssmThresholdLimitGroupsActive    Gauge32,
    ssmThresholdLimitGroupExceeding    Gauge32,
    ssmThresholdLimitGroupsExceeded    Counter32
}

ssmThresholdActionLimitIndex OBJECT-TYPE
    SYNTAX      Integer32 (1..2147483647)
    MAX-ACCESS  not-accessible
    STATUS      current
    DESCRIPTION 
        "Index of threshold limit whithin threshold action."
    ::= { ssmThresholdActionLimitEntry 1 }

ssmThresholdLimitGroupsActive OBJECT-TYPE
    SYNTAX      Gauge32
    MAX-ACCESS  read-only
    STATUS      current
    DESCRIPTION 
        "Number of currently active threshold groups."
    ::= { ssmThresholdActionLimitEntry 1010 }

ssmThresholdLimitGroupExceeding OBJECT-TYPE
    SYNTAX      Gauge32
    MAX-ACCESS  read-only
    STATUS      current
    DESCRIPTION 
        "Number of threshold groups currently exceeding a threshold."
    ::= { ssmThresholdActionLimitEntry 1020 }

ssmThresholdLimitGroupsExceeded OBJECT-TYPE
    SYNTAX      Counter32
    MAX-ACCESS  read-only
    STATUS      current
    DESCRIPTION 
        "Number of times that threshold groups has exceeded the threshold
         (the number of times that some threshold group has begun to
         exceed the threshold, invariant of the time they have been above
         the threshold)."
    ::= { ssmThresholdActionLimitEntry 1030 }

ssmThresholdActionLimitName OBJECT-TYPE
    SYNTAX      DisplayString
    MAX-ACCESS  read-only
    STATUS      current
    DESCRIPTION 
        "Name of threshold limit whithin threshold action."
    ::= { ssmThresholdActionLimitEntry 2 }

ssmBlacklist OBJECT IDENTIFIER
    ::= { ssmTrafficManagement 3040 }

ssmBlacklistRules OBJECT-TYPE
    SYNTAX      Unsigned32
    MAX-ACCESS  read-only
    STATUS      current
    DESCRIPTION 
        "Currently active blacklist rules."
    ::= { ssmBlacklist 1010 }

ssmMaxBlacklistEntries OBJECT-TYPE
    SYNTAX      Unsigned32
    MAX-ACCESS  read-only
    STATUS      current
    DESCRIPTION 
        "Maximum number of simultaneous blacklist entries."
    ::= { ssmBlacklist 1011 }

ssmBlacklistPacketsDropped OBJECT-TYPE
    SYNTAX      Unsigned32
    MAX-ACCESS  read-only
    STATUS      current
    DESCRIPTION 
        "Packets dropped by blacklist."
    ::= { ssmBlacklist 1020 }

ssmWhitelistFlowsAllowed OBJECT-TYPE
    SYNTAX      Unsigned32
    MAX-ACCESS  read-only
    STATUS      current
    DESCRIPTION 
        "Flows allowed in the system because of whitelisting even though
         the source was blacklisted."
    ::= { ssmBlacklist 1030 }

ssmWhitelistRules OBJECT-TYPE
    SYNTAX      Unsigned32
    MAX-ACCESS  read-only
    STATUS      current
    DESCRIPTION 
        "Configured whitelist rules."
    ::= { ssmBlacklist 1040 }

ssmALG OBJECT IDENTIFIER
    ::= { clavisterSystemStats 2100 }

ssmDNS OBJECT IDENTIFIER
    ::= { ssmALG 2030 }

ssmDNSALGFwdQueriesSys OBJECT-TYPE
    SYNTAX      Counter64
    MAX-ACCESS  read-only
    STATUS      current
    DESCRIPTION 
        "Number of DNS queries forwarded."
    ::= { ssmDNS 1005 }

ssmDNSALGFwdResponsesSys OBJECT-TYPE
    SYNTAX      Counter64
    MAX-ACCESS  read-only
    STATUS      current
    DESCRIPTION 
        "Number of DNS responses forwarded."
    ::= { ssmDNS 1010 }

ssmDNSALGMalformedClientMsgsSys OBJECT-TYPE
    SYNTAX      Counter64
    MAX-ACCESS  read-only
    STATUS      current
    DESCRIPTION 
        "Number of DNS messages from client for which RFC protocol
         validation failed."
    ::= { ssmDNS 1015 }

ssmDNSALGMalformedServerMsgsSys OBJECT-TYPE
    SYNTAX      Counter64
    MAX-ACCESS  read-only
    STATUS      current
    DESCRIPTION 
        "Number of DNS messages from server for which RFC protocol
         validation failed."
    ::= { ssmDNS 1020 }

ssmDNSALGDroppedClientMsgsSys OBJECT-TYPE
    SYNTAX      Counter64
    MAX-ACCESS  read-only
    STATUS      current
    DESCRIPTION 
        "Number of dropped DNS messages from client, including messages
         dropped due to being malformed."
    ::= { ssmDNS 1025 }

ssmDNSALGDroppedServerMsgsSys OBJECT-TYPE
    SYNTAX      Counter64
    MAX-ACCESS  read-only
    STATUS      current
    DESCRIPTION 
        "Number of dropped DNS messages from server, including messages
         dropped due to being malformed."
    ::= { ssmDNS 1030 }

ssmDNSALGTranslationsSys OBJECT-TYPE
    SYNTAX      Counter64
    MAX-ACCESS  read-only
    STATUS      current
    DESCRIPTION 
        "Number of translated addresses."
    ::= { ssmDNS 1035 }

ssmDNSALGSessionsCurrentSys OBJECT-TYPE
    SYNTAX      Unsigned32
    MAX-ACCESS  read-only
    STATUS      current
    DESCRIPTION 
        "Currently active sessions."
    ::= { ssmDNS 1040 }

ssmDNSALGSessionsTotalSys OBJECT-TYPE
    SYNTAX      Counter64
    MAX-ACCESS  read-only
    STATUS      current
    DESCRIPTION 
        "Total amount of sessions processed over time."
    ::= { ssmDNS 1045 }

ssmDNSALGProfilesTable OBJECT-TYPE
    SYNTAX      SEQUENCE OF SsmDNSALGProfilesEntry
    MAX-ACCESS  not-accessible
    STATUS      current
    DESCRIPTION 
        "DNSALG profile statistics."
    ::= { ssmDNS 3010 }

ssmDNSALGProfilesEntry OBJECT-TYPE
    SYNTAX      SsmDNSALGProfilesEntry
    MAX-ACCESS  not-accessible
    STATUS      current
    DESCRIPTION 
        "The row in a table of profile statistics."
    INDEX       { ssmProfileIndex }
    ::= { ssmDNSALGProfilesTable 1 }

SsmDNSALGProfilesEntry ::= SEQUENCE {
    ssmDNSALGProfileIndex                Integer32,
    ssmDNSALGProfileName                 DisplayString,
    ssmDNSALGFwdQueries                  Counter64,
    ssmDNSALGFwdResponses                Counter64,
    ssmDNSALGMalformedClientMsgs         Counter64,
    ssmDNSALGMalformedServerMsgs         Counter64,
    ssmDNSALGDroppedClientMsgs           Counter64,
    ssmDNSALGDroppedServerMsgs           Counter64,
    ssmDNSALGTranslations                Counter64,
    ssmDNSALGSessionsCurrent             Unsigned32,
    ssmDNSALGSessionsTotal               Counter64
}

ssmDNSALGProfileIndex OBJECT-TYPE
    SYNTAX      Integer32
    MAX-ACCESS  read-only
    STATUS      current
    DESCRIPTION 
        "DNSALG profile row index."
    ::= { ssmDNSALGProfilesEntry 1 }

ssmDNSALGFwdQueries OBJECT-TYPE
    SYNTAX      Counter64
    MAX-ACCESS  read-only
    STATUS      current
    DESCRIPTION 
        "Number of DNS queries forwarded."
    ::= { ssmDNSALGProfilesEntry 1005 }

ssmDNSALGFwdResponses OBJECT-TYPE
    SYNTAX      Counter64
    MAX-ACCESS  read-only
    STATUS      current
    DESCRIPTION 
        "Number of DNS responses forwarded."
    ::= { ssmDNSALGProfilesEntry 1010 }

ssmDNSALGMalformedClientMsgs OBJECT-TYPE
    SYNTAX      Counter64
    MAX-ACCESS  read-only
    STATUS      current
    DESCRIPTION 
        "Number of DNS messages from client for which RFC protocol
         validation failed."
    ::= { ssmDNSALGProfilesEntry 1015 }

ssmDNSALGMalformedServerMsgs OBJECT-TYPE
    SYNTAX      Counter64
    MAX-ACCESS  read-only
    STATUS      current
    DESCRIPTION 
        "Number of DNS messages from server for which RFC protocol
         validation failed."
    ::= { ssmDNSALGProfilesEntry 1020 }

ssmDNSALGDroppedClientMsgs OBJECT-TYPE
    SYNTAX      Counter64
    MAX-ACCESS  read-only
    STATUS      current
    DESCRIPTION 
        "Number of dropped DNS messages from client, including messages
         dropped due to being malformed."
    ::= { ssmDNSALGProfilesEntry 1025 }

ssmDNSALGDroppedServerMsgs OBJECT-TYPE
    SYNTAX      Counter64
    MAX-ACCESS  read-only
    STATUS      current
    DESCRIPTION 
        "Number of dropped DNS messages from server, including messages
         dropped due to being malformed."
    ::= { ssmDNSALGProfilesEntry 1030 }

ssmDNSALGTranslations OBJECT-TYPE
    SYNTAX      Counter64
    MAX-ACCESS  read-only
    STATUS      current
    DESCRIPTION 
        "Number of translated addresses."
    ::= { ssmDNSALGProfilesEntry 1035 }

ssmDNSALGSessionsCurrent OBJECT-TYPE
    SYNTAX      Unsigned32
    MAX-ACCESS  read-only
    STATUS      current
    DESCRIPTION 
        "Currently active sessions."
    ::= { ssmDNSALGProfilesEntry 1040 }

ssmDNSALGSessionsTotal OBJECT-TYPE
    SYNTAX      Counter64
    MAX-ACCESS  read-only
    STATUS      current
    DESCRIPTION 
        "Total amount of sessions processed over time."
    ::= { ssmDNSALGProfilesEntry 1045 }

ssmDNSALGProfileName OBJECT-TYPE
    SYNTAX      DisplayString
    MAX-ACCESS  read-only
    STATUS      current
    DESCRIPTION 
        "DNSALG profile name."
    ::= { ssmDNSALGProfilesEntry 2 }

ssmFTP OBJECT IDENTIFIER
    ::= { ssmALG 2040 }

ssmFTPALGUnknownCmdsSystem OBJECT-TYPE
    SYNTAX      Unsigned32
    MAX-ACCESS  read-only
    STATUS      current
    DESCRIPTION 
        "Unknown commands received on FTPALG."
    ::= { ssmFTP 1000 }

ssmFTPALGDataChannelsCurrSystem OBJECT-TYPE
    SYNTAX      Unsigned32
    MAX-ACCESS  read-only
    STATUS      current
    DESCRIPTION 
        "Currently established data channels."
    ::= { ssmFTP 1005 }

ssmFTPALGDataChannelsTotalSystem OBJECT-TYPE
    SYNTAX      Counter64
    MAX-ACCESS  read-only
    STATUS      current
    DESCRIPTION 
        "Total established data channels."
    ::= { ssmFTP 1010 }

ssmFTPALGSessionsCurrentSystem OBJECT-TYPE
    SYNTAX      Unsigned32
    MAX-ACCESS  read-only
    STATUS      current
    DESCRIPTION 
        "Currently active sessions."
    ::= { ssmFTP 1015 }

ssmFTPALGSessionsTotalSystem OBJECT-TYPE
    SYNTAX      Counter64
    MAX-ACCESS  read-only
    STATUS      current
    DESCRIPTION 
        "Total amount of sessions."
    ::= { ssmFTP 1020 }

ssmFTPALGCmdRateExceededSystem OBJECT-TYPE
    SYNTAX      Counter32
    MAX-ACCESS  read-only
    STATUS      current
    DESCRIPTION 
        "Number of sessions that have exceeded the command rate limit."
    ::= { ssmFTP 1025 }

ssmFTPALGProfilesTable OBJECT-TYPE
    SYNTAX      SEQUENCE OF SsmFTPALGProfilesEntry
    MAX-ACCESS  not-accessible
    STATUS      current
    DESCRIPTION 
        "FTPALG profile statistics."
    ::= { ssmFTP 3000 }

ssmFTPALGProfilesEntry OBJECT-TYPE
    SYNTAX      SsmFTPALGProfilesEntry
    MAX-ACCESS  not-accessible
    STATUS      current
    DESCRIPTION 
        "The row in a table of profile statistics."
    INDEX       { ssmProfileIndex }
    ::= { ssmFTPALGProfilesTable 1 }

SsmFTPALGProfilesEntry ::= SEQUENCE {
    ssmFTPALGProfileIndex       Integer32,
    ssmFTPALGProfileName        DisplayString,
    ssmFTPALGUnknownCmds        Unsigned32,
    ssmFTPALGDataChannelsCurrent    Unsigned32,
    ssmFTPALGDataChannelsTotal    Counter64,
    ssmFTPALGSessionsCurrent    Unsigned32,
    ssmFTPALGSessionsTotal      Counter64,
    ssmFTPALGCmdRateExceeded    Counter32
}

ssmFTPALGProfileIndex OBJECT-TYPE
    SYNTAX      Integer32
    MAX-ACCESS  read-only
    STATUS      current
    DESCRIPTION 
        "Authentication profile row index."
    ::= { ssmFTPALGProfilesEntry 1 }

ssmFTPALGUnknownCmds OBJECT-TYPE
    SYNTAX      Unsigned32
    MAX-ACCESS  read-only
    STATUS      current
    DESCRIPTION 
        "Unknown commands received on FTPALG."
    ::= { ssmFTPALGProfilesEntry 1000 }

ssmFTPALGDataChannelsCurrent OBJECT-TYPE
    SYNTAX      Unsigned32
    MAX-ACCESS  read-only
    STATUS      current
    DESCRIPTION 
        "Currently established data channels."
    ::= { ssmFTPALGProfilesEntry 1005 }

ssmFTPALGDataChannelsTotal OBJECT-TYPE
    SYNTAX      Counter64
    MAX-ACCESS  read-only
    STATUS      current
    DESCRIPTION 
        "Total established data channels."
    ::= { ssmFTPALGProfilesEntry 1010 }

ssmFTPALGSessionsCurrent OBJECT-TYPE
    SYNTAX      Unsigned32
    MAX-ACCESS  read-only
    STATUS      current
    DESCRIPTION 
        "Current sessions for profile."
    ::= { ssmFTPALGProfilesEntry 1015 }

ssmFTPALGSessionsTotal OBJECT-TYPE
    SYNTAX      Counter64
    MAX-ACCESS  read-only
    STATUS      current
    DESCRIPTION 
        "Total sessions for profile."
    ::= { ssmFTPALGProfilesEntry 1020 }

ssmFTPALGCmdRateExceeded OBJECT-TYPE
    SYNTAX      Counter32
    MAX-ACCESS  read-only
    STATUS      current
    DESCRIPTION 
        "Number of sessions that have exceeded the command rate limit on
         a specific profile."
    ::= { ssmFTPALGProfilesEntry 1025 }

ssmFTPALGProfileName OBJECT-TYPE
    SYNTAX      DisplayString
    MAX-ACCESS  read-only
    STATUS      current
    DESCRIPTION 
        "FTPALG profile name."
    ::= { ssmFTPALGProfilesEntry 2 }

ssmGTP OBJECT IDENTIFIER
    ::= { ssmALG 2050 }

ssmGTPCGlobal OBJECT IDENTIFIER
    ::= { ssmGTP 2010 }

ssmGTPCDuplicatedIEsSys OBJECT-TYPE
    SYNTAX      Counter64
    MAX-ACCESS  read-only
    STATUS      current
    DESCRIPTION 
        "Number of GTP-C messages containing duplicated IEs."
    ::= { ssmGTPCGlobal 1010 }

ssmGTPCInvalidMandatoryIEsSys OBJECT-TYPE
    SYNTAX      Counter64
    MAX-ACCESS  read-only
    STATUS      current
    DESCRIPTION 
        "Number of GTP-C messages containing invalid mandatory IEs."
    ::= { ssmGTPCGlobal 1020 }

ssmGTPCInvalidOptionalIEsSys OBJECT-TYPE
    SYNTAX      Counter64
    MAX-ACCESS  read-only
    STATUS      current
    DESCRIPTION 
        "Number of GTP-C messages containing invalid optional IEs."
    ::= { ssmGTPCGlobal 1030 }

ssmGTPCMissingMandatoryIEsSys OBJECT-TYPE
    SYNTAX      Counter64
    MAX-ACCESS  read-only
    STATUS      current
    DESCRIPTION 
        "Number of GTP-C messages with missing mandatory IEs."
    ::= { ssmGTPCGlobal 1040 }

ssmGTPCDroppedSys OBJECT-TYPE
    SYNTAX      Counter64
    MAX-ACCESS  read-only
    STATUS      current
    DESCRIPTION 
        "Number of dropped GTP-C messages, including messages with
         invalid or unknown version."
    ::= { ssmGTPCGlobal 1050 }

ssmGTPCForwardedSys OBJECT-TYPE
    SYNTAX      Counter64
    MAX-ACCESS  read-only
    STATUS      current
    DESCRIPTION 
        "Number of forwarded GTP-C messages."
    ::= { ssmGTPCGlobal 1060 }

ssmGTPCReceivedSys OBJECT-TYPE
    SYNTAX      Counter64
    MAX-ACCESS  read-only
    STATUS      current
    DESCRIPTION 
        "Number of received GTP-C messages, including messages with
         invalid or unknown version."
    ::= { ssmGTPCGlobal 1070 }

ssmGTPCV1DroppedSys OBJECT-TYPE
    SYNTAX      Counter64
    MAX-ACCESS  read-only
    STATUS      current
    DESCRIPTION 
        "Number of dropped GTPv1-C messages."
    ::= { ssmGTPCGlobal 1080 }

ssmGTPCV1ForwardedSys OBJECT-TYPE
    SYNTAX      Counter64
    MAX-ACCESS  read-only
    STATUS      current
    DESCRIPTION 
        "Number of forwarded GTPv1-C messages."
    ::= { ssmGTPCGlobal 1090 }

ssmGTPCV1ReceivedSys OBJECT-TYPE
    SYNTAX      Counter64
    MAX-ACCESS  read-only
    STATUS      current
    DESCRIPTION 
        "Number of received GTPv1-C messages."
    ::= { ssmGTPCGlobal 1100 }

ssmGTPCV2DroppedSys OBJECT-TYPE
    SYNTAX      Counter64
    MAX-ACCESS  read-only
    STATUS      current
    DESCRIPTION 
        "Number of dropped GTPv2-C messages."
    ::= { ssmGTPCGlobal 1110 }

ssmGTPCV2ForwardedSys OBJECT-TYPE
    SYNTAX      Counter64
    MAX-ACCESS  read-only
    STATUS      current
    DESCRIPTION 
        "Number of forwarded GTPv2-C messages."
    ::= { ssmGTPCGlobal 1120 }

ssmGTPCV2ReceivedSys OBJECT-TYPE
    SYNTAX      Counter64
    MAX-ACCESS  read-only
    STATUS      current
    DESCRIPTION 
        "Number of received GTPv2-C messages."
    ::= { ssmGTPCGlobal 1130 }

ssmGTPCSessionsActiveSys OBJECT-TYPE
    SYNTAX      Unsigned32
    MAX-ACCESS  read-only
    STATUS      current
    DESCRIPTION 
        "Number of currently active GTP-C sessions."
    ::= { ssmGTPCGlobal 1140 }

ssmGTPCSessionsCreatedSys OBJECT-TYPE
    SYNTAX      Counter64
    MAX-ACCESS  read-only
    STATUS      current
    DESCRIPTION 
        "Number of created GTP-C sessions."
    ::= { ssmGTPCGlobal 1150 }

ssmGTPCSessionsDeletedSys OBJECT-TYPE
    SYNTAX      Counter64
    MAX-ACCESS  read-only
    STATUS      current
    DESCRIPTION 
        "Number of deleted GTP-C sessions."
    ::= { ssmGTPCGlobal 1160 }

ssmGTPCOutOfOrderIEsSys OBJECT-TYPE
    SYNTAX      Counter64
    MAX-ACCESS  read-only
    STATUS      current
    DESCRIPTION 
        "Number of GTP-C messages with out-of-order IEs."
    ::= { ssmGTPCGlobal 1170 }

ssmGTPCTruncatedMsgsSys OBJECT-TYPE
    SYNTAX      Counter64
    MAX-ACCESS  read-only
    STATUS      current
    DESCRIPTION 
        "Number of truncated GTP-C messages."
    ::= { ssmGTPCGlobal 1180 }

ssmGTPCUnexpectedIEsSys OBJECT-TYPE
    SYNTAX      Counter64
    MAX-ACCESS  read-only
    STATUS      current
    DESCRIPTION 
        "Number of GTP-C messages containing unexpected IEs."
    ::= { ssmGTPCGlobal 1190 }

ssmGTPCUnexpectedMsgsSys OBJECT-TYPE
    SYNTAX      Counter64
    MAX-ACCESS  read-only
    STATUS      current
    DESCRIPTION 
        "Number of unexpected GTP-C messages."
    ::= { ssmGTPCGlobal 1200 }

ssmGTPCUnknownIEsSys OBJECT-TYPE
    SYNTAX      Counter64
    MAX-ACCESS  read-only
    STATUS      current
    DESCRIPTION 
        "Number of GTP-C messages containing unknown IEs."
    ::= { ssmGTPCGlobal 1210 }

ssmGTPCUnknownMsgsSys OBJECT-TYPE
    SYNTAX      Counter64
    MAX-ACCESS  read-only
    STATUS      current
    DESCRIPTION 
        "Number of unknown GTP-C messages."
    ::= { ssmGTPCGlobal 1220 }

ssmGTPCUnsupportedVerSys OBJECT-TYPE
    SYNTAX      Counter64
    MAX-ACCESS  read-only
    STATUS      current
    DESCRIPTION 
        "Number of GTP-C messages received with an unsupported version."
    ::= { ssmGTPCGlobal 1225 }

ssmGTPUGlobal OBJECT IDENTIFIER
    ::= { ssmGTP 2020 }

ssmGTPUBearersActiveSys OBJECT-TYPE
    SYNTAX      Unsigned32
    MAX-ACCESS  read-only
    STATUS      current
    DESCRIPTION 
        "Number of currently active GTP-U bearers."
    ::= { ssmGTPUGlobal 1010 }

ssmGTPUBearersCreatedSys OBJECT-TYPE
    SYNTAX      Counter64
    MAX-ACCESS  read-only
    STATUS      current
    DESCRIPTION 
        "Number of created GTP-U bearers."
    ::= { ssmGTPUGlobal 1020 }

ssmGTPUBearersDeletedSys OBJECT-TYPE
    SYNTAX      Counter64
    MAX-ACCESS  read-only
    STATUS      current
    DESCRIPTION 
        "Number of deleted GTP-U bearers."
    ::= { ssmGTPUGlobal 1030 }

ssmGTPUInvalidTunnelsSys OBJECT-TYPE
    SYNTAX      Counter64
    MAX-ACCESS  read-only
    STATUS      current
    DESCRIPTION 
        "Number of GTP-U messages received for an invalid tunnel."
    ::= { ssmGTPUGlobal 1040 }

ssmGTPUDroppedSys OBJECT-TYPE
    SYNTAX      Counter64
    MAX-ACCESS  read-only
    STATUS      current
    DESCRIPTION 
        "Number of dropped GTP-U messages."
    ::= { ssmGTPUGlobal 1050 }

ssmGTPUForwardedSys OBJECT-TYPE
    SYNTAX      Counter64
    MAX-ACCESS  read-only
    STATUS      current
    DESCRIPTION 
        "Number of forwarded GTP-U messages."
    ::= { ssmGTPUGlobal 1060 }

ssmGTPUReceivedSys OBJECT-TYPE
    SYNTAX      Counter64
    MAX-ACCESS  read-only
    STATUS      current
    DESCRIPTION 
        "Number of received GTP-U messages."
    ::= { ssmGTPUGlobal 1070 }

ssmGTPUTruncatedMsgsSys OBJECT-TYPE
    SYNTAX      Counter64
    MAX-ACCESS  read-only
    STATUS      current
    DESCRIPTION 
        "Number of received truncated GTP-U messages."
    ::= { ssmGTPUGlobal 1080 }

ssmGTPUUnknownMsgsSys OBJECT-TYPE
    SYNTAX      Counter64
    MAX-ACCESS  read-only
    STATUS      current
    DESCRIPTION 
        "Number of unknown GTP-U messages."
    ::= { ssmGTPUGlobal 1090 }

ssmGTPUUnsupportedVersionsSys OBJECT-TYPE
    SYNTAX      Counter64
    MAX-ACCESS  read-only
    STATUS      current
    DESCRIPTION 
        "Number of GTP-U messages received with an unsupported version."
    ::= { ssmGTPUGlobal 1100 }

ssmGTPUMissingMandatoryIEsSys OBJECT-TYPE
    SYNTAX      Counter64
    MAX-ACCESS  read-only
    STATUS      current
    DESCRIPTION 
        "Number of GTP-U messages with missing mandatory IEs."
    ::= { ssmGTPUGlobal 1540 }

ssmGTPUOutOfOrderIEsSys OBJECT-TYPE
    SYNTAX      Counter64
    MAX-ACCESS  read-only
    STATUS      current
    DESCRIPTION 
        "Number of GTP-U messages with out-of-order information elements."
    ::= { ssmGTPUGlobal 1550 }

ssmGTPUDuplicatedIEsSys OBJECT-TYPE
    SYNTAX      Counter64
    MAX-ACCESS  read-only
    STATUS      current
    DESCRIPTION 
        "Number of GTP-U messages with duplicated IEs."
    ::= { ssmGTPUGlobal 1560 }

ssmGTPUUnexpectedIEsSys OBJECT-TYPE
    SYNTAX      Counter64
    MAX-ACCESS  read-only
    STATUS      current
    DESCRIPTION 
        "Number of GTP-U messages with unexpected IEs."
    ::= { ssmGTPUGlobal 1570 }

ssmGTPUUnknownIEsSys OBJECT-TYPE
    SYNTAX      Counter64
    MAX-ACCESS  read-only
    STATUS      current
    DESCRIPTION 
        "Number of GTP-U messages containing unknown IEs."
    ::= { ssmGTPUGlobal 1580 }

ssmGTPInspProfilesTable OBJECT-TYPE
    SYNTAX      SEQUENCE OF SsmGTPInspProfilesEntry
    MAX-ACCESS  not-accessible
    STATUS      current
    DESCRIPTION 
        "GTP inspection profile statistics."
    ::= { ssmGTP 3010 }

ssmGTPInspProfilesEntry OBJECT-TYPE
    SYNTAX      SsmGTPInspProfilesEntry
    MAX-ACCESS  not-accessible
    STATUS      current
    DESCRIPTION 
        "The row in a table of profile statistics."
    INDEX       { ssmProfileIndex }
    ::= { ssmGTPInspProfilesTable 1 }

SsmGTPInspProfilesEntry ::= SEQUENCE {
    ssmGTPInspProfileIndex                Integer32,
    ssmGTPInspProfileName                 DisplayString,
    ssmGTPCDuplicatedIEs                  Counter64,
    ssmGTPCInvalidMandatoryIEs            Counter64,
    ssmGTPCInvalidOptionalIEs             Counter64,
    ssmGTPCMissingMandatoryIEs            Counter64,
    ssmGTPCDropped                        Counter64,
    ssmGTPCForwarded                      Counter64,
    ssmGTPCReceived                       Counter64,
    ssmGTPCV1Dropped                      Counter64,
    ssmGTPCV1Forwarded                    Counter64,
    ssmGTPCV1Received                     Counter64,
    ssmGTPCV2Dropped                      Counter64,
    ssmGTPCV2Forwarded                    Counter64,
    ssmGTPCV2Received                     Counter64,
    ssmGTPCOutOfOrderIEs                  Counter64,
    ssmGTPCSessionsActive                 Unsigned32,
    ssmGTPCSessionsCreated                Counter64,
    ssmGTPCSessionsDeleted                Counter64,
    ssmGTPCTruncatedMsgs                  Counter64,
    ssmGTPCUnexpectedIEs                  Counter64,
    ssmGTPCUnexpectedMsgs                 Counter64,
    ssmGTPCUnknownIEs                     Counter64,
    ssmGTPCUnknownMsgs                    Counter64,
    ssmGTPUDuplicatedIEs                  Counter64,
    ssmGTPUInvalidTunnels                 Counter64,
    ssmGTPUMissingMandatoryIEs            Counter64,
    ssmGTPUDropped                        Counter64,
    ssmGTPUForwarded                      Counter64,
    ssmGTPUReceived                       Counter64,
    ssmGTPUOutOfOrderIEs                  Counter64,
    ssmGTPUTruncatedMsgs                  Counter64,
    ssmGTPUUnexpectedIEs                  Counter64,
    ssmGTPUUnknownIEs                     Counter64,
    ssmGTPUUnknownMsgs                    Counter64,
    ssmGTPUUnsupportedVersions            Counter64,
    ssmGTPCUnsupportedVer                 Counter64,
    ssmGTPUBearersActive                  Unsigned32,
    ssmGTPUBearersCreated                 Counter64,
    ssmGTPUBearersDeleted                 Counter64
}

ssmGTPInspProfileIndex OBJECT-TYPE
    SYNTAX      Integer32
    MAX-ACCESS  read-only
    STATUS      current
    DESCRIPTION 
        "GTP inspection profile row index."
    ::= { ssmGTPInspProfilesEntry 1 }

ssmGTPCDuplicatedIEs OBJECT-TYPE
    SYNTAX      Counter64
    MAX-ACCESS  read-only
    STATUS      current
    DESCRIPTION 
        "Number of GTP-C messages containing duplicated IEs."
    ::= { ssmGTPInspProfilesEntry 1010 }

ssmGTPCInvalidMandatoryIEs OBJECT-TYPE
    SYNTAX      Counter64
    MAX-ACCESS  read-only
    STATUS      current
    DESCRIPTION 
        "Number of GTP-C messages containing invalid mandatory IEs."
    ::= { ssmGTPInspProfilesEntry 1020 }

ssmGTPCInvalidOptionalIEs OBJECT-TYPE
    SYNTAX      Counter64
    MAX-ACCESS  read-only
    STATUS      current
    DESCRIPTION 
        "Number of GTP-C messages containing invalid optional IEs."
    ::= { ssmGTPInspProfilesEntry 1030 }

ssmGTPCMissingMandatoryIEs OBJECT-TYPE
    SYNTAX      Counter64
    MAX-ACCESS  read-only
    STATUS      current
    DESCRIPTION 
        "Number of GTP-C messages with missing mandatory IEs."
    ::= { ssmGTPInspProfilesEntry 1040 }

ssmGTPCDropped OBJECT-TYPE
    SYNTAX      Counter64
    MAX-ACCESS  read-only
    STATUS      current
    DESCRIPTION 
        "Number of dropped GTP-C messages, including messages with
         invalid or unknown version."
    ::= { ssmGTPInspProfilesEntry 1050 }

ssmGTPCForwarded OBJECT-TYPE
    SYNTAX      Counter64
    MAX-ACCESS  read-only
    STATUS      current
    DESCRIPTION 
        "Number of forwarded GTP-C messages."
    ::= { ssmGTPInspProfilesEntry 1060 }

ssmGTPCReceived OBJECT-TYPE
    SYNTAX      Counter64
    MAX-ACCESS  read-only
    STATUS      current
    DESCRIPTION 
        "Number of received GTP-C messages, including messages with
         invalid or unknown version."
    ::= { ssmGTPInspProfilesEntry 1070 }

ssmGTPCV1Dropped OBJECT-TYPE
    SYNTAX      Counter64
    MAX-ACCESS  read-only
    STATUS      current
    DESCRIPTION 
        "Number of dropped GTPv1-C messages."
    ::= { ssmGTPInspProfilesEntry 1080 }

ssmGTPCV1Forwarded OBJECT-TYPE
    SYNTAX      Counter64
    MAX-ACCESS  read-only
    STATUS      current
    DESCRIPTION 
        "Number of forwarded GTPv1-C messages."
    ::= { ssmGTPInspProfilesEntry 1090 }

ssmGTPCV1Received OBJECT-TYPE
    SYNTAX      Counter64
    MAX-ACCESS  read-only
    STATUS      current
    DESCRIPTION 
        "Number of received GTPv1-C messages."
    ::= { ssmGTPInspProfilesEntry 1100 }

ssmGTPCV2Dropped OBJECT-TYPE
    SYNTAX      Counter64
    MAX-ACCESS  read-only
    STATUS      current
    DESCRIPTION 
        "Number of dropped GTPv2-C messages."
    ::= { ssmGTPInspProfilesEntry 1110 }

ssmGTPCV2Forwarded OBJECT-TYPE
    SYNTAX      Counter64
    MAX-ACCESS  read-only
    STATUS      current
    DESCRIPTION 
        "Number of forwarded GTPv2-C messages."
    ::= { ssmGTPInspProfilesEntry 1120 }

ssmGTPCV2Received OBJECT-TYPE
    SYNTAX      Counter64
    MAX-ACCESS  read-only
    STATUS      current
    DESCRIPTION 
        "Number of received GTPv2-C messages."
    ::= { ssmGTPInspProfilesEntry 1130 }

ssmGTPCOutOfOrderIEs OBJECT-TYPE
    SYNTAX      Counter64
    MAX-ACCESS  read-only
    STATUS      current
    DESCRIPTION 
        "Number of GTP-C messages with out-of-order IEs."
    ::= { ssmGTPInspProfilesEntry 1140 }

ssmGTPCSessionsActive OBJECT-TYPE
    SYNTAX      Unsigned32
    MAX-ACCESS  read-only
    STATUS      current
    DESCRIPTION 
        "Number of currently active GTP-C sessions."
    ::= { ssmGTPInspProfilesEntry 1150 }

ssmGTPCSessionsCreated OBJECT-TYPE
    SYNTAX      Counter64
    MAX-ACCESS  read-only
    STATUS      current
    DESCRIPTION 
        "Number of created GTP-C sessions."
    ::= { ssmGTPInspProfilesEntry 1160 }

ssmGTPCSessionsDeleted OBJECT-TYPE
    SYNTAX      Counter64
    MAX-ACCESS  read-only
    STATUS      current
    DESCRIPTION 
        "Number of deleted GTP-C sessions."
    ::= { ssmGTPInspProfilesEntry 1170 }

ssmGTPCTruncatedMsgs OBJECT-TYPE
    SYNTAX      Counter64
    MAX-ACCESS  read-only
    STATUS      current
    DESCRIPTION 
        "Number of truncated GTP-C messages (too short)."
    ::= { ssmGTPInspProfilesEntry 1180 }

ssmGTPCUnexpectedIEs OBJECT-TYPE
    SYNTAX      Counter64
    MAX-ACCESS  read-only
    STATUS      current
    DESCRIPTION 
        "Number of GTP-C messages containing unexpected IEs."
    ::= { ssmGTPInspProfilesEntry 1190 }

ssmGTPCUnexpectedMsgs OBJECT-TYPE
    SYNTAX      Counter64
    MAX-ACCESS  read-only
    STATUS      current
    DESCRIPTION 
        "Number of unexpected GTP-C messages."
    ::= { ssmGTPInspProfilesEntry 1200 }

ssmGTPCUnknownIEs OBJECT-TYPE
    SYNTAX      Counter64
    MAX-ACCESS  read-only
    STATUS      current
    DESCRIPTION 
        "Number of GTP-C messages containing unknown IEs."
    ::= { ssmGTPInspProfilesEntry 1210 }

ssmGTPCUnknownMsgs OBJECT-TYPE
    SYNTAX      Counter64
    MAX-ACCESS  read-only
    STATUS      current
    DESCRIPTION 
        "Number of unknown GTP-C messages."
    ::= { ssmGTPInspProfilesEntry 1220 }

ssmGTPUDuplicatedIEs OBJECT-TYPE
    SYNTAX      Counter64
    MAX-ACCESS  read-only
    STATUS      current
    DESCRIPTION 
        "Number of GTP-U messages with duplicated IEs."
    ::= { ssmGTPInspProfilesEntry 1230 }

ssmGTPUInvalidTunnels OBJECT-TYPE
    SYNTAX      Counter64
    MAX-ACCESS  read-only
    STATUS      current
    DESCRIPTION 
        "Number of GTP-U messages received for an invalid tunnel."
    ::= { ssmGTPInspProfilesEntry 1235 }

ssmGTPUMissingMandatoryIEs OBJECT-TYPE
    SYNTAX      Counter64
    MAX-ACCESS  read-only
    STATUS      current
    DESCRIPTION 
        "Number of GTP-U messages with missing mandatory IEs."
    ::= { ssmGTPInspProfilesEntry 1240 }

ssmGTPUDropped OBJECT-TYPE
    SYNTAX      Counter64
    MAX-ACCESS  read-only
    STATUS      current
    DESCRIPTION 
        "Number of dropped GTP-U messages."
    ::= { ssmGTPInspProfilesEntry 1245 }

ssmGTPUForwarded OBJECT-TYPE
    SYNTAX      Counter64
    MAX-ACCESS  read-only
    STATUS      current
    DESCRIPTION 
        "Number of forwarded GTP-U messages."
    ::= { ssmGTPInspProfilesEntry 1250 }

ssmGTPUReceived OBJECT-TYPE
    SYNTAX      Counter64
    MAX-ACCESS  read-only
    STATUS      current
    DESCRIPTION 
        "Number of received GTP-U messages."
    ::= { ssmGTPInspProfilesEntry 1255 }

ssmGTPUOutOfOrderIEs OBJECT-TYPE
    SYNTAX      Counter64
    MAX-ACCESS  read-only
    STATUS      current
    DESCRIPTION 
        "Number of GTP-U messages with out-of-order information elements."
    ::= { ssmGTPInspProfilesEntry 1260 }

ssmGTPUTruncatedMsgs OBJECT-TYPE
    SYNTAX      Counter64
    MAX-ACCESS  read-only
    STATUS      current
    DESCRIPTION 
        "Number of received truncated GTP-U messages."
    ::= { ssmGTPInspProfilesEntry 1265 }

ssmGTPUUnexpectedIEs OBJECT-TYPE
    SYNTAX      Counter64
    MAX-ACCESS  read-only
    STATUS      current
    DESCRIPTION 
        "Number of GTP-U messages with unexpected IEs."
    ::= { ssmGTPInspProfilesEntry 1270 }

ssmGTPUUnknownIEs OBJECT-TYPE
    SYNTAX      Counter64
    MAX-ACCESS  read-only
    STATUS      current
    DESCRIPTION 
        "Number of GTP-U messages containing unknown IEs."
    ::= { ssmGTPInspProfilesEntry 1275 }

ssmGTPUUnknownMsgs OBJECT-TYPE
    SYNTAX      Counter64
    MAX-ACCESS  read-only
    STATUS      current
    DESCRIPTION 
        "Number of unknown GTP-U messages."
    ::= { ssmGTPInspProfilesEntry 1280 }

ssmGTPUUnsupportedVersions OBJECT-TYPE
    SYNTAX      Counter64
    MAX-ACCESS  read-only
    STATUS      current
    DESCRIPTION 
        "Number of GTP-U messages received with an unsupported version."
    ::= { ssmGTPInspProfilesEntry 1285 }

ssmGTPCUnsupportedVer OBJECT-TYPE
    SYNTAX      Counter64
    MAX-ACCESS  read-only
    STATUS      current
    DESCRIPTION 
        "Number of GTP-C messages received with an unsupported version."
    ::= { ssmGTPInspProfilesEntry 1290 }

ssmGTPUBearersActive OBJECT-TYPE
    SYNTAX      Unsigned32
    MAX-ACCESS  read-only
    STATUS      current
    DESCRIPTION 
        "Number of currently active GTP-U bearers."
    ::= { ssmGTPInspProfilesEntry 1510 }

ssmGTPUBearersCreated OBJECT-TYPE
    SYNTAX      Counter64
    MAX-ACCESS  read-only
    STATUS      current
    DESCRIPTION 
        "Number of created GTP-U bearers."
    ::= { ssmGTPInspProfilesEntry 1520 }

ssmGTPUBearersDeleted OBJECT-TYPE
    SYNTAX      Counter64
    MAX-ACCESS  read-only
    STATUS      current
    DESCRIPTION 
        "Number of deleted GTP-U bearers."
    ::= { ssmGTPInspProfilesEntry 1530 }

ssmGTPInspProfileName OBJECT-TYPE
    SYNTAX      DisplayString
    MAX-ACCESS  read-only
    STATUS      current
    DESCRIPTION 
        "GTP inspection profile name."
    ::= { ssmGTPInspProfilesEntry 2 }

ssmSIP OBJECT IDENTIFIER
    ::= { ssmALG 2090 }

ssmSIPALGGlobal OBJECT IDENTIFIER
    ::= { ssmSIP 2010 }

ssmSIPALGActiveSessionsSys OBJECT-TYPE
    SYNTAX      Unsigned32
    MAX-ACCESS  read-only
    STATUS      current
    DESCRIPTION 
        "Global number of active SIP sessions."
    ::= { ssmSIPALGGlobal 1005 }

ssmSIPALGActiveMediaSessionsSys OBJECT-TYPE
    SYNTAX      Unsigned32
    MAX-ACCESS  read-only
    STATUS      current
    DESCRIPTION 
        "Global number of active media sessions."
    ::= { ssmSIPALGGlobal 1010 }

ssmSIPALGSignalErrSys OBJECT-TYPE
    SYNTAX      Unsigned32
    MAX-ACCESS  read-only
    STATUS      current
    DESCRIPTION 
        "Global number of signaling errors."
    ::= { ssmSIPALGGlobal 1015 }

ssmSIPALGSesDiscTimeoutSys OBJECT-TYPE
    SYNTAX      Unsigned32
    MAX-ACCESS  read-only
    STATUS      current
    DESCRIPTION 
        "Global number of disconnected SIP sessions due to timeout."
    ::= { ssmSIPALGGlobal 1020 }

ssmSIPALGSesDiscRegTimeoutSys OBJECT-TYPE
    SYNTAX      Unsigned32
    MAX-ACCESS  read-only
    STATUS      current
    DESCRIPTION 
        "Global number of disconnected SIP sessions due to registration
         time expiry."
    ::= { ssmSIPALGGlobal 1025 }

ssmSIPALGMediaSesDiscTimeoutSys OBJECT-TYPE
    SYNTAX      Unsigned32
    MAX-ACCESS  read-only
    STATUS      current
    DESCRIPTION 
        "Global number of disconnected SIP media sessions due to timeout."
    ::= { ssmSIPALGGlobal 1030 }

ssmSIPALGActiveRegistrationsSys OBJECT-TYPE
    SYNTAX      Unsigned32
    MAX-ACCESS  read-only
    STATUS      current
    DESCRIPTION 
        "Global number of active SIP registrations."
    ::= { ssmSIPALGGlobal 1035 }

ssmSIPALGRegistrationsSys OBJECT-TYPE
    SYNTAX      Unsigned32
    MAX-ACCESS  read-only
    STATUS      current
    DESCRIPTION 
        "Global number of successful SIP registrations."
    ::= { ssmSIPALGGlobal 1040 }

ssmSIPALGRegistrationsFailSys OBJECT-TYPE
    SYNTAX      Unsigned32
    MAX-ACCESS  read-only
    STATUS      current
    DESCRIPTION 
        "Global number of failed SIP registrations."
    ::= { ssmSIPALGGlobal 1045 }

ssmSIPALGMediaSesNegSys OBJECT-TYPE
    SYNTAX      Unsigned32
    MAX-ACCESS  read-only
    STATUS      current
    DESCRIPTION 
        "Global number of negotiated media sessions."
    ::= { ssmSIPALGGlobal 1050 }

ssmSIPALGRegHijackDropSys OBJECT-TYPE
    SYNTAX      Unsigned32
    MAX-ACCESS  read-only
    STATUS      current
    DESCRIPTION 
        "Global number of dropped registrations requests due to
         consecutive registration failure for a given To URI and
         triggering of registration hijack protection."
    ::= { ssmSIPALGGlobal 1055 }

ssmSIPALGActiveCallSessionsSys OBJECT-TYPE
    SYNTAX      Unsigned32
    MAX-ACCESS  read-only
    STATUS      current
    DESCRIPTION 
        "Global number of active call sessions, i.e. calls in confirmed
         state."
    ::= { ssmSIPALGGlobal 1060 }

ssmSIPALGProfilesTable OBJECT-TYPE
    SYNTAX      SEQUENCE OF SsmSIPALGProfilesEntry
    MAX-ACCESS  not-accessible
    STATUS      current
    DESCRIPTION 
        "SIPALG profile statistics."
    ::= { ssmSIP 3010 }

ssmSIPALGProfilesEntry OBJECT-TYPE
    SYNTAX      SsmSIPALGProfilesEntry
    MAX-ACCESS  not-accessible
    STATUS      current
    DESCRIPTION 
        "The row in a table of profile statistics."
    INDEX       { ssmProfileIndex }
    ::= { ssmSIPALGProfilesTable 1 }

SsmSIPALGProfilesEntry ::= SEQUENCE {
    ssmSIPALGIndex                       Integer32,
    ssmSIPALGName                        DisplayString,
    ssmSIPALGActiveSessions              Unsigned32,
    ssmSIPALGActiveMediaSessions         Unsigned32,
    ssmSIPALGSignalErr                   Unsigned32,
    ssmSIPALGSesDiscTimeout              Unsigned32,
    ssmSIPALGSesDiscRegTimeout           Unsigned32,
    ssmSIPALGMediaSesDiscTimeout         Unsigned32,
    ssmSIPALGActiveRegistrations         Unsigned32,
    ssmSIPALGRegistrations               Unsigned32,
    ssmSIPALGRegistrationsFail           Unsigned32,
    ssmSIPALGMediaSesNeg                 Unsigned32,
    ssmSIPALGRegHijackDrop               Unsigned32,
    ssmSIPALGActiveCallSessions          Unsigned32
}

ssmSIPALGIndex OBJECT-TYPE
    SYNTAX      Integer32
    MAX-ACCESS  read-only
    STATUS      current
    DESCRIPTION 
        "SIPALG profile row index."
    ::= { ssmSIPALGProfilesEntry 1 }

ssmSIPALGActiveSessions OBJECT-TYPE
    SYNTAX      Unsigned32
    MAX-ACCESS  read-only
    STATUS      current
    DESCRIPTION 
        "Number of active SIP sessions."
    ::= { ssmSIPALGProfilesEntry 1005 }

ssmSIPALGActiveMediaSessions OBJECT-TYPE
    SYNTAX      Unsigned32
    MAX-ACCESS  read-only
    STATUS      current
    DESCRIPTION 
        "Number of active media sessions."
    ::= { ssmSIPALGProfilesEntry 1010 }

ssmSIPALGSignalErr OBJECT-TYPE
    SYNTAX      Unsigned32
    MAX-ACCESS  read-only
    STATUS      current
    DESCRIPTION 
        "Number of signaling errors."
    ::= { ssmSIPALGProfilesEntry 1015 }

ssmSIPALGSesDiscTimeout OBJECT-TYPE
    SYNTAX      Unsigned32
    MAX-ACCESS  read-only
    STATUS      current
    DESCRIPTION 
        "Number of disconnected SIP sessions due to timeout."
    ::= { ssmSIPALGProfilesEntry 1020 }

ssmSIPALGSesDiscRegTimeout OBJECT-TYPE
    SYNTAX      Unsigned32
    MAX-ACCESS  read-only
    STATUS      current
    DESCRIPTION 
        "Number of disconnected SIP sessions due to registration time
         expiry."
    ::= { ssmSIPALGProfilesEntry 1025 }

ssmSIPALGMediaSesDiscTimeout OBJECT-TYPE
    SYNTAX      Unsigned32
    MAX-ACCESS  read-only
    STATUS      current
    DESCRIPTION 
        "Number of disconnected SIP media sessions due to timeout."
    ::= { ssmSIPALGProfilesEntry 1030 }

ssmSIPALGActiveRegistrations OBJECT-TYPE
    SYNTAX      Unsigned32
    MAX-ACCESS  read-only
    STATUS      current
    DESCRIPTION 
        "Number of active SIP registrations."
    ::= { ssmSIPALGProfilesEntry 1035 }

ssmSIPALGRegistrations OBJECT-TYPE
    SYNTAX      Unsigned32
    MAX-ACCESS  read-only
    STATUS      current
    DESCRIPTION 
        "Number of successful SIP registrations."
    ::= { ssmSIPALGProfilesEntry 1040 }

ssmSIPALGRegistrationsFail OBJECT-TYPE
    SYNTAX      Unsigned32
    MAX-ACCESS  read-only
    STATUS      current
    DESCRIPTION 
        "Number of failed SIP registrations."
    ::= { ssmSIPALGProfilesEntry 1045 }

ssmSIPALGMediaSesNeg OBJECT-TYPE
    SYNTAX      Unsigned32
    MAX-ACCESS  read-only
    STATUS      current
    DESCRIPTION 
        "Number of negotiated media sessions."
    ::= { ssmSIPALGProfilesEntry 1050 }

ssmSIPALGRegHijackDrop OBJECT-TYPE
    SYNTAX      Unsigned32
    MAX-ACCESS  read-only
    STATUS      current
    DESCRIPTION 
        "Number of dropped registrations requests due to consecutive
         registration failure for a given To URI and triggering of
         registration hijack protection."
    ::= { ssmSIPALGProfilesEntry 1055 }

ssmSIPALGActiveCallSessions OBJECT-TYPE
    SYNTAX      Unsigned32
    MAX-ACCESS  read-only
    STATUS      current
    DESCRIPTION 
        "Number of active call sessions, i.e. calls in confirmed state."
    ::= { ssmSIPALGProfilesEntry 1060 }

ssmSIPALGName OBJECT-TYPE
    SYNTAX      DisplayString
    MAX-ACCESS  read-only
    STATUS      current
    DESCRIPTION 
        "SIPALG profile name."
    ::= { ssmSIPALGProfilesEntry 2 }

clavisterStatsConformance OBJECT IDENTIFIER
    ::= { clavisterMibConfs 1 }

clavisterSystemStatsGroups OBJECT IDENTIFIER
    ::= { clavisterMibObjectGroups 2 }

ssmARPGroup OBJECT-GROUP
    OBJECTS     { 
                  ssmProxiedReplies }
    STATUS      current
    DESCRIPTION
        "ARP statistics."
    ::= { clavisterSystemStatsGroups 11 }

ssmAdminParametersGroup OBJECT-GROUP
    OBJECTS     { 
                  ssmDateOfLastService,
                  ssmManagementIPAddressList,
                  ssmServiceIPAddressList,
                  ssmUserDefinedState }
    STATUS      current
    DESCRIPTION
        "Management information for structured management of the system."
    ::= { clavisterSystemStatsGroups 52 }

ssmAppCtrlStatsGroup OBJECT-GROUP
    OBJECTS     { 
                  ssmAppCtrlAppName,
                  ssmAppCtrlAppIdentified,
                  ssmAppCtrlAppBytes,
                  ssmAppCtrlAppPkts }
    STATUS      current
    DESCRIPTION
        "Application statistics."
    ::= { clavisterSystemStatsGroups 94 }

ssmApplicationControlGroup OBJECT-GROUP
    OBJECTS     { 
                  ssmAppCtrlAnalyzedBytes,
                  ssmAppCtrlAnalyzedPkts,
                  ssmAppCtrlApps,
                  ssmAppCtrlFlowsActive,
                  ssmAppCtrlFlowsClassified,
                  ssmAppCtrlFlowsUnclassified,
                  ssmAppCtrlReclassifications,
                  ssmAppCtrlTotBytes,
                  ssmAppCtrlTotPkts,
                  ssmAppCtrlUnclBytes,
                  ssmAppCtrlUnclPkts }
    STATUS      current
    DESCRIPTION
        "Application control statistics."
    ::= { clavisterSystemStatsGroups 95 }

ssmAuthProfilesGroup OBJECT-GROUP
    OBJECTS     { 
                  ssmActiveEapAkaUsers,
                  ssmActiveEapMd5Users,
                  ssmActiveEapSimUsers,
                  ssmActiveUsers,
                  ssmBruteForceAttacks,
                  ssmAuthsFailed,
                  ssmUserIdleTimeouts,
                  ssmAuthsRejected,
                  ssmRejectedUsername,
                  ssmReplacedUsers,
                  ssmUserSessionTimeouts,
                  ssmProfileSourceTimeouts,
                  ssmAuthsStarted,
                  ssmAuthsSucceeded,
                  ssmAuthsEapAkaSucceeded,
                  ssmAuthsEapMd5Succeeded,
                  ssmAuthsEapSimSucceeded,
                  ssmProfileName }
    STATUS      current
    DESCRIPTION
        "Authentication profile statistics."
    ::= { clavisterSystemStatsGroups 17 }

ssmAuthenticationSystemGroup OBJECT-GROUP
    OBJECTS     { 
                  ssmSysActiveEapAkaUsers,
                  ssmSysActiveEapMd5Users,
                  ssmSysActiveEapSimUsers,
                  ssmSysActiveUsers,
                  ssmSysBruteForceAttacks,
                  ssmSysAuthsFailed,
                  ssmSysUserIdleTimeouts,
                  ssmSysAuthsRejected,
                  ssmSysRejectedUsername,
                  ssmSysReplacedUsers,
                  ssmSysUserSessionTimeouts,
                  ssmSysSourceTimeouts,
                  ssmSysAuthsStarted,
                  ssmSysAuthsSucceeded,
                  ssmSysAuthsEapAkaSucceeded,
                  ssmSysAuthsEapMd5Succeeded,
                  ssmSysAuthsEapSimSucceeded }
    STATUS      current
    DESCRIPTION
        "System statistics."
    ::= { clavisterSystemStatsGroups 14 }

ssmBlacklistGroup OBJECT-GROUP
    OBJECTS     { 
                  ssmMaxBlacklistEntries,
                  ssmBlacklistRules,
                  ssmBlacklistPacketsDropped,
                  ssmWhitelistFlowsAllowed,
                  ssmWhitelistRules }
    STATUS      current
    DESCRIPTION
        "Global blacklist statistics module."
    ::= { clavisterSystemStatsGroups 56 }

ssmCLILogGroup OBJECT-GROUP
    OBJECTS     { 
                  ssmCLILogIPCFail,
                  ssmCLILogMemAllocFail,
                  ssmCLILogThrottled,
                  ssmCLILogSent }
    STATUS      current
    DESCRIPTION
        "CLI log statistics."
    ::= { clavisterSystemStatsGroups 38 }

ssmCPUGroup OBJECT-GROUP
    OBJECTS     { 
                  ssmCtrlPlaneCpuUsage,
                  ssmCtrlPlaneCpuAverage,
                  ssmCtrlPlaneCpuMax,
                  ssmFastPathCpuUsage,
                  ssmFastPathCpuAverage,
                  ssmFastPathCpuMax,
                  ssmSlowPathCpuUsage,
                  ssmSlowPathCpuAverage,
                  ssmSlowPathCpuMax,
                  ssmWorkerCpuUsage,
                  ssmWorkerCpuAverage,
                  ssmWorkerCpuMax }
    STATUS      current
    DESCRIPTION
        "CPU statistics."
    ::= { clavisterSystemStatsGroups 8 }

ssmCpuStatsGroup OBJECT-GROUP
    OBJECTS     { 
                  ssmCpuName,
                  ssmCpuUsage }
    STATUS      current
    DESCRIPTION
        "CPU statistics table."
    ::= { clavisterSystemStatsGroups 20 }

ssmCryptoDeviceGroup OBJECT-GROUP
    OBJECTS     { 
                  ssmCryptoDeviceIsOnline,
                  ssmCryptoDeviceName,
                  ssmCryptoDeviceSymAuthFails,
                  ssmCryptoDeviceSymDecryptFails,
                  ssmCryptoDeviceSymDecrypts,
                  ssmCryptoDeviceSymEncryptFails,
                  ssmCryptoDeviceSymEncrypts,
                  ssmCryptoDeviceSymInFlight,
                  ssmCryptoDeviceSymSessionFails,
                  ssmCryptoDeviceSymSessions }
    STATUS      current
    DESCRIPTION
        "Crypto device statistics."
    ::= { clavisterSystemStatsGroups 51 }

ssmDHCPClientGroup OBJECT-GROUP
    OBJECTS     { 
                  ssmDHCPClientAcksReceived,
                  ssmDHCPClientAddressAge,
                  ssmDHCPClientDeclinesSent,
                  ssmDHCPClientDiscoveriesResent,
                  ssmDHCPClientDiscoveriesSent,
                  ssmDHCPClientIfaceName,
                  ssmDHCPClientLeaseAquired,
                  ssmDHCPClientLeaseTTL,
                  ssmDHCPClientLeaseTimeTotal,
                  ssmDHCPClientLeaseTimeUsed,
                  ssmDHCPClientNacksReceived,
                  ssmDHCPClientOffersReceived,
                  ssmDHCPClientReleasesSent,
                  ssmDHCPClientRequestsResent,
                  ssmDHCPClientRequestsSent,
                  ssmDHCPClientState }
    STATUS      current
    DESCRIPTION
        "DHCP Client Table."
    ::= { clavisterSystemStatsGroups 54 }

ssmDHCPServerGroup OBJECT-GROUP
    OBJECTS     { 
                  ssmDHCPServerRejected }
    STATUS      current
    DESCRIPTION
        "DHCP Server."
    ::= { clavisterSystemStatsGroups 23 }

ssmDHCPServerRuleGroup OBJECT-GROUP
    OBJECTS     { 
                  ssmDHCPServerRuleIpPool,
                  ssmDHCPServerRuleActiveClients,
                  ssmDHCPServerRuleActiveClientsP,
                  ssmDHCPServerRuleName,
                  ssmDHCPServerRulePoolSize,
                  ssmDHCPServerRuleRejected,
                  ssmDHCPServerRuleUsage,
                  ssmDHCPServerRuleUsageP }
    STATUS      current
    DESCRIPTION
        "DHCP Server Table."
    ::= { clavisterSystemStatsGroups 24 }

ssmDNSGroup OBJECT-GROUP
    OBJECTS     { 
                  ssmDNSALGFwdQueriesSys,
                  ssmDNSALGFwdResponsesSys,
                  ssmDNSALGMalformedClientMsgsSys,
                  ssmDNSALGMalformedServerMsgsSys,
                  ssmDNSALGDroppedClientMsgsSys,
                  ssmDNSALGDroppedServerMsgsSys,
                  ssmDNSALGTranslationsSys,
                  ssmDNSALGSessionsCurrentSys,
                  ssmDNSALGSessionsTotalSys }
    STATUS      current
    DESCRIPTION
        "DNS ALG."
    ::= { clavisterSystemStatsGroups 67 }

ssmDNSALGProfilesGroup OBJECT-GROUP
    OBJECTS     { 
                  ssmDNSALGProfileIndex,
                  ssmDNSALGProfileName,
                  ssmDNSALGFwdQueries,
                  ssmDNSALGFwdResponses,
                  ssmDNSALGMalformedClientMsgs,
                  ssmDNSALGMalformedServerMsgs,
                  ssmDNSALGDroppedClientMsgs,
                  ssmDNSALGDroppedServerMsgs,
                  ssmDNSALGTranslations,
                  ssmDNSALGSessionsCurrent,
                  ssmDNSALGSessionsTotal }
    STATUS      current
    DESCRIPTION
        "DNSALG profile statistics."
    ::= { clavisterSystemStatsGroups 68 }

ssmFTPGroup OBJECT-GROUP
    OBJECTS     { 
                  ssmFTPALGCmdRateExceededSystem,
                  ssmFTPALGDataChannelsCurrSystem,
                  ssmFTPALGDataChannelsTotalSystem,
                  ssmFTPALGSessionsCurrentSystem,
                  ssmFTPALGSessionsTotalSystem,
                  ssmFTPALGUnknownCmdsSystem }
    STATUS      current
    DESCRIPTION
        "FTP ALG."
    ::= { clavisterSystemStatsGroups 58 }

ssmFTPALGProfilesGroup OBJECT-GROUP
    OBJECTS     { 
                  ssmFTPALGProfileIndex,
                  ssmFTPALGProfileName,
                  ssmFTPALGCmdRateExceeded,
                  ssmFTPALGDataChannelsCurrent,
                  ssmFTPALGDataChannelsTotal,
                  ssmFTPALGSessionsCurrent,
                  ssmFTPALGSessionsTotal,
                  ssmFTPALGUnknownCmds }
    STATUS      current
    DESCRIPTION
        "FTPALG profile statistics."
    ::= { clavisterSystemStatsGroups 59 }

ssmFlowGroup OBJECT-GROUP
    OBJECTS     { 
                  ssmFlowsClosed,
                  ssmFlowsCurrent,
                  ssmFlowsIPv4,
                  ssmFlowsIPv6,
                  ssmFlowLimit,
                  ssmFlowsOpened,
                  ssmFlowsReplaced }
    STATUS      current
    DESCRIPTION
        "Flow statistics."
    ::= { clavisterSystemStatsGroups 39 }

ssmGTPIfStatsGroup OBJECT-GROUP
    OBJECTS     { 
                  ssmGTPCIfActiveNegotiations,
                  ssmGTPCIfDetectedGTPSrvRestarts,
                  ssmGTPCIfFailedNegotiations,
                  ssmGTPCIfFailedSends,
                  ssmGTPCIfGTPSrvInitiatedDeletes,
                  ssmGTPCIfGTPCTunnels,
                  ssmGTPCIfIKEInitiatedDeletes,
                  ssmGTPCIfInvalidLengthIEs,
                  ssmGTPCIfInvalidMandatoryIEs,
                  ssmGTPCIfInvalidOptionalIEs,
                  ssmGTPCIfMissingMandatoryIEs,
                  ssmGTPCIfOutOfSequenceIEs,
                  ssmGTPCIfRetriesSent,
                  ssmGTPCIfClientInitiatedDeletes,
                  ssmGTPCIfTruncatedMsgs,
                  ssmGTPCIfUnexpectedMsgs,
                  ssmGTPCIfUnknownIEs,
                  ssmGTPCIfUnknownMsgs,
                  ssmGTPUIfGTPUTunnels,
                  ssmGTPUIfInvalidSeqNum,
                  ssmGTPUIfInvalidTunnels,
                  ssmGTPUIfTruncatedMsgs,
                  ssmGTPUIfUnsupportedExtHdr,
                  ssmGTPUIfUnsupportedMsgType,
                  ssmGTPUIfUnsupportedVer,
                  ssmGTPIfName }
    STATUS      current
    DESCRIPTION
        "GTP statistics."
    ::= { clavisterSystemStatsGroups 13 }

ssmGTPCGlobalGroup OBJECT-GROUP
    OBJECTS     { 
                  ssmGTPCDuplicatedIEsSys,
                  ssmGTPCInvalidMandatoryIEsSys,
                  ssmGTPCInvalidOptionalIEsSys,
                  ssmGTPCMissingMandatoryIEsSys,
                  ssmGTPCV1DroppedSys,
                  ssmGTPCV2DroppedSys,
                  ssmGTPCDroppedSys,
                  ssmGTPCV1ForwardedSys,
                  ssmGTPCV2ForwardedSys,
                  ssmGTPCForwardedSys,
                  ssmGTPCV1ReceivedSys,
                  ssmGTPCV2ReceivedSys,
                  ssmGTPCReceivedSys,
                  ssmGTPCOutOfOrderIEsSys,
                  ssmGTPCSessionsActiveSys,
                  ssmGTPCSessionsCreatedSys,
                  ssmGTPCSessionsDeletedSys,
                  ssmGTPCTruncatedMsgsSys,
                  ssmGTPCUnexpectedIEsSys,
                  ssmGTPCUnexpectedMsgsSys,
                  ssmGTPCUnknownIEsSys,
                  ssmGTPCUnknownMsgsSys,
                  ssmGTPCUnsupportedVerSys }
    STATUS      current
    DESCRIPTION
        "GTPC global statistics."
    ::= { clavisterSystemStatsGroups 91 }

ssmGTPUGlobalGroup OBJECT-GROUP
    OBJECTS     { 
                  ssmGTPUBearersActiveSys,
                  ssmGTPUBearersCreatedSys,
                  ssmGTPUBearersDeletedSys,
                  ssmGTPUDuplicatedIEsSys,
                  ssmGTPUInvalidTunnelsSys,
                  ssmGTPUMissingMandatoryIEsSys,
                  ssmGTPUDroppedSys,
                  ssmGTPUForwardedSys,
                  ssmGTPUReceivedSys,
                  ssmGTPUOutOfOrderIEsSys,
                  ssmGTPUTruncatedMsgsSys,
                  ssmGTPUUnexpectedIEsSys,
                  ssmGTPUUnknownIEsSys,
                  ssmGTPUUnknownMsgsSys,
                  ssmGTPUUnsupportedVersionsSys }
    STATUS      current
    DESCRIPTION
        "GTPU global statistics."
    ::= { clavisterSystemStatsGroups 92 }

ssmGTPInspProfilesGroup OBJECT-GROUP
    OBJECTS     { 
                  ssmGTPInspProfileIndex,
                  ssmGTPInspProfileName,
                  ssmGTPCDuplicatedIEs,
                  ssmGTPCInvalidMandatoryIEs,
                  ssmGTPCInvalidOptionalIEs,
                  ssmGTPCMissingMandatoryIEs,
                  ssmGTPCDropped,
                  ssmGTPCV1Dropped,
                  ssmGTPCV2Dropped,
                  ssmGTPCForwarded,
                  ssmGTPCV1Forwarded,
                  ssmGTPCV2Forwarded,
                  ssmGTPCReceived,
                  ssmGTPCV1Received,
                  ssmGTPCV2Received,
                  ssmGTPCOutOfOrderIEs,
                  ssmGTPCSessionsActive,
                  ssmGTPCSessionsCreated,
                  ssmGTPCSessionsDeleted,
                  ssmGTPCTruncatedMsgs,
                  ssmGTPCUnexpectedIEs,
                  ssmGTPCUnexpectedMsgs,
                  ssmGTPCUnknownIEs,
                  ssmGTPCUnknownMsgs,
                  ssmGTPCUnsupportedVer,
                  ssmGTPUBearersActive,
                  ssmGTPUBearersCreated,
                  ssmGTPUBearersDeleted,
                  ssmGTPUDuplicatedIEs,
                  ssmGTPUInvalidTunnels,
                  ssmGTPUMissingMandatoryIEs,
                  ssmGTPUDropped,
                  ssmGTPUForwarded,
                  ssmGTPUReceived,
                  ssmGTPUOutOfOrderIEs,
                  ssmGTPUTruncatedMsgs,
                  ssmGTPUUnexpectedIEs,
                  ssmGTPUUnknownIEs,
                  ssmGTPUUnknownMsgs,
                  ssmGTPUUnsupportedVersions }
    STATUS      current
    DESCRIPTION
        "GTP inspection profile statistics."
    ::= { clavisterSystemStatsGroups 93 }

ssmHAGroup OBJECT-GROUP
    OBJECTS     { 
                  ssmHASentConfigurations,
                  ssmHAElapsedTimeActive,
                  ssmHAElapsedTimeInactive,
                  ssmHAPeerUptime,
                  ssmHATimeStatusChange,
                  ssmHAHbeatTimeslotsMissed,
                  ssmHAHbeatInterval,
                  ssmHAIsActive,
                  ssmHAMessagesRecv,
                  ssmHAMessagesResent,
                  ssmHAMessagesSent,
                  ssmHANumFailovers,
                  ssmHANumHandovers,
                  ssmHAObjectCount,
                  ssmHAObjectsNotSynched,
                  ssmHAReservedBuffersFree,
                  ssmHAReservedBuffersTotal }
    STATUS      current
    DESCRIPTION
        "High Availability statistics."
    ::= { clavisterSystemStatsGroups 26 }

ssmHAFailuresGroup OBJECT-GROUP
    OBJECTS     { 
                  ssmHAFailureCurrent,
                  ssmHAFailureTotal,
                  ssmHAFailureCategory }
    STATUS      current
    DESCRIPTION
        "High Availability interface statistics."
    ::= { clavisterSystemStatsGroups 34 }

ssmHAFlowGroup OBJECT-GROUP
    OBJECTS     { 
                  ssmHAFlowNotSynced,
                  ssmHAFlowSyncFailed,
                  ssmHAFlowSynced,
                  ssmHAFlowSyncing }
    STATUS      current
    DESCRIPTION
        "HA flow statistics."
    ::= { clavisterSystemStatsGroups 33 }

ssmHAFragGroup OBJECT-GROUP
    OBJECTS     { 
                  ssmHAFragReassTimeout,
                  ssmHAFragRecv,
                  ssmHAFragRecvOK,
                  ssmHAFragReassFail,
                  ssmHAFragFragsReassOK,
                  ssmHAFragNumLocalReassFail,
                  ssmHAFragNumNoReassBuf }
    STATUS      current
    DESCRIPTION
        "HA fragmentation statistics."
    ::= { clavisterSystemStatsGroups 36 }

ssmHAIfStatsGroup OBJECT-GROUP
    OBJECTS     { 
                  ssmHAIfName,
                  ssmHAIfHeartbeatsSendFail,
                  ssmHAIfHeartbeatsRecv,
                  ssmHAIfHeartbeatsSent,
                  ssmHAIfDownCount,
                  ssmHAIfEarlyDownCount,
                  ssmHAIfHeartbeatsMissed }
    STATUS      current
    DESCRIPTION
        "High Availability interface statistics."
    ::= { clavisterSystemStatsGroups 35 }

ssmHAIntDepGroup OBJECT-GROUP
    OBJECTS     { 
                  ssmHAIntDepDelayedResolved,
                  ssmHAIntDepDirectResolved,
                  ssmHAIntDepDropped,
                  ssmHAIntDepReplaced,
                  ssmHAIntDepTimeout }
    STATUS      current
    DESCRIPTION
        "High Availability dependency system statistics."
    ::= { clavisterSystemStatsGroups 31 }

ssmHAInternalGroup OBJECT-GROUP
    OBJECTS     { 
                  ssmHAIntHBDelay,
                  ssmHAIntMessagesToCtrlPlane }
    STATUS      current
    DESCRIPTION
        "High Availability troubleshooting statistics."
    ::= { clavisterSystemStatsGroups 30 }

ssmHAModulesGroup OBJECT-GROUP
    OBJECTS     { 
                  ssmHAModName,
                  ssmHAModRecvAcks,
                  ssmHAModRecvNAcks,
                  ssmHAModMessageTokens,
                  ssmHAModMessagesRecv,
                  ssmHAModMessagesResent,
                  ssmHAModMessagesSent,
                  ssmHAModMessagesThrottled,
                  ssmHAModObjectQueries,
                  ssmHAModObjectCount,
                  ssmHAModRecreatedRequests }
    STATUS      current
    DESCRIPTION
        "High Availability module statistics."
    ::= { clavisterSystemStatsGroups 32 }

ssmHWSensorGroup OBJECT-GROUP
    OBJECTS     { 
                  ssmHWSensorHighCount,
                  ssmHWSensorHighest,
                  ssmHWSensorLowCount,
                  ssmHWSensorLowest,
                  ssmHWSensorName,
                  ssmHWSensorStatus,
                  ssmHWSensorType,
                  ssmHWSensorUnitType,
                  ssmHWSensorValue }
    STATUS      current
    DESCRIPTION
        "Sensor monitoring table."
    ::= { clavisterSystemStatsGroups 53 }

ssmIKEv1GlobalGroup OBJECT-GROUP
    OBJECTS     { 
                  ssmDPDDeletedIKEv1SAs,
                  ssmIKEv1BytesRecv,
                  ssmIKEv1BytesSent,
                  ssmIKEv1IKENegsActive,
                  ssmIKEv1IKENegsCompleted,
                  ssmIKEv1IKENegsFailed,
                  ssmIKEv1PacketsRecv,
                  ssmIKEv1PacketsResent,
                  ssmIKEv1PacketsSent,
                  ssmIKEv1IKERekeysActive,
                  ssmIKEv1IKERekeysCompleted,
                  ssmIKEv1IKERekeysFailed,
                  ssmIKEv1IKESAsActive,
                  ssmIKEv1IPsecNegsActive,
                  ssmIKEv1IPsecNegsCompleted,
                  ssmIKEv1IPsecNegsFailed,
                  ssmIKEv1IPsecRekeysActive,
                  ssmIKEv1IPsecRekeysCompleted,
                  ssmIKEv1IPsecRekeysFailed,
                  ssmIKEv1IPsecSAsActive,
                  ssmTimedOutIKEv1Negs }
    STATUS      current
    DESCRIPTION
        "IKEv1 statistics."
    ::= { clavisterSystemStatsGroups 25 }

ssmIKEv2GlobalGroup OBJECT-GROUP
    OBJECTS     { 
                  ssmDPDDeletedSAs,
                  ssmIKEBytesRecv,
                  ssmIKEBytesSent,
                  ssmIKEv2IKENegsActive,
                  ssmIKEv2IKENegsCompleted,
                  ssmIKEv2IKENegsFailed,
                  ssmIKEPacketsRecv,
                  ssmIKEPacketsResent,
                  ssmIKEPacketsSent,
                  ssmIKEv2IKERekeysActive,
                  ssmIKEv2IKERekeysCompleted,
                  ssmIKEv2IKERekeysFailed,
                  ssmIKEv2IKESAsActive,
                  ssmIKEv2IPsecNegsActive,
                  ssmIKEv2IPsecNegsCompleted,
                  ssmIKEv2IPsecNegsFailed,
                  ssmIKEv2IPsecRekeysActive,
                  ssmIKEv2IPsecRekeysCompleted,
                  ssmIKEv2IPsecRekeysFailed,
                  ssmIKEv2IPsecSAsActive,
                  ssmTimedOutNegs }
    STATUS      current
    DESCRIPTION
        "IKEv2 statistics."
    ::= { clavisterSystemStatsGroups 15 }

ssmIPRuleSetGroup OBJECT-GROUP
    OBJECTS     { 
                  ssmIPRuleSetName }
    STATUS      current
    DESCRIPTION
        "IP RuleSet statistics table."
    ::= { clavisterSystemStatsGroups 71 }

ssmIPRuleStatsGroup OBJECT-GROUP
    OBJECTS     { 
                  ssmIPRuleLastReset,
                  ssmIPRuleMatched,
                  ssmIPRuleName }
    STATUS      current
    DESCRIPTION
        "IP rule statistics table."
    ::= { clavisterSystemStatsGroups 72 }

ssmIPSGroup OBJECT-GROUP
    OBJECTS     { 
                  ssmIPSDoubleEncodingURL,
                  ssmIPSFlowsScanned,
                  ssmIPSInspectionErrors,
                  ssmIPSInvalidHEXURL,
                  ssmIPSInvalidUTF8URL,
                  ssmIPSCustomSignatures,
                  ssmIPSRejectedSignatures,
                  ssmIPSVendorSignatures,
                  ssmIPSScanLimitExceeded,
                  ssmIPSSignatureDBDate,
                  ssmIPSSignatureDBVersion,
                  ssmIPSThreatsDetected,
                  ssmIPSThreatsProtected }
    STATUS      current
    DESCRIPTION
        "Intrusion prevention system."
    ::= { clavisterSystemStatsGroups 75 }

ssmIPSRuleStatsGroup OBJECT-GROUP
    OBJECTS     { 
                  ssmIPSRuleLastReset,
                  ssmIPSRuleMatchName,
                  ssmIPSRuleMatched }
    STATUS      current
    DESCRIPTION
        "IPS rule statistics table."
    ::= { clavisterSystemStatsGroups 77 }

ssmIPSRulesGroup OBJECT-GROUP
    OBJECTS     { 
                  ssmIPSRuleDoubleEncodingURL,
                  ssmIPSRuleInspectionErrors,
                  ssmIPSRuleInvalidHEXURL,
                  ssmIPSRuleInvalidUTF8URL,
                  ssmIPSRuleScanLimitExceeded,
                  ssmIPSRuleThreatsDetected,
                  ssmIPSRuleThreatsProtected,
                  ssmIPSRuleSignaturesUsed,
                  ssmIPSRuleName,
                  ssmIPSRuleSignaturesSelected }
    STATUS      current
    DESCRIPTION
        "IPS per rule statistics."
    ::= { clavisterSystemStatsGroups 76 }

ssmIPsecIfStatsGroup OBJECT-GROUP
    OBJECTS     { 
                  ssmIPsecIfAntiReplayFails,
                  ssmIPsecIfBlockLenFails,
                  ssmIPsecIfDecryptFails,
                  ssmIPsecIfDummyPackets,
                  ssmIPsecIfEncryptFails,
                  ssmIPsecIfICVMismatches,
                  ssmIPsecIfNHMismatches,
                  ssmIPsecIfName,
                  ssmIPsecIfPadMismatches,
                  ssmIPsecIfRuntPackets,
                  ssmIPsecIfSeqOverflows }
    STATUS      current
    DESCRIPTION
        "IPsec interface statistics."
    ::= { clavisterSystemStatsGroups 9 }

ssmIfStatsGroup OBJECT-GROUP
    OBJECTS     { 
                  ssmIfAddress,
                  ssmIfBytesRecv,
                  ssmIfBytesSent,
                  ssmIfFragReassFail,
                  ssmIfFragsRecv,
                  ssmIfFragReassOK,
                  ssmIfIpv6BytesRecv,
                  ssmIfIpv6BytesSent,
                  ssmIfIpv6PktsRecv,
                  ssmIfIpv6PktsSent,
                  ssmIfMCastPktsRecv,
                  ssmIfMCastPktsSent,
                  ssmIfPktsDropped,
                  ssmIfPktsRecv,
                  ssmIfPktsSent,
                  ssmIfSendFails,
                  ssmIfName,
                  ssmIfDescription }
    STATUS      current
    DESCRIPTION
        "Interfaces statistics."
    ::= { clavisterSystemStatsGroups 5 }

ssmIfaceGlobalGroup OBJECT-GROUP
    OBJECTS     { 
                  ssmFragsReassTimeout,
                  ssmFragsRecv,
                  ssmFragsRecvOk,
                  ssmFragsReassFail,
                  ssmFragsReassOK }
    STATUS      current
    DESCRIPTION
        "Global interface statistics."
    ::= { clavisterSystemStatsGroups 19 }

ssmLogReceiverGroup OBJECT-GROUP
    OBJECTS     { 
                  ssmLogReceiverLogsFailed,
                  ssmLogReceiverName,
                  ssmLogReceiverLogsSent,
                  ssmLogReceiverLogsThrottled,
                  ssmLogReceiverType }
    STATUS      current
    DESCRIPTION
        "Log receiver statistics."
    ::= { clavisterSystemStatsGroups 96 }

ssmLogsGroup OBJECT-GROUP
    OBJECTS     { 
                  ssmLogsFromControlPlane,
                  ssmLogsFromDataPlane }
    STATUS      current
    DESCRIPTION
        "Log statistics."
    ::= { clavisterSystemStatsGroups 41 }

ssmMemCatGroup OBJECT-GROUP
    OBJECTS     { 
                  ssmMemCatCtrlPlaneUsage,
                  ssmMemCatDataPlaneUsage,
                  ssmMemCatName }
    STATUS      current
    DESCRIPTION
        "Memory statistics for memory categories."
    ::= { clavisterSystemStatsGroups 1 }

ssmMemProcessGroup OBJECT-GROUP
    OBJECTS     { 
                  ssmMemProcessName,
                  ssmMemProcessUsage }
    STATUS      current
    DESCRIPTION
        "Memory statistics for Control Plane processes."
    ::= { clavisterSystemStatsGroups 3 }

ssmMemoryGroup OBJECT-GROUP
    OBJECTS     { 
                  ssmCtrlPlaneMemFree,
                  ssmCtrlPlaneMemRegistered,
                  ssmCtrlPlaneMemTot,
                  ssmCtrlPlaneMemUsage,
                  ssmDataPlaneMemFree,
                  ssmDataPlaneMemRegistered,
                  ssmDataPlaneMemTot,
                  ssmDataPlaneMemUsage }
    STATUS      current
    DESCRIPTION
        "Memory statistics."
    ::= { clavisterSystemStatsGroups 16 }

ssmNATPoolGroup OBJECT-GROUP
    OBJECTS     { 
                  ssmNATPoolAvgFlowsPerDetBlckSCTP,
                  ssmNATPoolAvgFlowsPerDetBlockTCP,
                  ssmNATPoolAvgFlowsPerDetBlockUDP,
                  ssmNATPoolAvgFlowsPerDynBlckSCTP,
                  ssmNATPoolAvgFlowsPerDynBlockTCP,
                  ssmNATPoolAvgFlowsPerDynBlockUDP,
                  ssmNATPoolDetBlockDepletdCtrSCTP,
                  ssmNATPoolDetBlockDepletedCtrTCP,
                  ssmNATPoolDetBlockDepletedCtrUDP,
                  ssmNATPoolDetBlocksFreeSCTP,
                  ssmNATPoolDetBlocksFreeTCP,
                  ssmNATPoolDetBlocksFreeUDP,
                  ssmNATPoolDetBlocksInUseSCTP,
                  ssmNATPoolDetBlocksInUseTCP,
                  ssmNATPoolDetBlocksInUseUDP,
                  ssmNATPoolDynBlockAllocLimitCtr,
                  ssmNATPoolDynBlocksFreeSCTP,
                  ssmNATPoolDynBlocksFreeTCP,
                  ssmNATPoolDynBlocksFreeUDP,
                  ssmNATPoolDynBlocksInUseSCTP,
                  ssmNATPoolDynBlocksInUseTCP,
                  ssmNATPoolDynBlocksInUseUDP,
                  ssmNATPoolMaxDetFlowsSCTP,
                  ssmNATPoolMaxDetFlowsTCP,
                  ssmNATPoolMaxDetFlowsUDP,
                  ssmNATPoolMaxDynFlowsSCTP,
                  ssmNATPoolMaxDynFlowsTCP,
                  ssmNATPoolMaxDynFlowsUDP,
                  ssmNATPoolName,
                  ssmNATPoolPortsDepletedCtrSCTP,
                  ssmNATPoolPortsDepletedCtrTCP,
                  ssmNATPoolPortsDepletedCtrUDP,
                  ssmNATPoolActiveStates,
                  ssmNATPoolActiveStatesChanged,
                  ssmNATPoolLingerStatesChanged,
                  ssmNATPoolLingeringStates,
                  ssmNATPoolMaxStatesAllowed,
                  ssmNATPoolMaxStatesUsed,
                  ssmNATPoolActiveStatesReplaced,
                  ssmNATPoolLingerStatesReplaced,
                  ssmNATPoolTotalStates }
    STATUS      current
    DESCRIPTION
        "NATPool Table."
    ::= { clavisterSystemStatsGroups 55 }

ssmNDPInterfaceGroup OBJECT-GROUP
    OBJECTS     { 
                  ssmNDPIfaceName,
                  ssmNDPIfaceNeighborAdvsRecv,
                  ssmNDPIfaceNeighborAdvsSent,
                  ssmNDPIfaceNeighborSolicsRecv,
                  ssmNDPIfaceNeighborSolicsSent,
                  ssmNDPIfaceRouterAdvsRecv,
                  ssmNDPIfaceRouterAdvsSent,
                  ssmNDPIfaceRouterSolicsRecv,
                  ssmNDPIfaceRouterSolicsSent,
                  ssmNDPMinPrefixLifetime,
                  ssmNDPMinPrefixLifetimeRemaining,
                  ssmNDPNumPrefixes,
                  ssmNDPNumPrefixesOnLink }
    STATUS      current
    DESCRIPTION
        "NDP interface table."
    ::= { clavisterSystemStatsGroups 61 }

ssmNDPNeighborGroup OBJECT-GROUP
    OBJECTS     { 
                  ssmNDPNeighborAdvsRecv,
                  ssmNDPNeighborAdvsSent,
                  ssmNDPNeighborSolicsRecv,
                  ssmNDPNeighborSolicsSent }
    STATUS      current
    DESCRIPTION
        "NDP neighbor statistics."
    ::= { clavisterSystemStatsGroups 62 }

ssmNDPRouterGroup OBJECT-GROUP
    OBJECTS     { 
                  ssmNDPRouterAdvsRecv,
                  ssmNDPRouterAdvsSent,
                  ssmNDPRouterSolicsRecv,
                  ssmNDPRouterSolicsSent }
    STATUS      current
    DESCRIPTION
        "NDP router statistics."
    ::= { clavisterSystemStatsGroups 63 }

ssmOSPFGroup OBJECT-GROUP
    OBJECTS     { 
                  ssmOspfPktParamErrors }
    STATUS      current
    DESCRIPTION
        "OSPF statistics."
    ::= { clavisterSystemStatsGroups 22 }

ssmOspfProcGroup OBJECT-GROUP
    OBJECTS     { 
                  ssmOspfCurrentLSA,
                  ssmOspfCurrentRouters,
                  ssmOspfCurrentRoutes,
                  ssmOspfExportedRoutes,
                  ssmOspfFailedAdjacencies,
                  ssmOspfLsaErrors,
                  ssmOspfMaxLsa,
                  ssmOspfMaxRouters,
                  ssmOspfMaxRoutes,
                  ssmOspfProcName }
    STATUS      current
    DESCRIPTION
        "OSPF statistics table."
    ::= { clavisterSystemStatsGroups 21 }

ssmPipeStatsGroup OBJECT-GROUP
    OBJECTS     { 
                  ssmPipeStatsGroupsActive,
                  ssmPipeStatsAvgInterval,
                  ssmPipeStatsAvgTotalBpsRecv,
                  ssmPipeStatsAvgTotalBpsSent,
                  ssmPipeStatsAvgTotalPpsRecv,
                  ssmPipeStatsAvgTotalPpsSent,
                  ssmPipeStatsGroupLimitBps,
                  ssmPipeStatsGroupLimitPps,
                  ssmPipeName,
                  ssmPipeStatsTotalBpsRecv,
                  ssmPipeStatsTotalBpsSent,
                  ssmPipeStatsTotalByteRecv,
                  ssmPipeStatsTotalByteSent,
                  ssmPipeStatsGroupsTotal,
                  ssmPipeStatsTotalPktsRecv,
                  ssmPipeStatsTotalPktsSent,
                  ssmPipeStatsTotalPpsRecv,
                  ssmPipeStatsTotalPpsSent }
    STATUS      current
    DESCRIPTION
        "Pipe object statistics module."
    ::= { clavisterSystemStatsGroups 43 }

ssmPipeStatsPrecedenceGroup OBJECT-GROUP
    OBJECTS     { 
                  ssmPipePrecAvgBpsRecv,
                  ssmPipePrecAvgBpsSent,
                  ssmPipePrecAvgPpsRecv,
                  ssmPipePrecAvgPpsSent,
                  ssmPipePrecBpsRecv,
                  ssmPipePrecBpsSent,
                  ssmPipePrecByteRecv,
                  ssmPipePrecByteSent,
                  ssmPipePrecGroupLimitBps,
                  ssmPipePrecGroupLimitPps,
                  ssmPipePrecPktsRecv,
                  ssmPipePrecPktsSent,
                  ssmPipePrecPpsRecv,
                  ssmPipePrecPpsSent,
                  ssmPipePrecName }
    STATUS      current
    DESCRIPTION
        "Pipe object precedence statistics module."
    ::= { clavisterSystemStatsGroups 44 }

ssmPktAccGroup OBJECT-GROUP
    OBJECTS     { 
                  ssmPktAccName,
                  ssmPktAccUsage }
    STATUS      current
    DESCRIPTION
        "Packet account statistics table."
    ::= { clavisterSystemStatsGroups 47 }

ssmRADIUSGroup OBJECT-GROUP
    OBJECTS     { 
                  ssmRadiusAcceptPktsRecv,
                  ssmRadiusNonRespServer,
                  ssmRadiusPktsParseFail,
                  ssmRadiusRejectPktsRecv,
                  ssmRadiusReqPktResends,
                  ssmRadiusReqPktsSent }
    STATUS      current
    DESCRIPTION
        "RADIUS statistics."
    ::= { clavisterSystemStatsGroups 18 }

ssmRouteMonGroup OBJECT-GROUP
    OBJECTS     { 
                  ssmRouteMonDisables,
                  ssmRouteMonFailReason,
                  ssmRouteMonInterface,
                  ssmRouteMonName,
                  ssmRouteMonNetwork,
                  ssmRouteMonRoutingTable,
                  ssmRouteMonStatus }
    STATUS      current
    DESCRIPTION
        "Route statistics."
    ::= { clavisterSystemStatsGroups 46 }

ssmRouteMonitoringGroup OBJECT-GROUP
    OBJECTS     { 
                  ssmRouteMonNumDisabled,
                  ssmRouteMonNumMonitored }
    STATUS      current
    DESCRIPTION
        "Route monitoring statistics."
    ::= { clavisterSystemStatsGroups 45 }

ssmRoutingGroup OBJECT-GROUP
    OBJECTS     { 
                  ssmDynRoutesCreated,
                  ssmDynRoutesCurrent,
                  ssmDynRoutesMax,
                  ssmStaticRoutes }
    STATUS      current
    DESCRIPTION
        "Routing statistics."
    ::= { clavisterSystemStatsGroups 10 }

ssmRoutingOriginatorGroup OBJECT-GROUP
    OBJECTS     { 
                  ssmOriginatorDynRoutesCreated,
                  ssmOriginatorDynRoutesCurrent,
                  ssmOriginatorDynRoutesName,
                  ssmOriginatorDynRoutesMax }
    STATUS      current
    DESCRIPTION
        "Routing originators statistics."
    ::= { clavisterSystemStatsGroups 4 }

ssmRoutingTableGroup OBJECT-GROUP
    OBJECTS     { 
                  ssmRoutingTableDynRoutesCreated,
                  ssmRoutingTableDynRoutesCurrent,
                  ssmRoutingTableDynRoutesMax,
                  ssmRoutingTableName,
                  ssmRoutingTableStaticRoutes }
    STATUS      current
    DESCRIPTION
        "Routing table statistics."
    ::= { clavisterSystemStatsGroups 12 }

ssmSIPALGGlobalGroup OBJECT-GROUP
    OBJECTS     { 
                  ssmSIPALGActiveMediaSessionsSys,
                  ssmSIPALGActiveCallSessionsSys,
                  ssmSIPALGActiveSessionsSys,
                  ssmSIPALGActiveRegistrationsSys,
                  ssmSIPALGMediaSesDiscTimeoutSys,
                  ssmSIPALGSesDiscRegTimeoutSys,
                  ssmSIPALGSesDiscTimeoutSys,
                  ssmSIPALGRegistrationsFailSys,
                  ssmSIPALGMediaSesNegSys,
                  ssmSIPALGRegHijackDropSys,
                  ssmSIPALGSignalErrSys,
                  ssmSIPALGRegistrationsSys }
    STATUS      current
    DESCRIPTION
        "Global SIPALG statistics."
    ::= { clavisterSystemStatsGroups 65 }

ssmSIPALGProfilesGroup OBJECT-GROUP
    OBJECTS     { 
                  ssmSIPALGIndex,
                  ssmSIPALGName,
                  ssmSIPALGActiveMediaSessions,
                  ssmSIPALGActiveRegistrations,
                  ssmSIPALGActiveCallSessions,
                  ssmSIPALGActiveSessions,
                  ssmSIPALGMediaSesDiscTimeout,
                  ssmSIPALGSesDiscRegTimeout,
                  ssmSIPALGSesDiscTimeout,
                  ssmSIPALGRegistrationsFail,
                  ssmSIPALGMediaSesNeg,
                  ssmSIPALGRegHijackDrop,
                  ssmSIPALGSignalErr,
                  ssmSIPALGRegistrations }
    STATUS      current
    DESCRIPTION
        "SIPALG profile statistics."
    ::= { clavisterSystemStatsGroups 66 }

ssmSNMPGroup OBJECT-GROUP
    OBJECTS     { 
                  ssmSnmpFailedRequests,
                  ssmSnmpASNParseErrors,
                  ssmSnmpBadCommunityName,
                  ssmSnmpBadCommunityUse,
                  ssmSnmpBadVersion,
                  ssmSnmpPktsRecv,
                  ssmSnmpdEngineBoots,
                  ssmSnmpSilentDrops,
                  ssmSnmpSuccessfulRequests,
                  ssmSnmpThrottledRequests,
                  ssmSnmpDecryptionErrors,
                  ssmSnmpNotInTimeWindows,
                  ssmSnmpUnknownEngineIDs,
                  ssmSnmpUnknownUserNames,
                  ssmSnmpUnsupportedSecLevels,
                  ssmSnmpWrongDigests }
    STATUS      current
    DESCRIPTION
        "SNMP statistics."
    ::= { clavisterSystemStatsGroups 7 }

ssmSNMPTrapLogGroup OBJECT-GROUP
    OBJECTS     { 
                  ssmSnmpTrapLogIPCFail,
                  ssmSnmpTrapLogMemAllocFail,
                  ssmSnmpTrapLogThrottled,
                  ssmSnmpTrapLogSent }
    STATUS      current
    DESCRIPTION
        "SNMP trap log statistics."
    ::= { clavisterSystemStatsGroups 42 }

ssmSSLInspectionGroup OBJECT-GROUP
    OBJECTS     { 
                  ssmSSLInspFailedIntercepts,
                  ssmSSLInspSuccessfulIntercepts }
    STATUS      current
    DESCRIPTION
        "SSL Inspection."
    ::= { clavisterSystemStatsGroups 88 }

ssmSSLInspectionProfileGroup OBJECT-GROUP
    OBJECTS     { 
                  ssmClientFailedTLS,
                  ssmServerFailedTLS,
                  ssmSSLInspectionProfileName,
                  ssmClientSuccessfulTLS,
                  ssmServerSuccessfulTLS }
    STATUS      current
    DESCRIPTION
        "SSL Inspection per profile statistics."
    ::= { clavisterSystemStatsGroups 89 }

ssmSSLVPNGlobalGroup OBJECT-GROUP
    OBJECTS     { 
                  ssmSSLVPNAntiReplayFailsSys,
                  ssmSSLVPNChallengeActiveSys,
                  ssmSSLVPNChallengeFailedSys,
                  ssmSSLVPNChallengeSuccessSys,
                  ssmSSLVPNCtrlBytesRecvSys,
                  ssmSSLVPNCtrlBytesSentSys,
                  ssmSSLVPNCtrlPktsRecvSys,
                  ssmSSLVPNCtrlPktsResentSys,
                  ssmSSLVPNCtrlPktsSentSys,
                  ssmSSLVPNDecryptFailsSys,
                  ssmSSLVPNIntegrityFailsSys,
                  ssmSSLVPNInvalidPacketsSys,
                  ssmSSLVPNNegActiveSys,
                  ssmSSLVPNNegFailedSys,
                  ssmSSLVPNNegSuccessSys,
                  ssmSSLVPNReNegActiveSys,
                  ssmSSLVPNReNegFailedSys,
                  ssmSSLVPNReNegSuccessSys,
                  ssmSSLVPNSessCurrAuthSys,
                  ssmSSLVPNSessCurrSys,
                  ssmSSLVPNSessTimedOutSys,
                  ssmSSLVPNSessTotalSys }
    STATUS      current
    DESCRIPTION
        "Global SSLVPN interface statistics."
    ::= { clavisterSystemStatsGroups 85 }

ssmSSLVPNIfStatsGroup OBJECT-GROUP
    OBJECTS     { 
                  ssmSSLVPNDataReplayFails,
                  ssmSSLVPNChallengeActive,
                  ssmSSLVPNChallengeFailed,
                  ssmSSLVPNChallengeSuccess,
                  ssmSSLVPNCtrlBytesRecv,
                  ssmSSLVPNCtrlBytesSent,
                  ssmSSLVPNCtrlPktsRecv,
                  ssmSSLVPNCtrlPktsResent,
                  ssmSSLVPNCtrlPktsSent,
                  ssmSSLVPNDataDecryptFails,
                  ssmSSLVPNDataIntegrityFails,
                  ssmSSLVPNDataInvalidPkts,
                  ssmSSLVPNIfName,
                  ssmSSLVPNNegActive,
                  ssmSSLVPNNegFailed,
                  ssmSSLVPNNegSuccess,
                  ssmSSLVPNReNegActive,
                  ssmSSLVPNReNegFailed,
                  ssmSSLVPNReNegSuccess,
                  ssmSSLVPNSessCur,
                  ssmSSLVPNSessCurrAuth,
                  ssmSSLVPNSessTimedOut,
                  ssmSSLVPNSessTotal }
    STATUS      current
    DESCRIPTION
        "SSLVPN interface statistics."
    ::= { clavisterSystemStatsGroups 86 }

ssmSyslogGroup OBJECT-GROUP
    OBJECTS     { 
                  ssmSyslogIPCFail,
                  ssmSyslogMemAllocFail,
                  ssmSyslogThrottled,
                  ssmSyslogSent }
    STATUS      current
    DESCRIPTION
        "Syslog statistics."
    ::= { clavisterSystemStatsGroups 40 }

ssmSystemGroup OBJECT-GROUP
    OBJECTS     { 
                  ssmSysContact,
                  ssmSysName,
                  ssmSysLocation,
                  ssmVendorName,
                  ssmHardwareModel,
                  ssmProductName,
                  ssmHardwareSerialNumber,
                  ssmHardwareDateOfManufacture }
    STATUS      current
    DESCRIPTION
        "System statistics."
    ::= { clavisterSystemStatsGroups 6 }

ssmThresholdGroup OBJECT-GROUP
    OBJECTS     { 
                  ssmThresholdTotalActionBlacklist,
                  ssmThresholdTotalActionDrop,
                  ssmThresholdTotalActionNone,
                  ssmThresholdTotalActionRndDrop,
                  ssmThresholdTotalActRndDropDeny,
                  ssmThresholdTotalActionReject,
                  ssmThresholdTotalActiveGroups,
                  ssmThresholdTotalGroupExceeded,
                  ssmThresholdTotalOffendingGroups,
                  ssmThresholdTotalGroups }
    STATUS      current
    DESCRIPTION
        "Global threshold statistics module."
    ::= { clavisterSystemStatsGroups 57 }

ssmThresholdActionLimitGroup OBJECT-GROUP
    OBJECTS     { 
                  ssmThresholdLimitGroupsActive,
                  ssmThresholdLimitGroupsExceeded,
                  ssmThresholdActionLimitName,
                  ssmThresholdLimitGroupExceeding }
    STATUS      current
    DESCRIPTION
        "Threshold definition statistics module."
    ::= { clavisterSystemStatsGroups 78 }

ssmThresholdRuleActionGroup OBJECT-GROUP
    OBJECTS     { 
                  ssmThresholdActionName,
                  ssmThresholdActionTrigged }
    STATUS      current
    DESCRIPTION
        "Threshold action statistics module."
    ::= { clavisterSystemStatsGroups 79 }

ssmThresholdRuleSetGroup OBJECT-GROUP
    OBJECTS     { 
                  ssmThresholdRuleSetName }
    STATUS      current
    DESCRIPTION
        "Threshold RuleSet statistics table."
    ::= { clavisterSystemStatsGroups 73 }

ssmThresholdRuleStatsGroup OBJECT-GROUP
    OBJECTS     { 
                  ssmThresholdRuleLastReset,
                  ssmThresholdRuleMatched,
                  ssmThresholdRuleName,
                  ssmThresholdRuleTotalDrops,
                  ssmThresholdRuleTotalTrigged }
    STATUS      current
    DESCRIPTION
        "Threshold rule statistics table."
    ::= { clavisterSystemStatsGroups 74 }

ssmTimeSyncGroup OBJECT-GROUP
    OBJECTS     { 
                  ssmNTPActiveServers,
                  ssmNTPClockSynchronizations,
                  ssmNTPLastError,
                  ssmNTPLastSynchronization,
                  ssmNTPLasySyncTime,
                  ssmNTPLatestTimeDrift,
                  ssmNTPMaximumTimeDrift,
                  ssmNTPNextSynchronization,
                  ssmNTPResponsesDiscarded,
                  ssmNTPResponsesReceived,
                  ssmNTPRequestsSent,
                  ssmNTPServerAddress,
                  ssmNTPTimeAfter,
                  ssmNTPTimeBefore,
                  ssmNTPUpdateMethod }
    STATUS      current
    DESCRIPTION
        "Time syncronization client statistics."
    ::= { clavisterSystemStatsGroups 2 }

ssmTrafficGroup OBJECT-GROUP
    OBJECTS     { 
                  ssmSysFwdBytes,
                  ssmSysFwdIPsecBytes,
                  ssmSysFwdIPsecPackets,
                  ssmSysFwdPackets,
                  ssmSysForwardedVPNBytes,
                  ssmSysForwardedVPNPackets }
    STATUS      current
    DESCRIPTION
        "Traffic statistics."
    ::= { clavisterSystemStatsGroups 64 }

clavisterSystemCompliance MODULE-COMPLIANCE
    STATUS      current
    DESCRIPTION
        "Module Compliance"

    MODULE      -- this module

    MANDATORY-GROUPS {
                  ssmARPGroup,
                  ssmAdminParametersGroup,
                  ssmAppCtrlStatsGroup,
                  ssmApplicationControlGroup,
                  ssmAuthProfilesGroup,
                  ssmAuthenticationSystemGroup,
                  ssmBlacklistGroup,
                  ssmCLILogGroup,
                  ssmCPUGroup,
                  ssmCpuStatsGroup,
                  ssmCryptoDeviceGroup,
                  ssmDHCPClientGroup,
                  ssmDHCPServerGroup,
                  ssmDHCPServerRuleGroup,
                  ssmDNSGroup,
                  ssmDNSALGProfilesGroup,
                  ssmFTPGroup,
                  ssmFTPALGProfilesGroup,
                  ssmFlowGroup,
                  ssmGTPIfStatsGroup,
                  ssmGTPCGlobalGroup,
                  ssmGTPUGlobalGroup,
                  ssmGTPInspProfilesGroup,
                  ssmHAGroup,
                  ssmHAFailuresGroup,
                  ssmHAFlowGroup,
                  ssmHAFragGroup,
                  ssmHAIfStatsGroup,
                  ssmHAIntDepGroup,
                  ssmHAInternalGroup,
                  ssmHAModulesGroup,
                  ssmHWSensorGroup,
                  ssmIKEv1GlobalGroup,
                  ssmIKEv2GlobalGroup,
                  ssmIPRuleSetGroup,
                  ssmIPRuleStatsGroup,
                  ssmIPSGroup,
                  ssmIPSRuleStatsGroup,
                  ssmIPSRulesGroup,
                  ssmIPsecIfStatsGroup,
                  ssmIfStatsGroup,
                  ssmIfaceGlobalGroup,
                  ssmLogReceiverGroup,
                  ssmLogsGroup,
                  ssmMemCatGroup,
                  ssmMemProcessGroup,
                  ssmMemoryGroup,
                  ssmNATPoolGroup,
                  ssmNDPInterfaceGroup,
                  ssmNDPNeighborGroup,
                  ssmNDPRouterGroup,
                  ssmOSPFGroup,
                  ssmOspfProcGroup,
                  ssmPipeStatsGroup,
                  ssmPipeStatsPrecedenceGroup,
                  ssmPktAccGroup,
                  ssmRADIUSGroup,
                  ssmRouteMonGroup,
                  ssmRouteMonitoringGroup,
                  ssmRoutingGroup,
                  ssmRoutingOriginatorGroup,
                  ssmRoutingTableGroup,
                  ssmSIPALGGlobalGroup,
                  ssmSIPALGProfilesGroup,
                  ssmSNMPGroup,
                  ssmSNMPTrapLogGroup,
                  ssmSSLInspectionGroup,
                  ssmSSLInspectionProfileGroup,
                  ssmSSLVPNGlobalGroup,
                  ssmSSLVPNIfStatsGroup,
                  ssmSyslogGroup,
                  ssmSystemGroup,
                  ssmThresholdGroup,
                  ssmThresholdActionLimitGroup,
                  ssmThresholdRuleActionGroup,
                  ssmThresholdRuleSetGroup,
                  ssmThresholdRuleStatsGroup,
                  ssmTimeSyncGroup,
                  ssmTrafficGroup }
    ::= { clavisterStatsConformance 2 }

END -- end of module CLAVISTER-STREAM-MIB.
