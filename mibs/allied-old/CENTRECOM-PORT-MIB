-- ===============================================================================

--
-- Atkk Switch Port objects
--

CENTRECOM-PORT-MIB DEFINITIONS ::= BEGIN

        IMPORTS
                MODULE-IDENTITY         FROM SNMPv2-SMI
		RowStatus               FROM SNMPv2-TC
		OBJECT-TYPE             FROM RFC-1212
        extSwitchMIB        FROM CENTRECOM-MIB;

        atiPort MODULE-IDENTITY
                LAST-UPDATED "9802030000Z"
                ORGANIZATION "Allied Telesis K.K"
                CONTACT-INFO "www1.allied-telesis.co.jp/GIGA"
                DESCRIPTION "Atkk network port objects"
        ::= { extSwitchMIB 6 }

--
-- Load-sharing
--
	atiPortLoadshareTable OBJECT-TYPE
		SYNTAX  SEQUENCE OF AtiPortLoadshareEntry
		ACCESS  not-accessible
		STATUS  mandatory
		DESCRIPTION
                      "A table of bindings between a master port 
                        and its load-sharing slaves: create/delete 
                        entries here to add/delete a port to/from a 
                        load-sharing group. Default is empty table. 
                        There are restrictions on what row creates 
                        will be accepted by each device - see Summit 
                        release notes for details."
	::= { atiPort 1 }

	atiPortLoadshareEntry OBJECT-TYPE
		SYNTAX  AtiPortLoadshareEntry
		ACCESS  not-accessible
		STATUS  mandatory
		DESCRIPTION
                      "A binding between a master port and one
                       of its load-sharing slave ports."
                INDEX { atiPortLoadshareMasterIfIndex, 
                        atiPortLoadshareSlaveIfIndex } 
	::= { atiPortLoadshareTable 1 }

	AtiPortLoadshareEntry ::= SEQUENCE {
                atiPortLoadshareMasterIfIndex INTEGER, 
                atiPortLoadshareSlaveIfIndex INTEGER,
   				atiPortLoadshareGrouping	INTEGER,
                atiPortLoadshareStatus RowStatus 
	}

	atiPortLoadshareMasterIfIndex OBJECT-TYPE
                SYNTAX INTEGER
                ACCESS  read-write
                STATUS  mandatory
                DESCRIPTION
                      "The ifIndex value which identifies the
                       port controlling a loadsharing group
                       of ports which includes
                       atiPortLoadshareSlaveIfIndex."
        ::= { atiPortLoadshareEntry 1 }

	atiPortLoadshareSlaveIfIndex OBJECT-TYPE
                SYNTAX INTEGER
                ACCESS  read-write
                STATUS  mandatory
                DESCRIPTION
                      "The ifIndex value which identifies the
                       port which is a member of a loadsharing 
                       group controlled by 
                        atiPortLoadshareMasterIfIndex."
        ::= { atiPortLoadshareEntry 2 }

	atiPortLoadshareGrouping OBJECT-TYPE
                SYNTAX INTEGER { pair (2), quad (4) }
                ACCESS  read-write
                STATUS  mandatory
                DESCRIPTION
                      "The Grouping value which identifies if load sharing is
                      in pair or quad."
        ::= { atiPortLoadshareEntry 3 }

	atiPortLoadshareStatus OBJECT-TYPE
                SYNTAX  RowStatus
                ACCESS  read-write
                STATUS  mandatory
                DESCRIPTION
                        "The row status variable, used according to
                        row installation and removal conventions."
        ::= { atiPortLoadshareEntry 4 }

END
